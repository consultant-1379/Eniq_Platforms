-- File Name : BW-RatingFunctionFault.mib
BW-RatingFunctionFault DEFINITIONS ::= BEGIN
  IMPORTS
    NOTIFICATION-TYPE, MODULE-IDENTITY
      FROM SNMPv2-SMI
    common, identifier, timeStamp, alarmName, systemName, severity, alarmState, component, subcomponent, problemText, recommendedActionsText
      FROM BroadworksFault;

  systemFaults MODULE-IDENTITY
    LAST-UPDATED  "201206010000Z"
    ORGANIZATION  "Broadsoft, Inc"
    CONTACT-INFO  "Broadsoft, Inc.
9737 Washingtonian Blvd
Suite 350
Gaithersburg , MD 20878
Tel: +1-301-977-9440"
    DESCRIPTION
        "This MIB defines the faults for the BroadWorks RatingFunction Application."
    REVISION    "201206010000Z"
                DESCRIPTION     "Creation of the Fault MIB."
    ::=  {  common  1  }

  bwPMRatingFunctionLaunched  NOTIFICATION-TYPE
    OBJECTS     { identifier, timeStamp, alarmName, systemName, severity, component, subcomponent, problemText, recommendedActionsText }
    STATUS      current
    DESCRIPTION
        "This notification indicates that the RatingFunction has been started.
@severity:informational
@subcomponent:processmonitor
@correlationrules:bwPMRatingFunctionLaunched, bwPMRatingFunctionShutDown, bwPMRatingFunctionRestarted, bwPMRatingFunctionDeath and bwPMRatingFunctionOutOfMemory can be correlated into a single alarm.  These events have to be considered as a transition of the state machine for the management of the RatingFunction process"
-- @feature:165352
    ::=  {  systemFaults 11401  }

  bwPMRatingFunctionShutDown  NOTIFICATION-TYPE
    OBJECTS     { identifier, timeStamp, alarmName, systemName, severity, component, subcomponent, problemText, recommendedActionsText }
    STATUS      current
    DESCRIPTION
        "This notification indicates that the RatingFunction has been manually shut down.
@severity:informational
@subcomponent:processmonitor
@correlationrules:bwPMRatingFunctionLaunched, bwPMRatingFunctionShutDown, bwPMRatingFunctionRestarted, bwPMRatingFunctionDeath and bwPMRatingFunctionOutOfMemory can be correlated into a single alarm.  These events have to be considered as a transition of the state machine for the management of the RatingFunction process"
-- @feature:165352
    ::=  {  systemFaults 11402  }

  bwPMRatingFunctionRestarted  NOTIFICATION-TYPE
    OBJECTS     { identifier, timeStamp, alarmName, systemName, severity, component, subcomponent, problemText, recommendedActionsText }
    STATUS      current
    DESCRIPTION
        "This notification provides the date and time of the RatingFunction restart.
@severity:informational
@subcomponent:processmonitor
@correlationrules:bwPMRatingFunctionLaunched, bwPMRatingFunctionShutDown, bwPMRatingFunctionRestarted, bwPMRatingFunctionDeath and bwPMRatingFunctionOutOfMemory can be correlated into a single alarm.  These events have to be considered as a transition of the state machine for the management of the RatingFunction process"
-- @feature:165352
    ::=  {  systemFaults 11403  }

  bwPMRatingFunctionDeath  NOTIFICATION-TYPE
    OBJECTS     { identifier, timeStamp, alarmName, systemName, severity, component, subcomponent, problemText, recommendedActionsText }
    STATUS      current
    DESCRIPTION
        "This notification provides the date and time of the RatingFunction death.
@severity:critical
@subcomponent:processmonitor
@correlationrules:bwPMRatingFunctionLaunched, bwPMRatingFunctionShutDown, bwPMRatingFunctionRestarted, bwPMRatingFunctionDeath and bwPMRatingFunctionOutOfMemory can be correlated into a single alarm.  These events have to be considered as a transition of the state machine for the management of the RatingFunction process"
-- @feature:165352
    ::=  {  systemFaults 11404  }
    
bwPMRatingFunctionOutOfMemory  NOTIFICATION-TYPE
     OBJECTS     { identifier, timeStamp, alarmName, systemName, severity, component, subcomponent, problemText, recommendedActionsText }
     STATUS      current
     DESCRIPTION
         "This notification provides the date and time when the RatingFunction ran out of memory.
 @severity:high
 @subcomponent:processmonitor
 @correlationrules:bwPMRatingFunctionLaunched, bwPMRatingFunctionShutDown, bwPMRatingFunctionRestarted, bwPMRatingFunctionDeath, and bwPMRatingFunctionOutOfMemory can be correlated into a single alarm.  These events have to be considered as a transition of the state machine for the management of the RatingFunction process"
-- @feature:165352
    ::=  {  systemFaults 11405  }  

END

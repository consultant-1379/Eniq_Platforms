-- File Name : BW-ProvisioningFault-XS-TAS.mib

BW-ProvisioningFault-XS-TAS DEFINITIONS ::= BEGIN
  IMPORTS
    NOTIFICATION-TYPE, MODULE-IDENTITY
      FROM SNMPv2-SMI
    common, faultFields, identifier, timeStamp, alarmName, systemName, severity, alarmState, component, subcomponent, problemText, recommendedActionsText, correlationParameter, npRemoteAddress, npRemotePort, npMessage, npReason, npHost, npUserId, npServiceProviderId, npLicenseKey, npGroupId, npFirstName, npLastName, npGroupName, npOriginalAddress, npNewAddress, npDeviceName, npBridgeName, npOperation, npDomain, npTaskName, npNbOfErrors, npTimeLength, npFeatureName, npServerName, npConfiguredAddress, npResolvedAddress, npFilename, npUrl, npCommand, npPublicIdentity, npDataReference, npResultCodeType, npResultCode, npMaximumNbItems, npError, npExceptionMessage, npProfileDescription, npNetAddress, npReportName, npDateTime, npDBSchemaName, npBroadCloudRequest, npBroadCloudUid, npBroadCloudService, npBroadCloudFailureReason
      FROM BroadworksFault;

  systemFaults MODULE-IDENTITY
    LAST-UPDATED  "201303050000Z"
    ORGANIZATION  "Broadsoft, Inc"
    CONTACT-INFO  "Broadsoft, Inc.
9737 Washingtonian Blvd
Suite 350
Gaithersburg , MD 20878
Tel: +1-301-977-9440"
    DESCRIPTION
        "This MIB defines the faults for the Provisioning XS-TAS Server."
    REVISION    "201303050000Z"
                DESCRIPTION     "Creating Provisioning XS-TAS application from Provisioning application."
    REVISION    "201105020000Z"
                DESCRIPTION     "Added object 'correlationParameter' in the OBJECTS clause of applicable faults."
    REVISION    "201009140000Z"
                DESCRIPTION     "Moved object 'alarmState' after object 'severity' in the OBJECTS clause of applicable faults."
    REVISION    "200907200000Z"
                DESCRIPTION     "MIB Creation, based on the defunct BW-ApplicationServerFault.mib."
    ::=  {  common  1  }

-- Provisioning Server Faults...

  bwPMProvisioningServerXSTASLaunched  NOTIFICATION-TYPE
    OBJECTS     { identifier, timeStamp, alarmName, systemName, severity, component, subcomponent, problemText, recommendedActionsText }
    STATUS      current
    DESCRIPTION
        "This notification indicates that the Provisioning XS-TAS Server has been started.
@severity:informational
@subcomponent:processmonitor
@correlationrules:bwPMProvisioningServerXSTASLaunched, bwPMProvisioningServerXSTASShutDown, bwPMProvisioningServerXSTASRestarted, bwPMProvisioningServerXSTASDeath and bwPMProvisioningServerXSTASOutOfMemory can be correlated into a single alarm.  These events have to be considered as a transition of the state machine for the management of the ProvisioningServerXSTAS process."
    ::=  {  systemFaults 11701  }

  bwPMProvisioningServerXSTASShutDown  NOTIFICATION-TYPE
    OBJECTS     { identifier, timeStamp, alarmName, systemName, severity, component, subcomponent, problemText, recommendedActionsText }
    STATUS      current
    DESCRIPTION
        "This notification indicates that the Provisioning XS-TAS Server has been manually shut down.
@severity:informational
@subcomponent:processmonitor
@correlationrules:bwPMProvisioningServerXSTASLaunched, bwPMProvisioningServerXSTASShutDown, bwPMProvisioningServerXSTASRestarted, bwPMProvisioningServerXSTASDeath and bwPMProvisioningServerXSTASOutOfMemory can be correlated into a single alarm.  These events have to be considered as a transition of the state machine for the management of the ProvisioningServerXSTAS process."
    ::=  {  systemFaults 11702  }

  bwPMProvisioningServerXSTASRestarted  NOTIFICATION-TYPE
    OBJECTS     { identifier, timeStamp, alarmName, systemName, severity, component, subcomponent, problemText, recommendedActionsText }
    STATUS      current
    DESCRIPTION
        "This notification provides the date and time of the Provisioning XS-TAS Server restart.
@severity:informational
@subcomponent:processmonitor
@correlationrules:bwPMProvisioningServerXSTASLaunched, bwPMProvisioningServerXSTASShutDown, bwPMProvisioningServerXSTASRestarted, bwPMProvisioningServerXSTASDeath and bwPMProvisioningServerXSTASOutOfMemory can be correlated into a single alarm.  These events have to be considered as a transition of the state machine for the management of the ProvisioningServerXSTAS process."
    ::=  {  systemFaults 11703  }

  bwPMProvisioningServerXSTASDeath  NOTIFICATION-TYPE
    OBJECTS     { identifier, timeStamp, alarmName, systemName, severity, component, subcomponent, problemText, recommendedActionsText }
    STATUS      current
    DESCRIPTION
        "This notification provides the date and time of the Provisioning XS-TAS Server death.
@severity:critical
@subcomponent:processmonitor
@correlationrules:bwPMProvisioningServerXSTASLaunched, bwPMProvisioningServerXSTASShutDown, bwPMProvisioningServerXSTASRestarted, bwPMProvisioningServerXSTASDeath and bwPMProvisioningServerXSTASOutOfMemory can be correlated into a single alarm.  These events have to be considered as a transition of the state machine for the management of the ProvisioningServerXSTAS process."
    ::=  {  systemFaults 11704  }

  bwProvNSSynchronizationConnectivityFailure  NOTIFICATION-TYPE
    OBJECTS     { identifier, timeStamp, alarmName, systemName, severity, component, subcomponent, problemText, recommendedActionsText, npReason }
    STATUS      current
    DESCRIPTION
        "Failure to create data synchronization connection between Provisioning XS-TAS Server and Network Server.
@severity:high
@subcomponent:nssynch"
    ::=  {  systemFaults 11705  }

  bwProvNSLocationConnectivityFailure  NOTIFICATION-TYPE
    OBJECTS     { identifier, timeStamp, alarmName, systemName, severity, alarmState, component, subcomponent, problemText, recommendedActionsText, correlationParameter, npReason, npMessage }
    STATUS      current
    DESCRIPTION
        "Failure with connectivity between the Provisioning XS-TAS Server and the Network Server.
@severity:high
@subcomponent:nssynch"
    ::=  {  systemFaults 11706  }

  bwProvNSLocationFailure  NOTIFICATION-TYPE
    OBJECTS     { identifier, timeStamp, alarmName, systemName, severity, component, subcomponent, problemText, recommendedActionsText, npReason, npMessage, npRemoteAddress }
    STATUS      current
    DESCRIPTION
        "Data may be out of synch between the Provisioning XS-TAS Server and the Network Server.
@severity:medium
@subcomponent:nssynch"
    ::=  {  systemFaults 11707  }

  bwProvLicenseUserServiceAccntViolation  NOTIFICATION-TYPE
    OBJECTS     { identifier, timeStamp, alarmName, systemName, severity, component, subcomponent, problemText, recommendedActionsText, npLicenseKey }
    STATUS      current
    DESCRIPTION
        "This notification indicates that the license allocation has exceeded the limit.
@severity:high
@subcomponent:licensing"
    ::=  {  systemFaults 11708  }

  bwProvAddUserEvent  NOTIFICATION-TYPE
    OBJECTS     { identifier, timeStamp, alarmName, systemName, severity, component, subcomponent, problemText, recommendedActionsText, npUserId }
    STATUS      current
    DESCRIPTION
        "This notification indicates that a user is added.
@severity:informational
@subcomponent:transevent"
    ::=  {  systemFaults 11709  }

  bwProvDeleteUserEvent  NOTIFICATION-TYPE
    OBJECTS     { identifier, timeStamp, alarmName, systemName, severity, component, subcomponent, problemText, recommendedActionsText, npUserId }
    STATUS      current
    DESCRIPTION
        "This notification indicates that a user is deleted.
@severity:informational
@subcomponent:transevent"
    ::=  {  systemFaults 11710  }

  bwProvAddGroupEvent  NOTIFICATION-TYPE
    OBJECTS     { identifier, timeStamp, alarmName, systemName, severity, component, subcomponent, problemText, recommendedActionsText, npGroupId }
    STATUS      current
    DESCRIPTION
        "This notification indicates that a group is added.
@severity:informational
@subcomponent:transevent"
    ::=  {  systemFaults 11711  }

  bwProvDeleteGroupEvent  NOTIFICATION-TYPE
    OBJECTS     { identifier, timeStamp, alarmName, systemName, severity, component, subcomponent, problemText, recommendedActionsText, npGroupId }
    STATUS      current
    DESCRIPTION
        "This notification indicates that a group is deleted.
@severity:informational
@subcomponent:transevent"
    ::=  {  systemFaults 11712  }

  bwProvUserAddressChangeEvent  NOTIFICATION-TYPE
    OBJECTS     { identifier, timeStamp, alarmName, systemName, severity, component, subcomponent, problemText, recommendedActionsText, npFirstName, npLastName, npGroupName, npOriginalAddress, npNewAddress }
    STATUS      current
    DESCRIPTION
        "This notification indicates that a user's address has changed.
@severity:informational
@subcomponent:transevent"
    ::=  {  systemFaults 11713  }

  bwProvGroupAddressChangeEvent  NOTIFICATION-TYPE
    OBJECTS     { identifier, timeStamp, alarmName, systemName, severity, component, subcomponent, problemText, recommendedActionsText, npGroupName, npOriginalAddress, npNewAddress }
    STATUS      current
    DESCRIPTION
        "This notification indicates that a group's address has changed.
@severity:informational
@subcomponent:transevent"
    ::=  {  systemFaults 11714  }

  bwProvLDAPConnectionError  NOTIFICATION-TYPE
    OBJECTS     { identifier, timeStamp, alarmName, systemName, severity, component, subcomponent, problemText, recommendedActionsText, npRemoteAddress, npRemotePort }
    STATUS      current
    DESCRIPTION
        "Unable to establish a connection to the specified LDAP server.
@severity:medium
@subcomponent:ldap"
    ::=  {  systemFaults 11715  }

  bwProvLDAPConfigurationError  NOTIFICATION-TYPE
    OBJECTS     { identifier, timeStamp, alarmName, systemName, severity, component, subcomponent, problemText, recommendedActionsText, npRemoteAddress, npRemotePort }
    STATUS      current
    DESCRIPTION
        "Problem communicating with an LDAP server.  The problem is related to a system configuration error.
@severity:medium
@subcomponent:ldap"
    ::=  {  systemFaults 11716  }

  bwProvICBridgeCommunicationError  NOTIFICATION-TYPE
    OBJECTS     { identifier, timeStamp, alarmName, systemName, severity, component, subcomponent, problemText, recommendedActionsText, npBridgeName, npGroupName, npRemoteAddress, npOperation, npReason }
    STATUS      current
    DESCRIPTION
        "The alarm is generated at provisioning time when a communication problem to the BroadWorks Conferencing Server is detected.
@severity:medium
@subcomponent:conferencing"
    ::=  {  systemFaults 11717  }

  bwProvICBridgeResetError  NOTIFICATION-TYPE
    OBJECTS     { identifier, timeStamp, alarmName, systemName, severity, component, subcomponent, problemText, recommendedActionsText, npBridgeName }
    STATUS      obsolete
    DESCRIPTION
        "The alarm is generated when the bridge reset password operation is completed, successfully or not.
@severity:medium
@subcomponent:conferencing"
    ::=  {  systemFaults 11718  }

  bwProvExternalAuthenticationUnknownUser  NOTIFICATION-TYPE
    OBJECTS     { identifier, timeStamp, alarmName, systemName, severity, component, subcomponent, problemText, recommendedActionsText, npUserId, npDomain }
    STATUS      current
    DESCRIPTION
        "Applies to the scenario when the:
User ID is not provided or unknown, and/or,
Domain is required but not provided or unknown/incorrect.
@severity:low
@subcomponent:externalAuthentication"
    ::=  {  systemFaults 11719  }

  bwProvSrvcPackMigrationTerminated  NOTIFICATION-TYPE
    OBJECTS     { identifier, timeStamp, alarmName, systemName, severity, component, subcomponent, problemText, recommendedActionsText, npTaskName, npServiceProviderId, npUserId }
    STATUS      current
    DESCRIPTION
        "An administrator deliberately terminated a migration task before it was finished.
@severity:informational
@subcomponent:servicePackMigration"
    ::=  {  systemFaults 11720  }

  bwProvSrvcPackMigrationCompletedWithErrors  NOTIFICATION-TYPE
    OBJECTS     { identifier, timeStamp, alarmName, systemName, severity, component, subcomponent, problemText, recommendedActionsText, npTaskName, npServiceProviderId, npNbOfErrors }
    STATUS      current
    DESCRIPTION
        "A migration task ran to completion, but there were one or more errors.
@severity:medium
@subcomponent:servicePackMigration"
    ::=  {  systemFaults 11721  }

  bwProvSrvcPackMigrationStoppedDueToErrors  NOTIFICATION-TYPE
    OBJECTS     { identifier, timeStamp, alarmName, systemName, severity, component, subcomponent, problemText, recommendedActionsText, npTaskName, npServiceProviderId, npNbOfErrors }
    STATUS      current
    DESCRIPTION
        "A migration task was automatically stopped by the system because the number of errors reached the error threshold.
@severity:medium
@subcomponent:servicePackMigration"
    ::=  {  systemFaults 11722  }

  bwProvSrvcPackMigrationStoppedDueToTimeLimit  NOTIFICATION-TYPE
    OBJECTS     { identifier, timeStamp, alarmName, systemName, severity, component, subcomponent, problemText, recommendedActionsText, npTaskName, npServiceProviderId, npTimeLength }
    STATUS      current
    DESCRIPTION
        "A migration task was automatically stopped by the system because the duration of the task reached the maximum allowed time.
@severity:medium
@subcomponent:servicePackMigration"
    ::=  {  systemFaults 11723  }

  bwProvSrvcPackMigrationStoppedBySysShutdown  NOTIFICATION-TYPE
    OBJECTS     { identifier, timeStamp, alarmName, systemName, severity, component, subcomponent, problemText, recommendedActionsText, npTaskName, npServiceProviderId }
    STATUS      current
    DESCRIPTION
        "A migration task was automatically stopped by the system because the system was shut down.
@severity:medium
@subcomponent:servicePackMigration"
    ::=  {  systemFaults 11724  }

  bwProvSrvcPackMigrationFoundUnfinishedTask  NOTIFICATION-TYPE
    OBJECTS     { identifier, timeStamp, alarmName, systemName, severity, component, subcomponent, problemText, recommendedActionsText, npTaskName, npServiceProviderId }
    STATUS      current
    DESCRIPTION
        "An unfinished migration task was found during system restart.  This could happen if the system is not shut down gracefully.
@severity:medium
@subcomponent:servicePackMigration"
    ::=  {  systemFaults 11725  }

  bwProvSrvcPackMigrationLicenseViolation  NOTIFICATION-TYPE
    OBJECTS     { identifier, timeStamp, alarmName, systemName, severity, component, subcomponent, problemText, recommendedActionsText, npTaskName, npServiceProviderId }
    STATUS      current
    DESCRIPTION
        "A migration task was stopped because of pre-existing system license violation.
@severity:medium
@subcomponent:servicePackMigration
"
    ::=  {  systemFaults 11726  }

  bwProvSrvcPackMigrationSpSrvcQuantityViolation  NOTIFICATION-TYPE
    OBJECTS     { identifier, timeStamp, alarmName, systemName, severity, component, subcomponent, problemText, recommendedActionsText, npTaskName, npServiceProviderId, npFeatureName }
    STATUS      current
    DESCRIPTION
        "A migration task was stopped because of pre-existing system license violation.
@severity:medium
@subcomponent:servicePackMigration"
    ::=  {  systemFaults 11727  }

  bwProvSrvcPackMigrationSystemError  NOTIFICATION-TYPE
    OBJECTS     { identifier, timeStamp, alarmName, systemName, severity, component, subcomponent, problemText, recommendedActionsText, npTaskName, npServiceProviderId }
    STATUS      current
    DESCRIPTION
        "A migration task was stopped due to a non-recoverable system error.
@severity:medium
@subcomponent:servicePackMigration"
    ::=  {  systemFaults 11728  }

  bwProvCallLogSOAPServerUnreachable  NOTIFICATION-TYPE
    OBJECTS     { identifier, timeStamp, alarmName, systemName, severity, alarmState, component, subcomponent, problemText, recommendedActionsText, correlationParameter, npServerName, npConfiguredAddress, npResolvedAddress }
    STATUS      current
    DESCRIPTION
        "A Call Detail Server is not responding to read Requests.
@severity:high
@subcomponent:callLogs"
    ::=  {  systemFaults 11729  }

  bwProvOciReportingAclViolation  NOTIFICATION-TYPE
    OBJECTS     { identifier, timeStamp, alarmName, systemName, severity, component, subcomponent, problemText, recommendedActionsText, npRemoteAddress }
    STATUS      current
    DESCRIPTION
        "Connection request received from an unknown external system.
@severity:low
@subcomponent:ociReporting"
    ::=  {  systemFaults 11730  }

  bwProvOciReportingConnectionError  NOTIFICATION-TYPE
    OBJECTS     { identifier, timeStamp, alarmName, systemName, severity, alarmState, component, subcomponent, problemText, recommendedActionsText, correlationParameter, npRemoteAddress }
    STATUS      current
    DESCRIPTION
        "Error detected on connection to an external system.
@severity:low
@subcomponent:ociReporting"
    ::=  {  systemFaults 11731  }

  bwProvOciReportingBackLogFileDeleted NOTIFICATION-TYPE
    OBJECTS     { identifier, timeStamp, alarmName, systemName, severity, component, subcomponent, problemText, recommendedActionsText, npFilename, npHost }
    STATUS      current
    DESCRIPTION
        "The total size of the OCI reporting backlog files exceeded the system limit (500 MB).  The oldest file is deleted.
@severity:low
@subcomponent:ociReporting"
    ::=  {  systemFaults 11732  }

  bwProvValidationConnectionFailure NOTIFICATION-TYPE
    OBJECTS     { identifier, timeStamp, alarmName, systemName, severity, component, subcomponent, problemText, recommendedActionsText }
    STATUS      current
    DESCRIPTION
        "Connection between the Provisioning XS-TAS Server and the Execution Server for provisioning validation cannot be established.
@severity:low
@subcomponent:ociReporting"
    ::=  {  systemFaults 11733  }

  bwProvShNoAvailableHosts   NOTIFICATION-TYPE
    OBJECTS     { identifier, timeStamp, alarmName, systemName, severity, component, subcomponent, problemText, recommendedActionsText, npCommand, npPublicIdentity, npDataReference }
    STATUS      current
    DESCRIPTION
        "This fault is generated when host selection has exhausted all hosts.
@severity:high
@subcomponent:sh"
    ::= { systemFaults 11734 }

  bwProvShUserUnknownInHSS   NOTIFICATION-TYPE
    OBJECTS     { identifier, timeStamp, alarmName, systemName, severity, component, subcomponent, problemText, recommendedActionsText, npCommand, npPublicIdentity }
    STATUS      current
    DESCRIPTION
        "This fault is generated whenever the Provisioning XS-TAS Server receives an answer indicating that the user is unknown in the HSS.
@severity:high
@subcomponent:sh"
    ::= { systemFaults 11735 }

  bwProvShUserUnknownInAS   NOTIFICATION-TYPE
    OBJECTS     { identifier, timeStamp, alarmName, systemName, severity, component, subcomponent, problemText, recommendedActionsText, npCommand, npPublicIdentity }
    STATUS      current
    DESCRIPTION
        "This fault is generated whenever the Provisioning XS-TAS Server receives a request for a public identity that is unknown.
@severity:high
@subcomponent:sh"
    ::= { systemFaults 11736 }

  bwProvShGeneralErrorReceived   NOTIFICATION-TYPE
    OBJECTS     { identifier, timeStamp, alarmName, systemName, severity, component, subcomponent, problemText, recommendedActionsText, npCommand, npPublicIdentity, npResultCodeType, npResultCode }
    STATUS      current
    DESCRIPTION
        "This fault is generated whenever the Provisioning XS-TAS Server encounters an error that results in the failure of the public identity refresh procedure for reasons other than unknown user or host selection exhaustion.
@severity:high
@subcomponent:sh"
    ::= { systemFaults 11737 }

  bwProvShSystemRefreshInitiated   NOTIFICATION-TYPE
    OBJECTS     { identifier, timeStamp, alarmName, systemName, severity, component, subcomponent, problemText, recommendedActionsText }
    STATUS      current
    DESCRIPTION
        "This notification is generated whenever the Provisioning XS-TAS Server initiates the system refresh procedure over the Sh Interface.
@severity:informational
@subcomponent:sh"
    ::= { systemFaults 11738 }

  bwProvShSystemRefreshTerminated   NOTIFICATION-TYPE
    OBJECTS     { identifier, timeStamp, alarmName, systemName, severity, component, subcomponent, problemText, recommendedActionsText, npReason }
    STATUS      current
    DESCRIPTION
        "This notification is generated whenever the Provisioning XS-TAS Server has stopped the system refresh procedure over the Sh Interface.
@severity:informational
@subcomponent:sh"
    ::= { systemFaults 11739 }

  bwProvMobilityManagerUnreachable NOTIFICATION-TYPE
    OBJECTS     { identifier, timeStamp, alarmName, systemName, severity, component, subcomponent, problemText, recommendedActionsText, npUrl, npMessage }
    STATUS      current
    DESCRIPTION
        "A connection could not be established between BroadWorks and Mobility Manager.
@severity:high
@subcomponent:mm"
    ::= { systemFaults 11740 }

  bwProvMobilityManagerError   NOTIFICATION-TYPE
    OBJECTS     { identifier, timeStamp, alarmName, systemName, severity, component, subcomponent, problemText, recommendedActionsText, npMessage }
    STATUS      current
    DESCRIPTION
        "Mobility Manager returned an error.
@severity:high
@subcomponent:mm"
    ::= { systemFaults 11741 }

  bwProvShInterfaceInitializationError   NOTIFICATION-TYPE
    OBJECTS     { identifier, timeStamp, alarmName, systemName, severity, component, subcomponent, problemText, recommendedActionsText }
    STATUS      obsolete
    DESCRIPTION
        "This fault is generated when the Condor Sh APN cannot be initialized.
@severity:high
@subcomponent:sh"
    ::= { systemFaults 11742 }

  bwProvCPEDeviceConfigurationNumFilesExceeded NOTIFICATION-TYPE
    OBJECTS     { identifier ,timeStamp ,alarmName ,systemName, severity, alarmState ,component ,subcomponent ,problemText ,recommendedActionsText, correlationParameter, npMaximumNbItems }
    STATUS      current
    DESCRIPTION
        "This alarm is generated when the Device Management system has exceeded the maximum number of files to be generated.
@severity:high
@subcomponent:filesystem"
    ::= { systemFaults 11743 }

  bwProvCallCenterConnectionFailure NOTIFICATION-TYPE
    OBJECTS     { identifier, timeStamp, alarmName, systemName, severity, alarmState, component, subcomponent, problemText, recommendedActionsText, correlationParameter, npRemoteAddress }
    STATUS      current
    DESCRIPTION
        "Connection between the Provisioning XS-TAS Server and the Execution Server for Call Center cannot be established.
@severity:high
@subcomponent:bcct
@correlationrules:This alarm is cleared by the Provisioning XS-TAS Server once connection is re-established or reconfigured."
    ::= { systemFaults 11744 }

    bwProvInterfaceInitializationError NOTIFICATION-TYPE
    OBJECTS     { identifier, timeStamp, alarmName, systemName, severity, component, subcomponent, problemText, recommendedActionsText, npExceptionMessage }
    STATUS      current
    DESCRIPTION
        "The Diameter Interface cannot be initialized. 
@severity:high
@subcomponent:diameter"
    ::= { systemFaults 11745 }
  
  bwProvPeerConnectionFailure NOTIFICATION-TYPE
    OBJECTS { identifier, timeStamp, alarmName, systemName, severity, component, subcomponent, problemText, recommendedActionsText, npServerName, npRemoteAddress, npRemotePort }
    STATUS      current
    DESCRIPTION
        "A failure occurred on a connection between the PS and a Diameter Peer (or the XS if operating in Relay mode).
@severity:high
@subcomponent:accounting"
    ::= { systemFaults 11746 }

  bwProvServiceLicenseCollectionFailure NOTIFICATION-TYPE
    OBJECTS { identifier, timeStamp, alarmName, systemName, severity, component, subcomponent, problemText, recommendedActionsText, npError }
    STATUS      current
    DESCRIPTION
        "The Service License Collection Script could not successfully complete.
@severity:low
@subcomponent:licensing"
    ::= { systemFaults 11747 }

  bwProvSubscriberProfileSyncIOError NOTIFICATION-TYPE
    OBJECTS { identifier, timeStamp, alarmName, systemName, severity, alarmState, component, subcomponent, problemText, recommendedActionsText, correlationParameter, npProfileDescription }
    STATUS      current
    DESCRIPTION
        "Several attempt to sync a profile to the SubscriberAgent failed due to a communication issue.
@severity:medium
@subcomponent:subscriberProfileSync"
    ::= { systemFaults 11748 }

  bwProvSubscriberProfileSyncDataError NOTIFICATION-TYPE
    OBJECTS { identifier, timeStamp, alarmName, systemName, severity, component, subcomponent, problemText, recommendedActionsText, npProfileDescription }
    STATUS      current
    DESCRIPTION
        "Several attempt to sync a profile to the SubscriberAgent failed.
@severity:high
@subcomponent:subscriberProfileSync"
    ::= { systemFaults 11749 }

  bwProvCCScheduledReportFailed  NOTIFICATION-TYPE
    OBJECTS     { identifier, timeStamp, alarmName, systemName, severity, alarmState, component, subcomponent, problemText, recommendedActionsText, correlationParameter, npNetAddress, npReportName, npUserId, npDateTime }
    STATUS      current
    DESCRIPTION
        "Failed to generate a call center scheduled report.
@severity:medium
@subcomponent:ccReporting"
    ::=  {  systemFaults 11750  }

  bwProvSCFAPIURLUnreachable  NOTIFICATION-TYPE
    OBJECTS     { identifier, timeStamp, alarmName, systemName, severity, alarmState, component, subcomponent, problemText, recommendedActionsText, correlationParameter, npRemoteAddress }
    STATUS      current
    DESCRIPTION
        "Connection to SCF API failed due to URL not being reachable.
@severity:high
@subcomponent:ps"
    ::=  {  systemFaults 11751  }

  bwProvCCScheduledReportGenerationFailure  NOTIFICATION-TYPE
    OBJECTS     { identifier, timeStamp, alarmName, systemName, severity, component, subcomponent, problemText, recommendedActionsText, npNetAddress, npReportName, npUserId, npDateTime }
    STATUS      current
    DESCRIPTION
        "Failed to generate a call center scheduled report.
@severity:medium
@subcomponent:ccReporting"
    ::=  {  systemFaults 11752  }

  bwProvCCScheduledReportConfigurationFailure  NOTIFICATION-TYPE
    OBJECTS     { identifier, timeStamp, alarmName, systemName, severity, component, subcomponent, problemText, recommendedActionsText }
    STATUS      current
    DESCRIPTION
        "Failed to start the call center scheduling task.
@severity:medium
@subcomponent:ccReporting"
    ::=  {  systemFaults 11753  }

  bwProvBroadCloudTransactionFailure  NOTIFICATION-TYPE
    OBJECTS     { identifier, timeStamp, alarmName, systemName, severity, component, subcomponent, problemText, recommendedActionsText, npBroadCloudRequest, npUserId, npBroadCloudUid, npBroadCloudService, npBroadCloudFailureReason }
    STATUS      current
    DESCRIPTION
        "Failed to execute provisioning request to the BroadCloud server.
@severity:medium
@subcomponent:broadCloud"
    ::=  {  systemFaults 11754  }

  bwProvBroadCloudOutOfSync  NOTIFICATION-TYPE
    OBJECTS     { identifier, timeStamp, alarmName, systemName, severity, component, subcomponent, problemText, recommendedActionsText, npBroadCloudRequest, npUserId, npBroadCloudUid, npBroadCloudService }
    STATUS      current
    DESCRIPTION
        "Failed execute the rollback request to BroadCloud
@severity:medium
@subcomponent:broadCloud"
    ::=  {  systemFaults 11755  }

  bwProvCallLogSchemaInstanceProvisioningOverload  NOTIFICATION-TYPE
    OBJECTS     { identifier, timeStamp, alarmName, systemName, severity, component, subcomponent, problemText, recommendedActionsText, npDBSchemaName }
    STATUS      current
    DESCRIPTION
        "This alarm indicates that the number of users currently provisioned to use the given Enhanced Call Logs DB schema instance is overloaded as defined per Broadworks standards.
Low:  Current number of users assigned to the instance is above 200K.
High:  Current number of users assigned to the instance is above 300K.
@severity:low, high
@subcomponent:callLogs"
-- @feature:117143
    ::=  {  systemFaults 11756  }

bwPMProvisioningServerXSTASOutOfMemory  NOTIFICATION-TYPE
     OBJECTS     { identifier, timeStamp, alarmName, systemName, severity, component, subcomponent, problemText, recommendedActionsText }
     STATUS      current
     DESCRIPTION
         "This notification provides the date and time when the Provisioning XS-TAS Server ran out of memory.
 @severity:high
 @subcomponent:processmonitor
 @correlationrules:bwPMProvisioningServerXSTASLaunched, bwPMProvisioningServerXSTASShutDown, bwPMProvisioningServerXSTASRestarted, bwPMProvisioningServerXSTASDeath, and bwPMProvisioningServerXSTASOutOfMemory can be correlated into a single alarm.  These events have to be considered as a transition of the state machine for the management of the ProvisioningServerXSTAS process."
-- @feature:165352
    ::=  {  systemFaults 11757  }

  bwProvDeviceManagementFtpBlockedWriteThresholdReached  NOTIFICATION-TYPE
    OBJECTS     { identifier, timeStamp, alarmName, systemName, severity, component, subcomponent, problemText, recommendedActionsText }
    STATUS      current
    DESCRIPTION
        "The threshold has been reached for the number of occurrences of a Device Management (DM) FTP blocked write due to a network issue. As a result, future occurrences will leave the DM thread stuck and no more DM events will be processed. A restartbw is required to clear this condition.
@severity:high
@subcomponent:processmonitor"
-- @feature:143489
    ::=  {  systemFaults 11758  }

END

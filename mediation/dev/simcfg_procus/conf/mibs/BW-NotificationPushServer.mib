--===============================================================
-- File Name : BW-NotificationPushServer.mib
-- Author    : BroadSoft Inc.
-- Copyright 2000-2015, BroadSoft, Inc. All rights reserved.
-- Proprietary Property of BroadSoft, Inc. Gaithersburg, MD.
--===============================================================
BW-NotificationPushServer DEFINITIONS ::= BEGIN
  IMPORTS
    MODULE-COMPLIANCE, OBJECT-GROUP
      FROM SNMPv2-CONF
    enterprises, MODULE-IDENTITY, OBJECT-TYPE, Unsigned32, Counter32, Gauge32, Integer32
      FROM SNMPv2-SMI
    DateAndTime, DisplayString, TimeStamp
      FROM SNMPv2-TC;

  broadsoft MODULE-IDENTITY
    LAST-UPDATED  "201506260000Z"
    ORGANIZATION  "BroadSoft, Inc."
    CONTACT-INFO  "BroadSoft, Inc.
9737 Washingtonian Blvd
Suite 350
Gaithersburg, MD 20878
Tel: +1-301-977-9440"
    DESCRIPTION
        "This is the MIB for the BroadWorks Notification Push Server application."
    REVISION    "201506260000Z"
                DESCRIPTION    "Creation."
    ::=  {  enterprises 6431  }

  broadworks OBJECT IDENTIFIER
    ::=  {  broadsoft 1  }

  notificationPushServer OBJECT IDENTIFIER
    ::=  {  broadworks 57  }

  notifications OBJECT IDENTIFIER
    ::=  {  notificationPushServer 1  }

-- MIB Compliance - Root
  bwNotificationPushServerMibConformance OBJECT IDENTIFIER
    ::=  {  notificationPushServer 1000  }

-- MIB Compliance - Groups
  bwNotificationPushServerMibGroups OBJECT IDENTIFIER
    ::=  {  bwNotificationPushServerMibConformance 1  }

-- MIB Compliance - Module
  bwNotificationPushServerMibCompliancy OBJECT IDENTIFIER
    ::=  {  bwNotificationPushServerMibConformance 2  }


-- ################### ...............................
-- broadsoft(6431).broadworks(1).notificationPushServer(57).notifications(1)
-- ################### ...............................

  bwNPSStatsTable OBJECT-TYPE
    SYNTAX      SEQUENCE OF BwNPSStatsTableEntry
    MAX-ACCESS  not-accessible
    STATUS      current
    DESCRIPTION
    "This table exposes the notifications statistics."
    ::=  {  notifications 1  }

  bwNPSStatsTableEntry OBJECT-TYPE
    SYNTAX      BwNPSStatsTableEntry
    MAX-ACCESS  not-accessible
    STATUS      current
    DESCRIPTION
      "This row contains information about a notifications statistic."
    INDEX       { bwNPSStatsIndex }
    ::=  {  bwNPSStatsTable 1  }

  BwNPSStatsTableEntry ::= SEQUENCE {
    bwNPSStatsIndex  Unsigned32,
    bwNPSNotificationsAppId  DisplayString,
    bwNPSNotificationsPlatform  DisplayString,
    bwNPSNotificationsSuccessful  Counter32,
    bwNPSNotificationsFailed  Counter32
  }

  bwNPSStatsIndex OBJECT-TYPE
    SYNTAX      Unsigned32
    MAX-ACCESS  read-only
    STATUS      current
    DESCRIPTION
      "This integer represents an index to a given statistic."
-- @feature:BW-7193
    ::=  {  bwNPSStatsTableEntry 1  }

  bwNPSNotificationsAppId OBJECT-TYPE
    SYNTAX      DisplayString
    MAX-ACCESS  read-only
    STATUS      current
    DESCRIPTION
      "This is the application ID of an application for which the NPS pushes notifications."
-- @feature:BW-7193
    ::=  {  bwNPSStatsTableEntry 2  }

  bwNPSNotificationsPlatform OBJECT-TYPE
    SYNTAX      DisplayString
    MAX-ACCESS  read-only
    STATUS      current
    DESCRIPTION
      "This is the OS of the mobile operating system, i.e., 'iOS'."
-- @feature:BW-7193
    ::=  {  bwNPSStatsTableEntry 3  }

  bwNPSNotificationsSuccessful OBJECT-TYPE
    SYNTAX      Counter32
    MAX-ACCESS  read-only
    STATUS      current
    DESCRIPTION
      "This counter tracks the total number of notifications successfully sent by the NPS."
-- @feature:BW-7193
    ::=  {  bwNPSStatsTableEntry 4  }

  bwNPSNotificationsFailed OBJECT-TYPE
    SYNTAX      Counter32
    MAX-ACCESS  read-only
    STATUS      current
    DESCRIPTION
      "This counter tracks the total number of failed notifications sent by the NPS."
-- @feature:BW-7193
    ::=  {  bwNPSStatsTableEntry 5  }

-- BroadWorks MIB Conformance Definition  ...........................................

  bwnotificationpushserverNotificationsGroup OBJECT-GROUP
    OBJECTS { bwNPSStatsIndex, bwNPSNotificationsAppId, bwNPSNotificationsPlatform, bwNPSNotificationsSuccessful, bwNPSNotificationsFailed }
    STATUS  current
    DESCRIPTION "This group defines the statistics for notificationPushServer notifications."
    ::=  {  bwNotificationPushServerMibGroups 1  }

  bwNotificationPushServerBasicCompliance MODULE-COMPLIANCE
    STATUS      current
    DESCRIPTION
        "BW-NotificationPushServer MIB compliance."
    MODULE
      MANDATORY-GROUPS { bwnotificationpushserverNotificationsGroup }
    ::=  {  bwNotificationPushServerMibCompliancy 1  }

END

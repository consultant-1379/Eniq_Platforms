ERICSSON-MPE-RESPONSE-SES-PM-MIB DEFINITIONS ::= BEGIN

IMPORTS
     MODULE-IDENTITY, OBJECT-TYPE, Counter32 
          FROM SNMPv2-SMI

     MODULE-COMPLIANCE, OBJECT-GROUP
          FROM SNMPv2-CONF

     applIndex
          FROM NETWORK-SERVICES-MIB

     ItuPerceivedSeverity
          FROM ITU-ALARM-TC

     mpeModules
          FROM ERICSSON-MPE-REGISTRY-MIB ;

mpeResponseSesPmModule MODULE-IDENTITY
   LAST-UPDATED    "201603231116Z"
   ORGANIZATION    "Ericsson AB"
   CONTACT-INFO    "        Ericsson AB

                    Postal: Ericsson AB
                            Kistagangen 26
                            SE - 164 80 Stockholm
                            Sweden

                       Tel: +46 8 7571500
                       Fax:

                    E-Mail: support@ericsson.com"
   DESCRIPTION     "Events and Counters for Ses get Response."
::= { mpeModules 34 }

responseSesPmObjects  OBJECT IDENTIFIER ::= { mpeResponseSesPmModule 1 }

sARCnt  OBJECT IDENTIFIER ::= { responseSesPmObjects 1 }

sARAlarm  OBJECT IDENTIFIER ::= { responseSesPmObjects 2 }

sERCnt  OBJECT IDENTIFIER ::= { responseSesPmObjects 3 }

sERAlarm  OBJECT IDENTIFIER ::= { responseSesPmObjects 4 }

sTcLocCnt  OBJECT IDENTIFIER ::= { responseSesPmObjects 5 }

sTcLocAlarm  OBJECT IDENTIFIER ::= { responseSesPmObjects 6 }

sNSCnt  OBJECT IDENTIFIER ::= { responseSesPmObjects 7 }

sNSAlarm  OBJECT IDENTIFIER ::= { responseSesPmObjects 8 }

sIAMCnt  OBJECT IDENTIFIER ::= { responseSesPmObjects 9 }

sIAMAlarm  OBJECT IDENTIFIER ::= { responseSesPmObjects 10 }

sPsCnt  OBJECT IDENTIFIER ::= { responseSesPmObjects 11 }

sPsAlarm  OBJECT IDENTIFIER ::= { responseSesPmObjects 12 }

sExARCnt  OBJECT IDENTIFIER ::= { responseSesPmObjects 13 }

sExIIARCnt  OBJECT IDENTIFIER ::= { responseSesPmObjects 14 }

sExERCnt  OBJECT IDENTIFIER ::= { responseSesPmObjects 15 }

sPTSCnt  OBJECT IDENTIFIER ::= { responseSesPmObjects 16 }

sPTSAlarm  OBJECT IDENTIFIER ::= { responseSesPmObjects 17 }

sENSCnt  OBJECT IDENTIFIER ::= { responseSesPmObjects 18 }

sENSAlarm  OBJECT IDENTIFIER ::= { responseSesPmObjects 19 }

sCPSCnt  OBJECT IDENTIFIER ::= { responseSesPmObjects 20 }

sCPSAlarm  OBJECT IDENTIFIER ::= { responseSesPmObjects 21 }

sESIMSCnt  OBJECT IDENTIFIER ::= { responseSesPmObjects 22 }

sESIMSAlarm  OBJECT IDENTIFIER ::= { responseSesPmObjects 23 }

sEMASCnt  OBJECT IDENTIFIER ::= { responseSesPmObjects 24 }

sEMASAlarm  OBJECT IDENTIFIER ::= { responseSesPmObjects 25 }

sQISCnt  OBJECT IDENTIFIER ::= { responseSesPmObjects 26 }

sQISAlarm  OBJECT IDENTIFIER ::= { responseSesPmObjects 27 }

sAMSCnt  OBJECT IDENTIFIER ::= { responseSesPmObjects 28 }

sAMSAlarm  OBJECT IDENTIFIER ::= { responseSesPmObjects 29 }

sRMSCnt  OBJECT IDENTIFIER ::= { responseSesPmObjects 30 }

sRMSAlarm  OBJECT IDENTIFIER ::= { responseSesPmObjects 31 }

sCANCELPSCnt  OBJECT IDENTIFIER ::= { responseSesPmObjects 32 }

sCANCELPSAlarm  OBJECT IDENTIFIER ::= { responseSesPmObjects 33 }

sROAMINGSCnt  OBJECT IDENTIFIER ::= { responseSesPmObjects 34 }

sROAMINGSAlarm  OBJECT IDENTIFIER ::= { responseSesPmObjects 35 }

sGS  OBJECT IDENTIFIER ::= { responseSesPmObjects 36 }

sGSAlarm  OBJECT IDENTIFIER ::= { responseSesPmObjects 37 }

responseSesPmConformance  OBJECT IDENTIFIER ::= { mpeResponseSesPmModule 3 }

responseSesPmGroups  OBJECT IDENTIFIER ::= { responseSesPmConformance 1 }

responseSesPmCompliances  OBJECT IDENTIFIER ::= { responseSesPmConformance 2 }

sARCntTable OBJECT-TYPE
   SYNTAX          SEQUENCE OF SARCntEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sARCnt 1 } 

sARCntEntry OBJECT-TYPE
   SYNTAX          SARCntEntry
   MAX-ACCESS      not-accessible
   STATUS          current
   DESCRIPTION     "Counters for SES get the response from AOG."
   INDEX { applIndex }
::= { sARCntTable  1 }

SARCntEntry  ::= SEQUENCE
{
   sARCntAIP0to1kms          Counter32,
   sARCntAIP1001to5kms       Counter32,
   sARCntAIP5001to10kms      Counter32,
   sARCntAIP10001toTimeout   Counter32,
   sARCntAIPOverTimeout      Counter32,
   sARCntAIA0to1kms          Counter32,
   sARCntAIA1001to5kms       Counter32,
   sARCntAIA5001to10kms      Counter32,
   sARCntAIA10001toTimeout   Counter32,
   sARCntAIAOverTimeout      Counter32,
   sARCntAV0to1kms           Counter32,
   sARCntAV1001to5kms        Counter32,
   sARCntAV5001to10kms       Counter32,
   sARCntAV10001toTimeout    Counter32,
   sARCntAVOverTimeout       Counter32,
   sARCntAVI0to1kms          Counter32,
   sARCntAVI1001to5kms       Counter32,
   sARCntAVI5001to10kms      Counter32,
   sARCntAVI10001toTimeout   Counter32,
   sARCntAVIOverTimeout      Counter32,
   sARCntAVNSV0to1kms        Counter32,
   sARCntAVNSV1001to5kms     Counter32,
   sARCntAVNSV5001to10kms    Counter32,
   sARCntAVNSV10001toTimeout Counter32,
   sARCntAVNSVOverTimeout    Counter32,
   sARCntAIAS0to1kms         Counter32,
   sARCntAIAS1001to5kms      Counter32,
   sARCntAIAS5001to10kms     Counter32,
   sARCntAIAS10001toTimeout  Counter32,
   sARCntAIASOverTimeout     Counter32,
   sARCntAA0to1kms           Counter32,
   sARCntAA1001to5kms        Counter32,
   sARCntAA5001to10kms       Counter32,
   sARCntAA10001toTimeout    Counter32,
   sARCntAAOverTimeout       Counter32,
   sARCntAS0to1kms           Counter32,
   sARCntAS1001to5kms        Counter32,
   sARCntAS5001to10kms       Counter32,
   sARCntAS10001toTimeout    Counter32,
   sARCntASOverTimeout       Counter32,
   sARCntPSAS0to1kms         Counter32,
   sARCntPSAS1001to5kms      Counter32,
   sARCntPSAS5001to10kms     Counter32,
   sARCntPSAS10001toTimeout  Counter32,
   sARCntPSASOverTimeout     Counter32,
   sARCntSC0to199            Counter32,
   sARCntSC200               Counter32,
   sARCntSC201to299          Counter32,
   sARCntSC300to399          Counter32,
   sARCntSC400to499          Counter32,
   sARCntSC500to599          Counter32
}

sARCntAIP0to1kms  OBJECT-TYPE
   SYNTAX          Counter32
   MAX-ACCESS      read-only
   STATUS          current
   DESCRIPTION     "AOG IMSI PARAMETERS SES gets response from AOG in 0 
                    to 1k ms.
                    The applUptime epoch of the application instance 
                    should be used as reference point for this counter."
::= { sARCntEntry 2 }

sARCntAIP1001to5kms  OBJECT-TYPE
   SYNTAX          Counter32
   MAX-ACCESS      read-only
   STATUS          current
   DESCRIPTION     "AOG IMSI PARAMETERS SES gets response from AOG in 
                    1001 to 5k ms.
                    The applUptime epoch of the application instance 
                    should be used as reference point for this counter."
::= { sARCntEntry 3 }

sARCntAIP5001to10kms  OBJECT-TYPE
   SYNTAX          Counter32
   MAX-ACCESS      read-only
   STATUS          current
   DESCRIPTION     "AOG IMSI PARAMETERS SES gets response from AOG in 
                    5001 to 10k ms.
                    The applUptime epoch of the application instance 
                    should be used as reference point for this counter."
::= { sARCntEntry 4 }

sARCntAIP10001toTimeout  OBJECT-TYPE
   SYNTAX          Counter32
   MAX-ACCESS      read-only
   STATUS          current
   DESCRIPTION     "AOG IMSI PARAMETERS SES gets response from AOG in 
                    10001 to Timeout.
                    The applUptime epoch of the application instance 
                    should be used as reference point for this counter."
::= { sARCntEntry 5 }

sARCntAIPOverTimeout  OBJECT-TYPE
   SYNTAX          Counter32
   MAX-ACCESS      read-only
   STATUS          current
   DESCRIPTION     "AOG IMSI PARAMETERS SES gets response from AOG over 
                    Timeout.
                    The applUptime epoch of the application instance 
                    should be used as reference point for this counter."
::= { sARCntEntry 6 }

sARCntAIA0to1kms  OBJECT-TYPE
   SYNTAX          Counter32
   MAX-ACCESS      read-only
   STATUS          current
   DESCRIPTION     "AOG IMSI AUTHORIZATION SES gets response from AOG in 
                    0 to 1k ms.
                    The applUptime epoch of the application instance 
                    should be used as reference point for this counter."
::= { sARCntEntry 7 }

sARCntAIA1001to5kms  OBJECT-TYPE
   SYNTAX          Counter32
   MAX-ACCESS      read-only
   STATUS          current
   DESCRIPTION     "AOG IMSI AUTHORIZATION SES gets response from AOG in 
                    1001 to 5k ms.
                    The applUptime epoch of the application instance 
                    should be used as reference point for this counter."
::= { sARCntEntry 8 }

sARCntAIA5001to10kms  OBJECT-TYPE
   SYNTAX          Counter32
   MAX-ACCESS      read-only
   STATUS          current
   DESCRIPTION     "AOG IMSI AUTHORIZATION SES gets response from AOG in 
                    5001 to 10k ms.
                    The applUptime epoch of the application instance 
                    should be used as reference point for this counter."
::= { sARCntEntry 9 }

sARCntAIA10001toTimeout  OBJECT-TYPE
   SYNTAX          Counter32
   MAX-ACCESS      read-only
   STATUS          current
   DESCRIPTION     "AOG IMSI AUTHORIZATION SES gets response from AOG in 
                    10001 to Timeout.
                    The applUptime epoch of the application instance 
                    should be used as reference point for this counter."
::= { sARCntEntry 10 }

sARCntAIAOverTimeout  OBJECT-TYPE
   SYNTAX          Counter32
   MAX-ACCESS      read-only
   STATUS          current
   DESCRIPTION     "AOG IMSI AUTHORIZATION SES gets response from AOG 
                    over Timeout.
                    The applUptime epoch of the application instance 
                    should be used as reference point for this counter."
::= { sARCntEntry 11 }

sARCntAV0to1kms  OBJECT-TYPE
   SYNTAX          Counter32
   MAX-ACCESS      read-only
   STATUS          current
   DESCRIPTION     "AOG IMSI SES gets response from AOG in 0 to 1k ms.
                    The applUptime epoch of the application instance 
                    should be used as reference point for this counter."
::= { sARCntEntry 12 }

sARCntAV1001to5kms  OBJECT-TYPE
   SYNTAX          Counter32
   MAX-ACCESS      read-only
   STATUS          current
   DESCRIPTION     "AOG IMSI SES gets response from AOG in 1001 to 5k ms.
                    The applUptime epoch of the application instance 
                    should be used as reference point for this counter."
::= { sARCntEntry 13 }

sARCntAV5001to10kms  OBJECT-TYPE
   SYNTAX          Counter32
   MAX-ACCESS      read-only
   STATUS          current
   DESCRIPTION     "AOG IMSI SES gets response from AOG in 5001 to 10k 
                    ms.
                    The applUptime epoch of the application instance 
                    should be used as reference point for this counter."
::= { sARCntEntry 14 }

sARCntAV10001toTimeout  OBJECT-TYPE
   SYNTAX          Counter32
   MAX-ACCESS      read-only
   STATUS          current
   DESCRIPTION     "AOG IMSI SES gets response from AOG in 10001 to 
                    Timeout.
                    The applUptime epoch of the application instance 
                    should be used as reference point for this counter."
::= { sARCntEntry 15 }

sARCntAVOverTimeout  OBJECT-TYPE
   SYNTAX          Counter32
   MAX-ACCESS      read-only
   STATUS          current
   DESCRIPTION     "AOG IMSI SES gets response from AOG over Timeout.
                    The applUptime epoch of the application instance 
                    should be used as reference point for this counter."
::= { sARCntEntry 16 }

sARCntAVI0to1kms  OBJECT-TYPE
   SYNTAX          Counter32
   MAX-ACCESS      read-only
   STATUS          current
   DESCRIPTION     "AOG VIMSI IMSI SES gets response from AOG in 0 to 1k 
                    ms.
                    The applUptime epoch of the application instance 
                    should be used as reference point for this counter."
::= { sARCntEntry 17 }

sARCntAVI1001to5kms  OBJECT-TYPE
   SYNTAX          Counter32
   MAX-ACCESS      read-only
   STATUS          current
   DESCRIPTION     "AOG VIMSI IMSI SES gets response from AOG in 1001 to 
                    5k ms.
                    The applUptime epoch of the application instance 
                    should be used as reference point for this counter."
::= { sARCntEntry 18 }

sARCntAVI5001to10kms  OBJECT-TYPE
   SYNTAX          Counter32
   MAX-ACCESS      read-only
   STATUS          current
   DESCRIPTION     "AOG VIMSI IMSI SES gets response from AOG in 5001 to 
                    10k ms.
                    The applUptime epoch of the application instance 
                    should be used as reference point for this counter."
::= { sARCntEntry 19 }

sARCntAVI10001toTimeout  OBJECT-TYPE
   SYNTAX          Counter32
   MAX-ACCESS      read-only
   STATUS          current
   DESCRIPTION     "AOG VIMSI IMSI SES gets response from AOG in 10001 to 
                    Timeout.
                    The applUptime epoch of the application instance 
                    should be used as reference point for this counter."
::= { sARCntEntry 20 }

sARCntAVIOverTimeout  OBJECT-TYPE
   SYNTAX          Counter32
   MAX-ACCESS      read-only
   STATUS          current
   DESCRIPTION     "AOG VIMSI IMSI SES gets response from AOG over 
                    Timeout.
                    The applUptime epoch of the application instance 
                    should be used as reference point for this counter."
::= { sARCntEntry 21 }

sARCntAVNSV0to1kms  OBJECT-TYPE
   SYNTAX          Counter32
   MAX-ACCESS      read-only
   STATUS          current
   DESCRIPTION     "AOG VIMSI NONSIMVIMSI SERVICES VOWIFI SES gets 
                    response from AOG in 0 to 1k ms.
                    The applUptime epoch of the application instance 
                    should be used as reference point for this counter."
::= { sARCntEntry 22 }

sARCntAVNSV1001to5kms  OBJECT-TYPE
   SYNTAX          Counter32
   MAX-ACCESS      read-only
   STATUS          current
   DESCRIPTION     "AOG VIMSI NONSIMVIMSI SERVICES VOWIFI SES gets 
                    response from AOG in 1001 to 5k ms.
                    The applUptime epoch of the application instance 
                    should be used as reference point for this counter."
::= { sARCntEntry 23 }

sARCntAVNSV5001to10kms  OBJECT-TYPE
   SYNTAX          Counter32
   MAX-ACCESS      read-only
   STATUS          current
   DESCRIPTION     "AOG VIMSI NONSIMVIMSI SERVICES VOWIFI SES gets 
                    response from AOG in 5001 to 10k ms.
                    The applUptime epoch of the application instance 
                    should be used as reference point for this counter."
::= { sARCntEntry 24 }

sARCntAVNSV10001toTimeout  OBJECT-TYPE
   SYNTAX          Counter32
   MAX-ACCESS      read-only
   STATUS          current
   DESCRIPTION     "AOG VIMSI NONSIMVIMSI SERVICES VOWIFI SES gets 
                    response from AOG in 10001 to Timeout.
                    The applUptime epoch of the application instance 
                    should be used as reference point for this counter."
::= { sARCntEntry 25 }

sARCntAVNSVOverTimeout  OBJECT-TYPE
   SYNTAX          Counter32
   MAX-ACCESS      read-only
   STATUS          current
   DESCRIPTION     "AOG VIMSI NONSIMVIMSI SERVICES VOWIFI SES gets 
                    response from AOG over Timeout.
                    The applUptime epoch of the application instance 
                    should be used as reference point for this counter."
::= { sARCntEntry 26 }

sARCntAIAS0to1kms  OBJECT-TYPE
   SYNTAX          Counter32
   MAX-ACCESS      read-only
   STATUS          current
   DESCRIPTION     "AOG IMSI AUTHORIZATION SERVICENAMES SES gets response 
                    from AOG in 0 to 1k ms.
                    The applUptime epoch of the application instance 
                    should be used as reference point for this counter."
::= { sARCntEntry 27 }

sARCntAIAS1001to5kms  OBJECT-TYPE
   SYNTAX          Counter32
   MAX-ACCESS      read-only
   STATUS          current
   DESCRIPTION     "AOG IMSI AUTHORIZATION SERVICENAMES SES gets response 
                    from AOG in 1001 to 5k ms.
                    The applUptime epoch of the application instance 
                    should be used as reference point for this counter."
::= { sARCntEntry 28 }

sARCntAIAS5001to10kms  OBJECT-TYPE
   SYNTAX          Counter32
   MAX-ACCESS      read-only
   STATUS          current
   DESCRIPTION     "AOG IMSI AUTHORIZATION SERVICENAMES SES gets response 
                    from AOG in 5001 to 10k ms.
                    The applUptime epoch of the application instance 
                    should be used as reference point for this counter."
::= { sARCntEntry 29 }

sARCntAIAS10001toTimeout  OBJECT-TYPE
   SYNTAX          Counter32
   MAX-ACCESS      read-only
   STATUS          current
   DESCRIPTION     "AOG IMSI AUTHORIZATION SERVICENAMES SES gets response 
                    from AOG in 10001 to 10k ms.
                    The applUptime epoch of the application instance 
                    should be used as reference point for this counter."
::= { sARCntEntry 30 }

sARCntAIASOverTimeout  OBJECT-TYPE
   SYNTAX          Counter32
   MAX-ACCESS      read-only
   STATUS          current
   DESCRIPTION     "AOG IMSI AUTHORIZATION SERVICENAMES SES gets response 
                    from AOG over Timeout.
                    The applUptime epoch of the application instance 
                    should be used as reference point for this counter."
::= { sARCntEntry 31 }

sARCntAA0to1kms  OBJECT-TYPE
   SYNTAX          Counter32
   MAX-ACCESS      read-only
   STATUS          current
   DESCRIPTION     "AOG APNSTOKEN SES gets response from AOG in 0 to 1k 
                    ms.
                    The applUptime epoch of the application instance 
                    should be used as reference point for this counter."
::= { sARCntEntry 32 }

sARCntAA1001to5kms  OBJECT-TYPE
   SYNTAX          Counter32
   MAX-ACCESS      read-only
   STATUS          current
   DESCRIPTION     "AOG APNSTOKEN SES gets response from AOG in 1001 to 
                    5k ms.
                    The applUptime epoch of the application instance 
                    should be used as reference point for this counter."
::= { sARCntEntry 33 }

sARCntAA5001to10kms  OBJECT-TYPE
   SYNTAX          Counter32
   MAX-ACCESS      read-only
   STATUS          current
   DESCRIPTION     "AOG APNSTOKEN SES gets response from AOG in 5001 to 
                    10k ms.
                    The applUptime epoch of the application instance 
                    should be used as reference point for this counter."
::= { sARCntEntry 34 }

sARCntAA10001toTimeout  OBJECT-TYPE
   SYNTAX          Counter32
   MAX-ACCESS      read-only
   STATUS          current
   DESCRIPTION     "AOG APNSTOKEN SES gets response from AOG in 10001 to 
                    Timeout.
                    The applUptime epoch of the application instance 
                    should be used as reference point for this counter."
::= { sARCntEntry 35 }

sARCntAAOverTimeout  OBJECT-TYPE
   SYNTAX          Counter32
   MAX-ACCESS      read-only
   STATUS          current
   DESCRIPTION     "AOG APNSTOKEN SES gets response from AOG over 
                    Timeout.
                    The applUptime epoch of the application instance 
                    should be used as reference point for this counter."
::= { sARCntEntry 36 }

sARCntAS0to1kms  OBJECT-TYPE
   SYNTAX          Counter32
   MAX-ACCESS      read-only
   STATUS          current
   DESCRIPTION     "AOG SIPUSER SES gets response from AOG in 0 to 1k ms.
                    The applUptime epoch of the application instance 
                    should be used as reference point for this counter."
::= { sARCntEntry 37 }

sARCntAS1001to5kms  OBJECT-TYPE
   SYNTAX          Counter32
   MAX-ACCESS      read-only
   STATUS          current
   DESCRIPTION     "AOG SIPUSER SES gets response from AOG in 1001 to 5k 
                    ms.
                    The applUptime epoch of the application instance 
                    should be used as reference point for this counter."
::= { sARCntEntry 38 }

sARCntAS5001to10kms  OBJECT-TYPE
   SYNTAX          Counter32
   MAX-ACCESS      read-only
   STATUS          current
   DESCRIPTION     "AOG SIPUSER SES gets response from AOG in 5001 to 10k 
                    ms.
                    The applUptime epoch of the application instance 
                    should be used as reference point for this counter."
::= { sARCntEntry 39 }

sARCntAS10001toTimeout  OBJECT-TYPE
   SYNTAX          Counter32
   MAX-ACCESS      read-only
   STATUS          current
   DESCRIPTION     "AOG SIPUSER SES gets response from AOG in 10001 to 
                    Timeout.
                    The applUptime epoch of the application instance 
                    should be used as reference point for this counter."
::= { sARCntEntry 40 }

sARCntASOverTimeout  OBJECT-TYPE
   SYNTAX          Counter32
   MAX-ACCESS      read-only
   STATUS          current
   DESCRIPTION     "AOG SIPUSER SES gets response from AOG over Timeout.
                    The applUptime epoch of the application instance 
                    should be used as reference point for this counter."
::= { sARCntEntry 41 }

sARCntPSAS0to1kms  OBJECT-TYPE
   SYNTAX          Counter32
   MAX-ACCESS      read-only
   STATUS          current
   DESCRIPTION     "AOG update psas status response from AOG in 0 to 1k 
                    ms.
                    The applUptime epoch of the application instance 
                    should be used as reference point for this counter."
::= { sARCntEntry 42 }

sARCntPSAS1001to5kms  OBJECT-TYPE
   SYNTAX          Counter32
   MAX-ACCESS      read-only
   STATUS          current
   DESCRIPTION     "AOG update psas status response from AOG in 1001 to 
                    5k ms.
                    The applUptime epoch of the application instance 
                    should be used as reference point for this counter."
::= { sARCntEntry 43 }

sARCntPSAS5001to10kms  OBJECT-TYPE
   SYNTAX          Counter32
   MAX-ACCESS      read-only
   STATUS          current
   DESCRIPTION     "AOG update psas status response from AOG in 5001 to 
                    10k ms.
                    The applUptime epoch of the application instance 
                    should be used as reference point for this counter."
::= { sARCntEntry 44 }

sARCntPSAS10001toTimeout  OBJECT-TYPE
   SYNTAX          Counter32
   MAX-ACCESS      read-only
   STATUS          current
   DESCRIPTION     "AOG update psas status response from AOG in 10001 to 
                    Timeout.
                    The applUptime epoch of the application instance 
                    should be used as reference point for this counter."
::= { sARCntEntry 45 }

sARCntPSASOverTimeout  OBJECT-TYPE
   SYNTAX          Counter32
   MAX-ACCESS      read-only
   STATUS          current
   DESCRIPTION     "AOG update psas status response from AOG over 
                    Timeout.
                    The applUptime epoch of the application instance 
                    should be used as reference point for this counter."
::= { sARCntEntry 46 }

sARCntSC0to199  OBJECT-TYPE
   SYNTAX          Counter32
   MAX-ACCESS      read-only
   STATUS          current
   DESCRIPTION     "Status code from AOG in 0 to 199.
                    The applUptime epoch of the application instance 
                    should be used as reference point for this counter."
::= { sARCntEntry 47 }

sARCntSC200  OBJECT-TYPE
   SYNTAX          Counter32
   MAX-ACCESS      read-only
   STATUS          current
   DESCRIPTION     "Status code from AOG in 200.
                    The applUptime epoch of the application instance 
                    should be used as reference point for this counter."
::= { sARCntEntry 48 }

sARCntSC201to299  OBJECT-TYPE
   SYNTAX          Counter32
   MAX-ACCESS      read-only
   STATUS          current
   DESCRIPTION     "Status code from AOG in 201 to 299.
                    The applUptime epoch of the application instance 
                    should be used as reference point for this counter."
::= { sARCntEntry 49 }

sARCntSC300to399  OBJECT-TYPE
   SYNTAX          Counter32
   MAX-ACCESS      read-only
   STATUS          current
   DESCRIPTION     "Status code from AOG in 300 to 399.
                    The applUptime epoch of the application instance 
                    should be used as reference point for this counter."
::= { sARCntEntry 50 }

sARCntSC400to499  OBJECT-TYPE
   SYNTAX          Counter32
   MAX-ACCESS      read-only
   STATUS          current
   DESCRIPTION     "Status code from AOG in 400 to 499.
                    The applUptime epoch of the application instance 
                    should be used as reference point for this counter."
::= { sARCntEntry 51 }

sARCntSC500to599  OBJECT-TYPE
   SYNTAX          Counter32
   MAX-ACCESS      read-only
   STATUS          current
   DESCRIPTION     "Status code from AOG in 500 to 599.
                    The applUptime epoch of the application instance 
                    should be used as reference point for this counter."
::= { sARCntEntry 52 }

sARAlarmTable OBJECT-TYPE
   SYNTAX          SEQUENCE OF SARAlarmEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sARAlarm 1 } 

sARAlarmEntry OBJECT-TYPE
   SYNTAX          SARAlarmEntry
   MAX-ACCESS      not-accessible
   STATUS          current
   DESCRIPTION     "Alarm for SES connects AOG failed."
   INDEX { applIndex }
::= { sARAlarmTable  1 }

SARAlarmEntry  ::= SEQUENCE
{
   sARAlarmFailAlarm ItuPerceivedSeverity
}

sARAlarmFailAlarm  OBJECT-TYPE
   SYNTAX          ItuPerceivedSeverity
   MAX-ACCESS      read-only
   STATUS          current
   DESCRIPTION     "Ses Connects Aog Failed or Aog Configuration Error."
::= { sARAlarmEntry 2 }

sERCntTable OBJECT-TYPE
   SYNTAX          SEQUENCE OF SERCntEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sERCnt 1 } 

sERCntEntry OBJECT-TYPE
   SYNTAX          SERCntEntry
   MAX-ACCESS      not-accessible
   STATUS          current
   DESCRIPTION     "Counters for SES get the response from ESAdapter."
   INDEX { applIndex }
::= { sERCntTable  1 }

SERCntEntry  ::= SEQUENCE
{
   sERCntAV0to1kms          Counter32,
   sERCntAV1001to5kms       Counter32,
   sERCntAV5001to10kms      Counter32,
   sERCntAV10001toTimeout   Counter32,
   sERCntAVOverTimeout      Counter32,
   sERCntET0to1kms          Counter32,
   sERCntET1001to5kms       Counter32,
   sERCntET5001to10kms      Counter32,
   sERCntET10001toTimeout   Counter32,
   sERCntETOverTimeout      Counter32,
   sERCntMI0to1kms          Counter32,
   sERCntMI1001to5kms       Counter32,
   sERCntMI5001to10kms      Counter32,
   sERCntMI10001toTimeout   Counter32,
   sERCntMIOverTimeout      Counter32,
   sERCntIP0to1kms          Counter32,
   sERCntIP1001to5kms       Counter32,
   sERCntIP5001to10kms      Counter32,
   sERCntIP10001toTimeout   Counter32,
   sERCntIPOverTimeout      Counter32,
   sERCntIM0to1kms          Counter32,
   sERCntIM1001to5kms       Counter32,
   sERCntIM5001to10kms      Counter32,
   sERCntIM10001toTimeout   Counter32,
   sERCntIMOverTimeout      Counter32,
   sERCntDI0to1kms          Counter32,
   sERCntDI1001to5kms       Counter32,
   sERCntDI5001to10kms      Counter32,
   sERCntDI10001toTimeout   Counter32,
   sERCntDIOverTimeout      Counter32,
   sERCntSU0to1kms          Counter32,
   sERCntSU1001to5kms       Counter32,
   sERCntSU5001to10kms      Counter32,
   sERCntSU10001toTimeout   Counter32,
   sERCntSUOverTimeout      Counter32,
   sERCntSC0to199           Counter32,
   sERCntSC200              Counter32,
   sERCntSC201to299         Counter32,
   sERCntSC300to399         Counter32,
   sERCntSC400to499         Counter32,
   sERCntSC500to599         Counter32,
   sERCntGCI0to1kms         Counter32,
   sERCntGCI1001to5kms      Counter32,
   sERCntGCI5001to10kms     Counter32,
   sERCntGCI10001toTimeout  Counter32,
   sERCntGCIOverTimeout     Counter32,
   sERCntGRM0to1kms         Counter32,
   sERCntGRM1001to5kms      Counter32,
   sERCntGRM5001to10kms     Counter32,
   sERCntGRM10001toTimeout  Counter32,
   sERCntGRMOverTimeout     Counter32,
   sERCntMO2I0to1kms        Counter32,
   sERCntMO2I1001to5kms     Counter32,
   sERCntMO2I5001to10kms    Counter32,
   sERCntMO2I10001toTimeout Counter32,
   sERCntMO2IOverTimeout    Counter32,
   sERCntCSP0to1kms         Counter32,
   sERCntCSP1001to5kms      Counter32,
   sERCntCSP5001to10kms     Counter32,
   sERCntCSP10001toTimeout  Counter32,
   sERCntCSPOverTimeout     Counter32
}

sERCntAV0to1kms  OBJECT-TYPE
   SYNTAX          Counter32
   MAX-ACCESS      read-only
   STATUS          current
   DESCRIPTION     "Authentication Vector SES gets response from 
                    ESAdapter in 0 to 1k ms.
                    The applUptime epoch of the application instance 
                    should be used as reference point for this counter."
::= { sERCntEntry 2 }

sERCntAV1001to5kms  OBJECT-TYPE
   SYNTAX          Counter32
   MAX-ACCESS      read-only
   STATUS          current
   DESCRIPTION     "Authentication Vector SES gets response from 
                    ESAdapter in 1001 to 5k ms.
                    The applUptime epoch of the application instance 
                    should be used as reference point for this counter."
::= { sERCntEntry 3 }

sERCntAV5001to10kms  OBJECT-TYPE
   SYNTAX          Counter32
   MAX-ACCESS      read-only
   STATUS          current
   DESCRIPTION     "Authentication Vector SES gets response from 
                    ESAdapter in 5001 to 10k ms.
                    The applUptime epoch of the application instance 
                    should be used as reference point for this counter."
::= { sERCntEntry 4 }

sERCntAV10001toTimeout  OBJECT-TYPE
   SYNTAX          Counter32
   MAX-ACCESS      read-only
   STATUS          current
   DESCRIPTION     "Authentication Vector SES gets response from 
                    ESAdapter in 10001 to Timeout.
                    The applUptime epoch of the application instance 
                    should be used as reference point for this counter."
::= { sERCntEntry 5 }

sERCntAVOverTimeout  OBJECT-TYPE
   SYNTAX          Counter32
   MAX-ACCESS      read-only
   STATUS          current
   DESCRIPTION     "Authentication Vector SES gets response from 
                    ESAdapter over Timeout.
                    The applUptime epoch of the application instance 
                    should be used as reference point for this counter."
::= { sERCntEntry 6 }

sERCntET0to1kms  OBJECT-TYPE
   SYNTAX          Counter32
   MAX-ACCESS      read-only
   STATUS          current
   DESCRIPTION     "Entitlements SES gets response from ESAdapter in 0 to 
                    1k ms.
                    The applUptime epoch of the application instance 
                    should be used as reference point for this counter."
::= { sERCntEntry 7 }

sERCntET1001to5kms  OBJECT-TYPE
   SYNTAX          Counter32
   MAX-ACCESS      read-only
   STATUS          current
   DESCRIPTION     "Entitlements SES gets response from ESAdapter in 1001 
                    to 5k ms.
                    The applUptime epoch of the application instance 
                    should be used as reference point for this counter."
::= { sERCntEntry 8 }

sERCntET5001to10kms  OBJECT-TYPE
   SYNTAX          Counter32
   MAX-ACCESS      read-only
   STATUS          current
   DESCRIPTION     "Entitlements SES gets response from ESAdapter in 5001 
                    to 10k ms.
                    The applUptime epoch of the application instance 
                    should be used as reference point for this counter."
::= { sERCntEntry 9 }

sERCntET10001toTimeout  OBJECT-TYPE
   SYNTAX          Counter32
   MAX-ACCESS      read-only
   STATUS          current
   DESCRIPTION     "Entitlements SES gets response from ESAdapter in 
                    10001 to Timeout.
                    The applUptime epoch of the application instance 
                    should be used as reference point for this counter."
::= { sERCntEntry 10 }

sERCntETOverTimeout  OBJECT-TYPE
   SYNTAX          Counter32
   MAX-ACCESS      read-only
   STATUS          current
   DESCRIPTION     "Entitlements SES gets response from ESAdapter over 
                    Timeout.
                    The applUptime epoch of the application instance 
                    should be used as reference point for this counter."
::= { sERCntEntry 11 }

sERCntMI0to1kms  OBJECT-TYPE
   SYNTAX          Counter32
   MAX-ACCESS      read-only
   STATUS          current
   DESCRIPTION     "MSISDN_IMSI SES gets response from ESAdapter in 0 to 
                    1k ms.
                    The applUptime epoch of the application instance 
                    should be used as reference point for this counter."
::= { sERCntEntry 12 }

sERCntMI1001to5kms  OBJECT-TYPE
   SYNTAX          Counter32
   MAX-ACCESS      read-only
   STATUS          current
   DESCRIPTION     "MSISDN_IMSI SES gets response from ESAdapter in 1001 
                    to 5k ms.
                    The applUptime epoch of the application instance 
                    should be used as reference point for this counter."
::= { sERCntEntry 13 }

sERCntMI5001to10kms  OBJECT-TYPE
   SYNTAX          Counter32
   MAX-ACCESS      read-only
   STATUS          current
   DESCRIPTION     "MSISDN_IMSI SES gets response from ESAdapter in 5001 
                    to 10k ms.
                    The applUptime epoch of the application instance 
                    should be used as reference point for this counter."
::= { sERCntEntry 14 }

sERCntMI10001toTimeout  OBJECT-TYPE
   SYNTAX          Counter32
   MAX-ACCESS      read-only
   STATUS          current
   DESCRIPTION     "MSISDN_IMSI SES gets response from ESAdapter in 10001 
                    to Timeout.
                    The applUptime epoch of the application instance 
                    should be used as reference point for this counter."
::= { sERCntEntry 15 }

sERCntMIOverTimeout  OBJECT-TYPE
   SYNTAX          Counter32
   MAX-ACCESS      read-only
   STATUS          current
   DESCRIPTION     "MSISDN_IMSI SES gets response from ESAdapter over 
                    Timeout.
                    The applUptime epoch of the application instance 
                    should be used as reference point for this counter."
::= { sERCntEntry 16 }

sERCntIP0to1kms  OBJECT-TYPE
   SYNTAX          Counter32
   MAX-ACCESS      read-only
   STATUS          current
   DESCRIPTION     "IP SES gets response from ESAdapter in 0 to 1k ms.
                    The applUptime epoch of the application instance 
                    should be used as reference point for this counter."
::= { sERCntEntry 17 }

sERCntIP1001to5kms  OBJECT-TYPE
   SYNTAX          Counter32
   MAX-ACCESS      read-only
   STATUS          current
   DESCRIPTION     "IP SES gets response from ESAdapter in 1001 to 5k ms.
                    The applUptime epoch of the application instance 
                    should be used as reference point for this counter."
::= { sERCntEntry 18 }

sERCntIP5001to10kms  OBJECT-TYPE
   SYNTAX          Counter32
   MAX-ACCESS      read-only
   STATUS          current
   DESCRIPTION     "IP SES gets response from ESAdapter in 5001 to 10k 
                    ms.
                    The applUptime epoch of the application instance 
                    should be used as reference point for this counter."
::= { sERCntEntry 19 }

sERCntIP10001toTimeout  OBJECT-TYPE
   SYNTAX          Counter32
   MAX-ACCESS      read-only
   STATUS          current
   DESCRIPTION     "IP SES gets response from ESAdapter in 10001 to 
                    Timeout.
                    The applUptime epoch of the application instance 
                    should be used as reference point for this counter."
::= { sERCntEntry 20 }

sERCntIPOverTimeout  OBJECT-TYPE
   SYNTAX          Counter32
   MAX-ACCESS      read-only
   STATUS          current
   DESCRIPTION     "IP SES gets response from ESAdapter over Timeout.
                    The applUptime epoch of the application instance 
                    should be used as reference point for this counter."
::= { sERCntEntry 21 }

sERCntIM0to1kms  OBJECT-TYPE
   SYNTAX          Counter32
   MAX-ACCESS      read-only
   STATUS          current
   DESCRIPTION     "IMSI_MSISDN SES gets response from ESAdapter in 0 to 
                    1k ms.
                    The applUptime epoch of the application instance 
                    should be used as reference point for this counter."
::= { sERCntEntry 22 }

sERCntIM1001to5kms  OBJECT-TYPE
   SYNTAX          Counter32
   MAX-ACCESS      read-only
   STATUS          current
   DESCRIPTION     "IMSI_MSISDN SES gets response from ESAdapter in 1001 
                    to 5k ms.
                    The applUptime epoch of the application instance 
                    should be used as reference point for this counter."
::= { sERCntEntry 23 }

sERCntIM5001to10kms  OBJECT-TYPE
   SYNTAX          Counter32
   MAX-ACCESS      read-only
   STATUS          current
   DESCRIPTION     "IMSI_MSISDN SES gets response from ESAdapter in 5001 
                    to 10k ms.
                    The applUptime epoch of the application instance 
                    should be used as reference point for this counter."
::= { sERCntEntry 24 }

sERCntIM10001toTimeout  OBJECT-TYPE
   SYNTAX          Counter32
   MAX-ACCESS      read-only
   STATUS          current
   DESCRIPTION     "IMSI_MSISDN SES gets response from ESAdapter in 10001 
                    to Timeout.
                    The applUptime epoch of the application instance 
                    should be used as reference point for this counter."
::= { sERCntEntry 25 }

sERCntIMOverTimeout  OBJECT-TYPE
   SYNTAX          Counter32
   MAX-ACCESS      read-only
   STATUS          current
   DESCRIPTION     "IMSI_MSISDN SES gets response from ESAdapter over 
                    Timeout.
                    The applUptime epoch of the application instance 
                    should be used as reference point for this counter."
::= { sERCntEntry 26 }

sERCntDI0to1kms  OBJECT-TYPE
   SYNTAX          Counter32
   MAX-ACCESS      read-only
   STATUS          current
   DESCRIPTION     "Device Capability IMSI SES gets response from 
                    ESAdapter in 0 to 1k ms.
                    The applUptime epoch of the application instance 
                    should be used as reference point for this counter."
::= { sERCntEntry 27 }

sERCntDI1001to5kms  OBJECT-TYPE
   SYNTAX          Counter32
   MAX-ACCESS      read-only
   STATUS          current
   DESCRIPTION     "Device Capability IMSI SES gets response from 
                    ESAdapter in 1001 to 5k ms.
                    The applUptime epoch of the application instance 
                    should be used as reference point for this counter."
::= { sERCntEntry 28 }

sERCntDI5001to10kms  OBJECT-TYPE
   SYNTAX          Counter32
   MAX-ACCESS      read-only
   STATUS          current
   DESCRIPTION     "Device Capability IMSI SES gets response from 
                    ESAdapter in 5001 to 10k ms.
                    The applUptime epoch of the application instance 
                    should be used as reference point for this counter."
::= { sERCntEntry 29 }

sERCntDI10001toTimeout  OBJECT-TYPE
   SYNTAX          Counter32
   MAX-ACCESS      read-only
   STATUS          current
   DESCRIPTION     "Device Capability IMSI SES gets response from 
                    ESAdapter in 10001 to Timeout.
                    The applUptime epoch of the application instance 
                    should be used as reference point for this counter."
::= { sERCntEntry 30 }

sERCntDIOverTimeout  OBJECT-TYPE
   SYNTAX          Counter32
   MAX-ACCESS      read-only
   STATUS          current
   DESCRIPTION     "Device Capability IMSI SES gets response from 
                    ESAdapter over Timeout.
                    The applUptime epoch of the application instance 
                    should be used as reference point for this counter."
::= { sERCntEntry 31 }

sERCntSU0to1kms  OBJECT-TYPE
   SYNTAX          Counter32
   MAX-ACCESS      read-only
   STATUS          current
   DESCRIPTION     "Subscription and Usage SES gets response from 
                    ESAdapter in 0 to 1k ms.
                    The applUptime epoch of the application instance 
                    should be used as reference point for this counter."
::= { sERCntEntry 32 }

sERCntSU1001to5kms  OBJECT-TYPE
   SYNTAX          Counter32
   MAX-ACCESS      read-only
   STATUS          current
   DESCRIPTION     "Subscription and Usage SES gets response from 
                    ESAdapter in 1001 to 5k ms.
                    The applUptime epoch of the application instance 
                    should be used as reference point for this counter."
::= { sERCntEntry 33 }

sERCntSU5001to10kms  OBJECT-TYPE
   SYNTAX          Counter32
   MAX-ACCESS      read-only
   STATUS          current
   DESCRIPTION     "Subscription and Usage SES gets response from 
                    ESAdapter in 5001 to 10k ms.
                    The applUptime epoch of the application instance 
                    should be used as reference point for this counter."
::= { sERCntEntry 34 }

sERCntSU10001toTimeout  OBJECT-TYPE
   SYNTAX          Counter32
   MAX-ACCESS      read-only
   STATUS          current
   DESCRIPTION     "Subscription and Usage SES gets response from 
                    ESAdapter in 10001 to Timeout.
                    The applUptime epoch of the application instance 
                    should be used as reference point for this counter."
::= { sERCntEntry 35 }

sERCntSUOverTimeout  OBJECT-TYPE
   SYNTAX          Counter32
   MAX-ACCESS      read-only
   STATUS          current
   DESCRIPTION     "Subscription and Usage SES gets response from 
                    ESAdapter over Timeout.
                    The applUptime epoch of the application instance 
                    should be used as reference point for this counter."
::= { sERCntEntry 36 }

sERCntSC0to199  OBJECT-TYPE
   SYNTAX          Counter32
   MAX-ACCESS      read-only
   STATUS          current
   DESCRIPTION     "Status code from ESAdapter in 0 to 199.
                    The applUptime epoch of the application instance 
                    should be used as reference point for this counter."
::= { sERCntEntry 37 }

sERCntSC200  OBJECT-TYPE
   SYNTAX          Counter32
   MAX-ACCESS      read-only
   STATUS          current
   DESCRIPTION     "Status code from ESAdapter in 200.
                    The applUptime epoch of the application instance 
                    should be used as reference point for this counter."
::= { sERCntEntry 38 }

sERCntSC201to299  OBJECT-TYPE
   SYNTAX          Counter32
   MAX-ACCESS      read-only
   STATUS          current
   DESCRIPTION     "Status code from ESAdapter in 201 to 299.
                    The applUptime epoch of the application instance 
                    should be used as reference point for this counter."
::= { sERCntEntry 39 }

sERCntSC300to399  OBJECT-TYPE
   SYNTAX          Counter32
   MAX-ACCESS      read-only
   STATUS          current
   DESCRIPTION     "Status code from ESAdapter in 300 to 399.
                    The applUptime epoch of the application instance 
                    should be used as reference point for this counter."
::= { sERCntEntry 40 }

sERCntSC400to499  OBJECT-TYPE
   SYNTAX          Counter32
   MAX-ACCESS      read-only
   STATUS          current
   DESCRIPTION     "Status code from ESAdapter in 400 to 499.
                    The applUptime epoch of the application instance 
                    should be used as reference point for this counter."
::= { sERCntEntry 41 }

sERCntSC500to599  OBJECT-TYPE
   SYNTAX          Counter32
   MAX-ACCESS      read-only
   STATUS          current
   DESCRIPTION     "Status code from ESAdapter in 500 to 599.
                    The applUptime epoch of the application instance 
                    should be used as reference point for this counter."
::= { sERCntEntry 42 }

sERCntGCI0to1kms  OBJECT-TYPE
   SYNTAX          Counter32
   MAX-ACCESS      read-only
   STATUS          current
   DESCRIPTION     "Get certificate info response from ESAdapter in 0 to 
                    1k ms.
                    The applUptime epoch of the application instance 
                    should be used as reference point for this counter."
::= { sERCntEntry 43 }

sERCntGCI1001to5kms  OBJECT-TYPE
   SYNTAX          Counter32
   MAX-ACCESS      read-only
   STATUS          current
   DESCRIPTION     "Get certificate info response from ESAdapter in 1001 
                    to 5k ms.
                    The applUptime epoch of the application instance 
                    should be used as reference point for this counter."
::= { sERCntEntry 44 }

sERCntGCI5001to10kms  OBJECT-TYPE
   SYNTAX          Counter32
   MAX-ACCESS      read-only
   STATUS          current
   DESCRIPTION     "Get certificate info response from ESAdapter in 5001 
                    to 10k ms.
                    The applUptime epoch of the application instance 
                    should be used as reference point for this counter."
::= { sERCntEntry 45 }

sERCntGCI10001toTimeout  OBJECT-TYPE
   SYNTAX          Counter32
   MAX-ACCESS      read-only
   STATUS          current
   DESCRIPTION     "Get certificate info response from ESAdapter in 10001 
                    to Timeout.
                    The applUptime epoch of the application instance 
                    should be used as reference point for this counter."
::= { sERCntEntry 46 }

sERCntGCIOverTimeout  OBJECT-TYPE
   SYNTAX          Counter32
   MAX-ACCESS      read-only
   STATUS          current
   DESCRIPTION     "Get certificate info response from ESAdapter over 
                    Timeout.
                    The applUptime epoch of the application instance 
                    should be used as reference point for this counter."
::= { sERCntEntry 47 }

sERCntGRM0to1kms  OBJECT-TYPE
   SYNTAX          Counter32
   MAX-ACCESS      read-only
   STATUS          current
   DESCRIPTION     "Get registered MSISDN response from ESAdapter in 0 to 
                    1k ms.
                    The applUptime epoch of the application instance 
                    should be used as reference point for this counter."
::= { sERCntEntry 48 }

sERCntGRM1001to5kms  OBJECT-TYPE
   SYNTAX          Counter32
   MAX-ACCESS      read-only
   STATUS          current
   DESCRIPTION     "Get registered MSISDN response from ESAdapter in 1001 
                    to 5k ms.
                    The applUptime epoch of the application instance 
                    should be used as reference point for this counter."
::= { sERCntEntry 49 }

sERCntGRM5001to10kms  OBJECT-TYPE
   SYNTAX          Counter32
   MAX-ACCESS      read-only
   STATUS          current
   DESCRIPTION     "Get registered MSISDN response from ESAdapter in 5001 
                    to 10k ms.
                    The applUptime epoch of the application instance 
                    should be used as reference point for this counter."
::= { sERCntEntry 50 }

sERCntGRM10001toTimeout  OBJECT-TYPE
   SYNTAX          Counter32
   MAX-ACCESS      read-only
   STATUS          current
   DESCRIPTION     "Get registered MSISDN response from ESAdapter in 
                    10001 to Timeout.
                    The applUptime epoch of the application instance 
                    should be used as reference point for this counter."
::= { sERCntEntry 51 }

sERCntGRMOverTimeout  OBJECT-TYPE
   SYNTAX          Counter32
   MAX-ACCESS      read-only
   STATUS          current
   DESCRIPTION     "Get registered MSISDN response from ESAdapter over 
                    Timeout.
                    The applUptime epoch of the application instance 
                    should be used as reference point for this counter."
::= { sERCntEntry 52 }

sERCntMO2I0to1kms  OBJECT-TYPE
   SYNTAX          Counter32
   MAX-ACCESS      read-only
   STATUS          current
   DESCRIPTION     "Get IMSI by MSISDN and ownerId response from 
                    ESAdapter in 0 to 1k ms.
                    The applUptime epoch of the application instance 
                    should be used as reference point for this counter."
::= { sERCntEntry 53 }

sERCntMO2I1001to5kms  OBJECT-TYPE
   SYNTAX          Counter32
   MAX-ACCESS      read-only
   STATUS          current
   DESCRIPTION     "Get IMSI by MSISDN and ownerId response from 
                    ESAdapter in 1001 to 5k ms.
                    The applUptime epoch of the application instance 
                    should be used as reference point for this counter."
::= { sERCntEntry 54 }

sERCntMO2I5001to10kms  OBJECT-TYPE
   SYNTAX          Counter32
   MAX-ACCESS      read-only
   STATUS          current
   DESCRIPTION     "Get IMSI by MSISDN and ownerId response from 
                    ESAdapter in 5001 to 10k ms.
                    The applUptime epoch of the application instance 
                    should be used as reference point for this counter."
::= { sERCntEntry 55 }

sERCntMO2I10001toTimeout  OBJECT-TYPE
   SYNTAX          Counter32
   MAX-ACCESS      read-only
   STATUS          current
   DESCRIPTION     "Get IMSI by MSISDN and ownerId response from 
                    ESAdapter in 10001 to Timeout.
                    The applUptime epoch of the application instance 
                    should be used as reference point for this counter."
::= { sERCntEntry 56 }

sERCntMO2IOverTimeout  OBJECT-TYPE
   SYNTAX          Counter32
   MAX-ACCESS      read-only
   STATUS          current
   DESCRIPTION     "Get IMSI by MSISDN and ownerId response from 
                    ESAdapter over Timeout.
                    The applUptime epoch of the application instance 
                    should be used as reference point for this counter."
::= { sERCntEntry 57 }

sERCntCSP0to1kms  OBJECT-TYPE
   SYNTAX          Counter32
   MAX-ACCESS      read-only
   STATUS          current
   DESCRIPTION     "Check service permission response from ESAdapter in 0 
                    to 1k ms.
                    The applUptime epoch of the application instance 
                    should be used as reference point for this counter."
::= { sERCntEntry 58 }

sERCntCSP1001to5kms  OBJECT-TYPE
   SYNTAX          Counter32
   MAX-ACCESS      read-only
   STATUS          current
   DESCRIPTION     "Check service permission response from ESAdapter in 
                    1001 to 5k ms.
                    The applUptime epoch of the application instance 
                    should be used as reference point for this counter."
::= { sERCntEntry 59 }

sERCntCSP5001to10kms  OBJECT-TYPE
   SYNTAX          Counter32
   MAX-ACCESS      read-only
   STATUS          current
   DESCRIPTION     "Check service permission response from ESAdapter in 
                    5001 to 10k ms.
                    The applUptime epoch of the application instance 
                    should be used as reference point for this counter."
::= { sERCntEntry 60 }

sERCntCSP10001toTimeout  OBJECT-TYPE
   SYNTAX          Counter32
   MAX-ACCESS      read-only
   STATUS          current
   DESCRIPTION     "Check service permission response from ESAdapter in 
                    10001 to Timeout.
                    The applUptime epoch of the application instance 
                    should be used as reference point for this counter."
::= { sERCntEntry 61 }

sERCntCSPOverTimeout  OBJECT-TYPE
   SYNTAX          Counter32
   MAX-ACCESS      read-only
   STATUS          current
   DESCRIPTION     "Check service permission response from ESAdapter over 
                    Timeout.
                    The applUptime epoch of the application instance 
                    should be used as reference point for this counter."
::= { sERCntEntry 62 }

sERAlarmTable OBJECT-TYPE
   SYNTAX          SEQUENCE OF SERAlarmEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sERAlarm 1 } 

sERAlarmEntry OBJECT-TYPE
   SYNTAX          SERAlarmEntry
   MAX-ACCESS      not-accessible
   STATUS          current
   DESCRIPTION     "Alarm for SES connects ESAdapter failed."
   INDEX { applIndex }
::= { sERAlarmTable  1 }

SERAlarmEntry  ::= SEQUENCE
{
   sERAlarmFailedAlarm ItuPerceivedSeverity
}

sERAlarmFailedAlarm  OBJECT-TYPE
   SYNTAX          ItuPerceivedSeverity
   MAX-ACCESS      read-only
   STATUS          current
   DESCRIPTION     "SES Connects ESAdapter Failed or ESAdapter 
                    Configuration Error."
::= { sERAlarmEntry 2 }

sTcLocCntTable OBJECT-TYPE
   SYNTAX          SEQUENCE OF STcLocCntEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sTcLocCnt 1 } 

sTcLocCntEntry OBJECT-TYPE
   SYNTAX          STcLocCntEntry
   MAX-ACCESS      not-accessible
   STATUS          current
   DESCRIPTION     "SES Term Condition and Location Info Response 
                    Counters"
   INDEX { applIndex }
::= { sTcLocCntTable  1 }

STcLocCntEntry  ::= SEQUENCE
{
   sTcLocCntTL0to1kms        Counter32,
   sTcLocCntTL1001to5kms     Counter32,
   sTcLocCntTL5001to10kms    Counter32,
   sTcLocCntTL10001toTimeout Counter32,
   sTcLocCntTLOverTimeout    Counter32,
   sTcLocCntSC0to199         Counter32,
   sTcLocCntSC200            Counter32,
   sTcLocCntSC201to299       Counter32,
   sTcLocCntSC300to399       Counter32,
   sTcLocCntSC400to499       Counter32,
   sTcLocCntSC500to599       Counter32
}

sTcLocCntTL0to1kms  OBJECT-TYPE
   SYNTAX          Counter32
   MAX-ACCESS      read-only
   STATUS          current
   DESCRIPTION     "Term Condition and Location Info SES gets response 
                    from server in 0 to 1k ms.
                    The applUptime epoch of the application instance 
                    should be used as reference point for this counter."
::= { sTcLocCntEntry 2 }

sTcLocCntTL1001to5kms  OBJECT-TYPE
   SYNTAX          Counter32
   MAX-ACCESS      read-only
   STATUS          current
   DESCRIPTION     "Term Condition and Location Info SES gets response 
                    from server in 1001 to 5k ms.
                    The applUptime epoch of the application instance 
                    should be used as reference point for this counter."
::= { sTcLocCntEntry 3 }

sTcLocCntTL5001to10kms  OBJECT-TYPE
   SYNTAX          Counter32
   MAX-ACCESS      read-only
   STATUS          current
   DESCRIPTION     "Term Condition and Location Info SES gets response 
                    from server in 5001 to 10k ms.
                    The applUptime epoch of the application instance 
                    should be used as reference point for this counter."
::= { sTcLocCntEntry 4 }

sTcLocCntTL10001toTimeout  OBJECT-TYPE
   SYNTAX          Counter32
   MAX-ACCESS      read-only
   STATUS          current
   DESCRIPTION     "Term Condition and Location Info SES gets response 
                    from server in 10001 to Timeout.
                    The applUptime epoch of the application instance 
                    should be used as reference point for this counter."
::= { sTcLocCntEntry 5 }

sTcLocCntTLOverTimeout  OBJECT-TYPE
   SYNTAX          Counter32
   MAX-ACCESS      read-only
   STATUS          current
   DESCRIPTION     "Term Condition and Location Info SES gets response 
                    from server over Timeout.
                    The applUptime epoch of the application instance 
                    should be used as reference point for this counter."
::= { sTcLocCntEntry 6 }

sTcLocCntSC0to199  OBJECT-TYPE
   SYNTAX          Counter32
   MAX-ACCESS      read-only
   STATUS          current
   DESCRIPTION     "Status code from term condition and location server 
                    in 0 to 199.
                    The applUptime epoch of the application instance 
                    should be used as reference point for this counter."
::= { sTcLocCntEntry 7 }

sTcLocCntSC200  OBJECT-TYPE
   SYNTAX          Counter32
   MAX-ACCESS      read-only
   STATUS          current
   DESCRIPTION     "Status code from term condition and location server 
                    in 200.
                    The applUptime epoch of the application instance 
                    should be used as reference point for this counter."
::= { sTcLocCntEntry 8 }

sTcLocCntSC201to299  OBJECT-TYPE
   SYNTAX          Counter32
   MAX-ACCESS      read-only
   STATUS          current
   DESCRIPTION     "Status code from term condition and location server 
                    in 201 to 299.
                    The applUptime epoch of the application instance 
                    should be used as reference point for this counter."
::= { sTcLocCntEntry 9 }

sTcLocCntSC300to399  OBJECT-TYPE
   SYNTAX          Counter32
   MAX-ACCESS      read-only
   STATUS          current
   DESCRIPTION     "Status code from term condition and location server 
                    in 300 to 399.
                    The applUptime epoch of the application instance 
                    should be used as reference point for this counter."
::= { sTcLocCntEntry 10 }

sTcLocCntSC400to499  OBJECT-TYPE
   SYNTAX          Counter32
   MAX-ACCESS      read-only
   STATUS          current
   DESCRIPTION     "Status code from term condition and location server 
                    in 400 to 499.
                    The applUptime epoch of the application instance 
                    should be used as reference point for this counter."
::= { sTcLocCntEntry 11 }

sTcLocCntSC500to599  OBJECT-TYPE
   SYNTAX          Counter32
   MAX-ACCESS      read-only
   STATUS          current
   DESCRIPTION     "Status code from term condition and location server 
                    in 500 to 599.
                    The applUptime epoch of the application instance 
                    should be used as reference point for this counter."
::= { sTcLocCntEntry 12 }

sTcLocAlarmTable OBJECT-TYPE
   SYNTAX          SEQUENCE OF STcLocAlarmEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sTcLocAlarm 1 } 

sTcLocAlarmEntry OBJECT-TYPE
   SYNTAX          STcLocAlarmEntry
   MAX-ACCESS      not-accessible
   STATUS          current
   DESCRIPTION     "Alarm for SES connects Term Condition and Location 
                    server failed."
   INDEX { applIndex }
::= { sTcLocAlarmTable  1 }

STcLocAlarmEntry  ::= SEQUENCE
{
   sTcLocAlarmFailedAlarm ItuPerceivedSeverity
}

sTcLocAlarmFailedAlarm  OBJECT-TYPE
   SYNTAX          ItuPerceivedSeverity
   MAX-ACCESS      read-only
   STATUS          current
   DESCRIPTION     "SES Connects Term Condition and Location server 
                    Failed or Term Condition and Location server Configuration 
                    Error."
::= { sTcLocAlarmEntry 2 }

sNSCntTable OBJECT-TYPE
   SYNTAX          SEQUENCE OF SNSCntEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sNSCnt 1 } 

sNSCntEntry OBJECT-TYPE
   SYNTAX          SNSCntEntry
   MAX-ACCESS      not-accessible
   STATUS          current
   DESCRIPTION     "Counters for SES get the response from Notification 
                    Server."
   INDEX { applIndex }
::= { sNSCntTable  1 }

SNSCntEntry  ::= SEQUENCE
{
   sNSCntNANSE0to1kms        Counter32,
   sNSCntNANSE1001to5kms     Counter32,
   sNSCntNANSE5001to10kms    Counter32,
   sNSCntNANSE10001toTimeout Counter32,
   sNSCntNANSEOverTimeout    Counter32,
   sNSCntNDNSE0to1kms        Counter32,
   sNSCntNDNSE1001to5kms     Counter32,
   sNSCntNDNSE5001to10kms    Counter32,
   sNSCntNDNSE10001toTimeout Counter32,
   sNSCntNDNSEOverTimeout    Counter32,
   sNSCntNDNSD0to1kms        Counter32,
   sNSCntNDNSD1001to5kms     Counter32,
   sNSCntNDNSD5001to10kms    Counter32,
   sNSCntNDNSD10001toTimeout Counter32,
   sNSCntNDNSDOverTimeout    Counter32,
   sNSCntSC0to200            Counter32,
   sNSCntSC200to201          Counter32,
   sNSCntSC201to204          Counter32,
   sNSCntSC204to304          Counter32,
   sNSCntSC304to400          Counter32,
   sNSCntSC400to404          Counter32
}

sNSCntNANSE0to1kms  OBJECT-TYPE
   SYNTAX          Counter32
   MAX-ACCESS      read-only
   STATUS          current
   DESCRIPTION     "NS ADD NOTIFICATION SUBSCRIPTION ENABLE SES gets 
                    response from Notification Server in 0 to 1k ms.
                    The applUptime epoch of the application instance 
                    should be used as reference point for this counter."
::= { sNSCntEntry 2 }

sNSCntNANSE1001to5kms  OBJECT-TYPE
   SYNTAX          Counter32
   MAX-ACCESS      read-only
   STATUS          current
   DESCRIPTION     "NS ADD NOTIFICATION SUBSCRIPTION ENABLE SES gets 
                    response from Notification Server in 1001 to 5k ms.
                    The applUptime epoch of the application instance 
                    should be used as reference point for this counter."
::= { sNSCntEntry 3 }

sNSCntNANSE5001to10kms  OBJECT-TYPE
   SYNTAX          Counter32
   MAX-ACCESS      read-only
   STATUS          current
   DESCRIPTION     "NS ADD NOTIFICATION SUBSCRIPTION ENABLE SES gets 
                    response from Notification Server in 5001 to 10k ms.
                    The applUptime epoch of the application instance 
                    should be used as reference point for this counter."
::= { sNSCntEntry 4 }

sNSCntNANSE10001toTimeout  OBJECT-TYPE
   SYNTAX          Counter32
   MAX-ACCESS      read-only
   STATUS          current
   DESCRIPTION     "NS ADD NOTIFICATION SUBSCRIPTION ENABLE SES gets 
                    response from Notification Server in 10001 to Timeout.
                    The applUptime epoch of the application instance 
                    should be used as reference point for this counter."
::= { sNSCntEntry 5 }

sNSCntNANSEOverTimeout  OBJECT-TYPE
   SYNTAX          Counter32
   MAX-ACCESS      read-only
   STATUS          current
   DESCRIPTION     "NS ADD NOTIFICATION SUBSCRIPTION ENABLE SES gets 
                    response from Notification Server over Timeout.
                    The applUptime epoch of the application instance 
                    should be used as reference point for this counter."
::= { sNSCntEntry 6 }

sNSCntNDNSE0to1kms  OBJECT-TYPE
   SYNTAX          Counter32
   MAX-ACCESS      read-only
   STATUS          current
   DESCRIPTION     "NS DELETE NOTIFICATION SUBSCRIPTION ENABLE SES gets 
                    response from Notification Server in 0 to 1k ms.
                    The applUptime epoch of the application instance 
                    should be used as reference point for this counter."
::= { sNSCntEntry 7 }

sNSCntNDNSE1001to5kms  OBJECT-TYPE
   SYNTAX          Counter32
   MAX-ACCESS      read-only
   STATUS          current
   DESCRIPTION     "NS DELETE NOTIFICATION SUBSCRIPTION ENABLE SES gets 
                    response from Notification Server in 1001 to 5k ms.
                    The applUptime epoch of the application instance 
                    should be used as reference point for this counter."
::= { sNSCntEntry 8 }

sNSCntNDNSE5001to10kms  OBJECT-TYPE
   SYNTAX          Counter32
   MAX-ACCESS      read-only
   STATUS          current
   DESCRIPTION     "NS DELETE NOTIFICATION SUBSCRIPTION ENABLE SES gets 
                    response from Notification Server in 5001 to 10k ms.
                    The applUptime epoch of the application instance 
                    should be used as reference point for this counter."
::= { sNSCntEntry 9 }

sNSCntNDNSE10001toTimeout  OBJECT-TYPE
   SYNTAX          Counter32
   MAX-ACCESS      read-only
   STATUS          current
   DESCRIPTION     "NS DELETE NOTIFICATION SUBSCRIPTION ENABLE SES gets 
                    response from Notification Server in 10001 to Timeout.
                    The applUptime epoch of the application instance 
                    should be used as reference point for this counter."
::= { sNSCntEntry 10 }

sNSCntNDNSEOverTimeout  OBJECT-TYPE
   SYNTAX          Counter32
   MAX-ACCESS      read-only
   STATUS          current
   DESCRIPTION     "NS DELETE NOTIFICATION SUBSCRIPTION ENABLE SES gets 
                    response from Notification Server over Timeout.
                    The applUptime epoch of the application instance 
                    should be used as reference point for this counter."
::= { sNSCntEntry 11 }

sNSCntNDNSD0to1kms  OBJECT-TYPE
   SYNTAX          Counter32
   MAX-ACCESS      read-only
   STATUS          current
   DESCRIPTION     "NS DELETE NOTIFICATION SUBSCRIPTION DISABLE SES gets 
                    response from Notification Server in 0 to 1k ms.
                    The applUptime epoch of the application instance 
                    should be used as reference point for this counter."
::= { sNSCntEntry 12 }

sNSCntNDNSD1001to5kms  OBJECT-TYPE
   SYNTAX          Counter32
   MAX-ACCESS      read-only
   STATUS          current
   DESCRIPTION     "NS DELETE NOTIFICATION SUBSCRIPTION DISABLE SES gets 
                    response from Notification Server in 1001 to 5k ms.
                    The applUptime epoch of the application instance 
                    should be used as reference point for this counter."
::= { sNSCntEntry 13 }

sNSCntNDNSD5001to10kms  OBJECT-TYPE
   SYNTAX          Counter32
   MAX-ACCESS      read-only
   STATUS          current
   DESCRIPTION     "NS DELETE NOTIFICATION SUBSCRIPTION DISABLE SES gets 
                    response from Notification Server in 5001 to 10k ms.
                    The applUptime epoch of the application instance 
                    should be used as reference point for this counter."
::= { sNSCntEntry 14 }

sNSCntNDNSD10001toTimeout  OBJECT-TYPE
   SYNTAX          Counter32
   MAX-ACCESS      read-only
   STATUS          current
   DESCRIPTION     "NS DELETE NOTIFICATION SUBSCRIPTION DISABLE SES gets 
                    response from Notification Server in 10001 to Timeout.
                    The applUptime epoch of the application instance 
                    should be used as reference point for this counter."
::= { sNSCntEntry 15 }

sNSCntNDNSDOverTimeout  OBJECT-TYPE
   SYNTAX          Counter32
   MAX-ACCESS      read-only
   STATUS          current
   DESCRIPTION     "NS DELETE NOTIFICATION SUBSCRIPTION DISABLE SES gets 
                    response from Notification Server over Timeout.
                    The applUptime epoch of the application instance 
                    should be used as reference point for this counter."
::= { sNSCntEntry 16 }

sNSCntSC0to200  OBJECT-TYPE
   SYNTAX          Counter32
   MAX-ACCESS      read-only
   STATUS          current
   DESCRIPTION     "Status code from Notification Server in 0 to 200.
                    The applUptime epoch of the application instance 
                    should be used as reference point for this counter."
::= { sNSCntEntry 17 }

sNSCntSC200to201  OBJECT-TYPE
   SYNTAX          Counter32
   MAX-ACCESS      read-only
   STATUS          current
   DESCRIPTION     "Status code from Notification Server in 200 to 201.
                    The applUptime epoch of the application instance 
                    should be used as reference point for this counter."
::= { sNSCntEntry 18 }

sNSCntSC201to204  OBJECT-TYPE
   SYNTAX          Counter32
   MAX-ACCESS      read-only
   STATUS          current
   DESCRIPTION     "Status code from Notification Server in 201 to 204.
                    The applUptime epoch of the application instance 
                    should be used as reference point for this counter."
::= { sNSCntEntry 19 }

sNSCntSC204to304  OBJECT-TYPE
   SYNTAX          Counter32
   MAX-ACCESS      read-only
   STATUS          current
   DESCRIPTION     "Status code from Notification Server in 204 to 304.
                    The applUptime epoch of the application instance 
                    should be used as reference point for this counter."
::= { sNSCntEntry 20 }

sNSCntSC304to400  OBJECT-TYPE
   SYNTAX          Counter32
   MAX-ACCESS      read-only
   STATUS          current
   DESCRIPTION     "Status code from Notification Server in 304 to 400.
                    The applUptime epoch of the application instance 
                    should be used as reference point for this counter."
::= { sNSCntEntry 21 }

sNSCntSC400to404  OBJECT-TYPE
   SYNTAX          Counter32
   MAX-ACCESS      read-only
   STATUS          current
   DESCRIPTION     "Status code from Notification Server in 400 to 404.
                    The applUptime epoch of the application instance 
                    should be used as reference point for this counter."
::= { sNSCntEntry 22 }

sNSAlarmTable OBJECT-TYPE
   SYNTAX          SEQUENCE OF SNSAlarmEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sNSAlarm 1 } 

sNSAlarmEntry OBJECT-TYPE
   SYNTAX          SNSAlarmEntry
   MAX-ACCESS      not-accessible
   STATUS          current
   DESCRIPTION     "Alarm for SES connects Notification Server failed."
   INDEX { applIndex }
::= { sNSAlarmTable  1 }

SNSAlarmEntry  ::= SEQUENCE
{
   sNSAlarmFailAlarm ItuPerceivedSeverity
}

sNSAlarmFailAlarm  OBJECT-TYPE
   SYNTAX          ItuPerceivedSeverity
   MAX-ACCESS      read-only
   STATUS          current
   DESCRIPTION     "Ses Connects Notification Server Failed or 
                    Notification Server Configuration Error."
::= { sNSAlarmEntry 2 }

sIAMCntTable OBJECT-TYPE
   SYNTAX          SEQUENCE OF SIAMCntEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sIAMCnt 1 } 

sIAMCntEntry OBJECT-TYPE
   SYNTAX          SIAMCntEntry
   MAX-ACCESS      not-accessible
   STATUS          current
   DESCRIPTION     "Counters for SES get the response from IAM."
   INDEX { applIndex }
::= { sIAMCntTable  1 }

SIAMCntEntry  ::= SEQUENCE
{
   sIAMCntIaAT0to1kms        Counter32,
   sIAMCntIaAT1001to5kms     Counter32,
   sIAMCntIaAT5001to10kms    Counter32,
   sIAMCntIaAT10001toTimeout Counter32,
   sIAMCntIaATOverTimeout    Counter32,
   sIAMCntVAT0to1kms         Counter32,
   sIAMCntVAT1001to5kms      Counter32,
   sIAMCntVAT5001to10kms     Counter32,
   sIAMCntVAT10001toTimeout  Counter32,
   sIAMCntVATOverTimeout     Counter32,
   sIAMCntQUP0to1kms         Counter32,
   sIAMCntQUP1001to5kms      Counter32,
   sIAMCntQUP5001to10kms     Counter32,
   sIAMCntQUP10001toTimeout  Counter32,
   sIAMCntQUPOverTimeout     Counter32,
   sIAMCntSC0to200           Counter32,
   sIAMCntSC200to400         Counter32,
   sIAMCntSC400to404         Counter32,
   sIAMCntSC404to422         Counter32,
   sIAMCntSC422to500         Counter32,
   sIAMCntSC500to503         Counter32
}

sIAMCntIaAT0to1kms  OBJECT-TYPE
   SYNTAX          Counter32
   MAX-ACCESS      read-only
   STATUS          current
   DESCRIPTION     "Issuing an Access Token response from IAM in 0 to 1k 
                    ms.
                    The applUptime epoch of the application instance 
                    should be used as reference point for this counter."
::= { sIAMCntEntry 2 }

sIAMCntIaAT1001to5kms  OBJECT-TYPE
   SYNTAX          Counter32
   MAX-ACCESS      read-only
   STATUS          current
   DESCRIPTION     "Issuing an Access Token response from IAM in 1001 to 
                    5k ms.
                    The applUptime epoch of the application instance 
                    should be used as reference point for this counter."
::= { sIAMCntEntry 3 }

sIAMCntIaAT5001to10kms  OBJECT-TYPE
   SYNTAX          Counter32
   MAX-ACCESS      read-only
   STATUS          current
   DESCRIPTION     "Issuing an Access Token response from IAM in 5001 to 
                    10k ms.
                    The applUptime epoch of the application instance 
                    should be used as reference point for this counter."
::= { sIAMCntEntry 4 }

sIAMCntIaAT10001toTimeout  OBJECT-TYPE
   SYNTAX          Counter32
   MAX-ACCESS      read-only
   STATUS          current
   DESCRIPTION     "Issuing an Access Token response from IAM in 10001 to 
                    Timeout.
                    The applUptime epoch of the application instance 
                    should be used as reference point for this counter."
::= { sIAMCntEntry 5 }

sIAMCntIaATOverTimeout  OBJECT-TYPE
   SYNTAX          Counter32
   MAX-ACCESS      read-only
   STATUS          current
   DESCRIPTION     "Issuing an Access Token response from IAM over 
                    Timeout.
                    The applUptime epoch of the application instance 
                    should be used as reference point for this counter."
::= { sIAMCntEntry 6 }

sIAMCntVAT0to1kms  OBJECT-TYPE
   SYNTAX          Counter32
   MAX-ACCESS      read-only
   STATUS          current
   DESCRIPTION     "Validate Access Token response from IAM in 0 to 1k 
                    ms.
                    The applUptime epoch of the application instance 
                    should be used as reference point for this counter."
::= { sIAMCntEntry 7 }

sIAMCntVAT1001to5kms  OBJECT-TYPE
   SYNTAX          Counter32
   MAX-ACCESS      read-only
   STATUS          current
   DESCRIPTION     "Validate Access Token response from IAM in 1001 to 5k 
                    ms.
                    The applUptime epoch of the application instance 
                    should be used as reference point for this counter."
::= { sIAMCntEntry 8 }

sIAMCntVAT5001to10kms  OBJECT-TYPE
   SYNTAX          Counter32
   MAX-ACCESS      read-only
   STATUS          current
   DESCRIPTION     "Validate Access Token response from IAM in 5001 to 
                    10k ms.
                    The applUptime epoch of the application instance 
                    should be used as reference point for this counter."
::= { sIAMCntEntry 9 }

sIAMCntVAT10001toTimeout  OBJECT-TYPE
   SYNTAX          Counter32
   MAX-ACCESS      read-only
   STATUS          current
   DESCRIPTION     "Validate Access Token response from IAM in 10001 to 
                    Timeout.
                    The applUptime epoch of the application instance 
                    should be used as reference point for this counter."
::= { sIAMCntEntry 10 }

sIAMCntVATOverTimeout  OBJECT-TYPE
   SYNTAX          Counter32
   MAX-ACCESS      read-only
   STATUS          current
   DESCRIPTION     "Validate Access Token response from IAM over Timeout.
                    The applUptime epoch of the application instance 
                    should be used as reference point for this counter."
::= { sIAMCntEntry 11 }

sIAMCntQUP0to1kms  OBJECT-TYPE
   SYNTAX          Counter32
   MAX-ACCESS      read-only
   STATUS          current
   DESCRIPTION     "Query User Profile response from IAM in 0 to 1k ms.
                    The applUptime epoch of the application instance 
                    should be used as reference point for this counter."
::= { sIAMCntEntry 12 }

sIAMCntQUP1001to5kms  OBJECT-TYPE
   SYNTAX          Counter32
   MAX-ACCESS      read-only
   STATUS          current
   DESCRIPTION     "Query User Profile response from IAM in 1001 to 5k 
                    ms.
                    The applUptime epoch of the application instance 
                    should be used as reference point for this counter."
::= { sIAMCntEntry 13 }

sIAMCntQUP5001to10kms  OBJECT-TYPE
   SYNTAX          Counter32
   MAX-ACCESS      read-only
   STATUS          current
   DESCRIPTION     "Query User Profile response from IAM in 5001 to 10k 
                    ms.
                    The applUptime epoch of the application instance 
                    should be used as reference point for this counter."
::= { sIAMCntEntry 14 }

sIAMCntQUP10001toTimeout  OBJECT-TYPE
   SYNTAX          Counter32
   MAX-ACCESS      read-only
   STATUS          current
   DESCRIPTION     "Query User Profile response from IAM in 10001 to 
                    Timeout.
                    The applUptime epoch of the application instance 
                    should be used as reference point for this counter."
::= { sIAMCntEntry 15 }

sIAMCntQUPOverTimeout  OBJECT-TYPE
   SYNTAX          Counter32
   MAX-ACCESS      read-only
   STATUS          current
   DESCRIPTION     "Query User Profile response from IAM over Timeout.
                    The applUptime epoch of the application instance 
                    should be used as reference point for this counter."
::= { sIAMCntEntry 16 }

sIAMCntSC0to200  OBJECT-TYPE
   SYNTAX          Counter32
   MAX-ACCESS      read-only
   STATUS          current
   DESCRIPTION     "Status code from IAM in 0 to 200.
                    The applUptime epoch of the application instance 
                    should be used as reference point for this counter."
::= { sIAMCntEntry 17 }

sIAMCntSC200to400  OBJECT-TYPE
   SYNTAX          Counter32
   MAX-ACCESS      read-only
   STATUS          current
   DESCRIPTION     "Status code from IAM in 200 to 400.
                    The applUptime epoch of the application instance 
                    should be used as reference point for this counter."
::= { sIAMCntEntry 18 }

sIAMCntSC400to404  OBJECT-TYPE
   SYNTAX          Counter32
   MAX-ACCESS      read-only
   STATUS          current
   DESCRIPTION     "Status code from IAM in 400 to 404.
                    The applUptime epoch of the application instance 
                    should be used as reference point for this counter."
::= { sIAMCntEntry 19 }

sIAMCntSC404to422  OBJECT-TYPE
   SYNTAX          Counter32
   MAX-ACCESS      read-only
   STATUS          current
   DESCRIPTION     "Status code from IAM in 404 to 422.
                    The applUptime epoch of the application instance 
                    should be used as reference point for this counter."
::= { sIAMCntEntry 20 }

sIAMCntSC422to500  OBJECT-TYPE
   SYNTAX          Counter32
   MAX-ACCESS      read-only
   STATUS          current
   DESCRIPTION     "Status code from IAM in 422 to 500.
                    The applUptime epoch of the application instance 
                    should be used as reference point for this counter."
::= { sIAMCntEntry 21 }

sIAMCntSC500to503  OBJECT-TYPE
   SYNTAX          Counter32
   MAX-ACCESS      read-only
   STATUS          current
   DESCRIPTION     "Status code from IAM in 500 to 503.
                    The applUptime epoch of the application instance 
                    should be used as reference point for this counter."
::= { sIAMCntEntry 22 }

sIAMAlarmTable OBJECT-TYPE
   SYNTAX          SEQUENCE OF SIAMAlarmEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sIAMAlarm 1 } 

sIAMAlarmEntry OBJECT-TYPE
   SYNTAX          SIAMAlarmEntry
   MAX-ACCESS      not-accessible
   STATUS          current
   DESCRIPTION     "Alarm for SES connects IAM failed."
   INDEX { applIndex }
::= { sIAMAlarmTable  1 }

SIAMAlarmEntry  ::= SEQUENCE
{
   sIAMAlarmFailAlarm ItuPerceivedSeverity
}

sIAMAlarmFailAlarm  OBJECT-TYPE
   SYNTAX          ItuPerceivedSeverity
   MAX-ACCESS      read-only
   STATUS          current
   DESCRIPTION     "SES Connects IAM Failed or IAM Configuration Error."
::= { sIAMAlarmEntry 2 }

sPsCntTable OBJECT-TYPE
   SYNTAX          SEQUENCE OF SPsCntEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sPsCnt 1 } 

sPsCntEntry OBJECT-TYPE
   SYNTAX          SPsCntEntry
   MAX-ACCESS      not-accessible
   STATUS          current
   DESCRIPTION     "Counters for SES get the response from Push Server."
   INDEX { applIndex }
::= { sPsCntTable  1 }

SPsCntEntry  ::= SEQUENCE
{
   sPsCntCEN0to1kms        Counter32,
   sPsCntCEN1001to5kms     Counter32,
   sPsCntCEN5001to10kms    Counter32,
   sPsCntCEN10001toTimeout Counter32,
   sPsCntCENOverTimeout    Counter32,
   sPsCntSTE0to1kms        Counter32,
   sPsCntSTE1001to5kms     Counter32,
   sPsCntSTE5001to10kms    Counter32,
   sPsCntSTE10001toTimeout Counter32,
   sPsCntSTEOverTimeout    Counter32,
   sPsCntSC0to199          Counter32,
   sPsCntSC200             Counter32,
   sPsCntSC201to299        Counter32,
   sPsCntSC300to399        Counter32,
   sPsCntSC400to499        Counter32,
   sPsCntSC500to599        Counter32
}

sPsCntCEN0to1kms  OBJECT-TYPE
   SYNTAX          Counter32
   MAX-ACCESS      read-only
   STATUS          current
   DESCRIPTION     "SES gets change event notification response from push 
                    server in 0 to 1k ms.
                    The applUptime epoch of the application instance 
                    should be used as reference point for this counter."
::= { sPsCntEntry 2 }

sPsCntCEN1001to5kms  OBJECT-TYPE
   SYNTAX          Counter32
   MAX-ACCESS      read-only
   STATUS          current
   DESCRIPTION     "SES gets change event notification response from push 
                    server in 1001 to 5k ms.
                    The applUptime epoch of the application instance 
                    should be used as reference point for this counter."
::= { sPsCntEntry 3 }

sPsCntCEN5001to10kms  OBJECT-TYPE
   SYNTAX          Counter32
   MAX-ACCESS      read-only
   STATUS          current
   DESCRIPTION     "SES gets change event notification response from push 
                    server in 5001 to 10k ms.
                    The applUptime epoch of the application instance 
                    should be used as reference point for this counter."
::= { sPsCntEntry 4 }

sPsCntCEN10001toTimeout  OBJECT-TYPE
   SYNTAX          Counter32
   MAX-ACCESS      read-only
   STATUS          current
   DESCRIPTION     "SES gets change event notification response from push 
                    server in 10001 to Timeout.
                    The applUptime epoch of the application instance 
                    should be used as reference point for this counter."
::= { sPsCntEntry 5 }

sPsCntCENOverTimeout  OBJECT-TYPE
   SYNTAX          Counter32
   MAX-ACCESS      read-only
   STATUS          current
   DESCRIPTION     "SES gets change event notification response from push 
                    server over Timeout.
                    The applUptime epoch of the application instance 
                    should be used as reference point for this counter."
::= { sPsCntEntry 6 }

sPsCntSTE0to1kms  OBJECT-TYPE
   SYNTAX          Counter32
   MAX-ACCESS      read-only
   STATUS          current
   DESCRIPTION     "SES gets service token expire response from push 
                    server in 0 to 1k ms.
                    The applUptime epoch of the application instance 
                    should be used as reference point for this counter."
::= { sPsCntEntry 7 }

sPsCntSTE1001to5kms  OBJECT-TYPE
   SYNTAX          Counter32
   MAX-ACCESS      read-only
   STATUS          current
   DESCRIPTION     "SES gets service token expire response from push 
                    server in 1001 to 5k ms.
                    The applUptime epoch of the application instance 
                    should be used as reference point for this counter."
::= { sPsCntEntry 8 }

sPsCntSTE5001to10kms  OBJECT-TYPE
   SYNTAX          Counter32
   MAX-ACCESS      read-only
   STATUS          current
   DESCRIPTION     "SSES gets service token expire response from push 
                    server in 5001 to 10k ms.
                    The applUptime epoch of the application instance 
                    should be used as reference point for this counter."
::= { sPsCntEntry 9 }

sPsCntSTE10001toTimeout  OBJECT-TYPE
   SYNTAX          Counter32
   MAX-ACCESS      read-only
   STATUS          current
   DESCRIPTION     "SES gets service token expire response from push 
                    server in 10001 to Timeout.
                    The applUptime epoch of the application instance 
                    should be used as reference point for this counter."
::= { sPsCntEntry 10 }

sPsCntSTEOverTimeout  OBJECT-TYPE
   SYNTAX          Counter32
   MAX-ACCESS      read-only
   STATUS          current
   DESCRIPTION     "SES gets service token expire response from push 
                    server over Timeout.
                    The applUptime epoch of the application instance 
                    should be used as reference point for this counter."
::= { sPsCntEntry 11 }

sPsCntSC0to199  OBJECT-TYPE
   SYNTAX          Counter32
   MAX-ACCESS      read-only
   STATUS          current
   DESCRIPTION     "Status code from push server in 0 to 199.
                    The applUptime epoch of the application instance 
                    should be used as reference point for this counter."
::= { sPsCntEntry 12 }

sPsCntSC200  OBJECT-TYPE
   SYNTAX          Counter32
   MAX-ACCESS      read-only
   STATUS          current
   DESCRIPTION     "Status code from push server in 200.
                    The applUptime epoch of the application instance 
                    should be used as reference point for this counter."
::= { sPsCntEntry 13 }

sPsCntSC201to299  OBJECT-TYPE
   SYNTAX          Counter32
   MAX-ACCESS      read-only
   STATUS          current
   DESCRIPTION     "Status code from push server in 201 to 299.
                    The applUptime epoch of the application instance 
                    should be used as reference point for this counter."
::= { sPsCntEntry 14 }

sPsCntSC300to399  OBJECT-TYPE
   SYNTAX          Counter32
   MAX-ACCESS      read-only
   STATUS          current
   DESCRIPTION     "Status code from push server in 300 to 399.
                    The applUptime epoch of the application instance 
                    should be used as reference point for this counter."
::= { sPsCntEntry 15 }

sPsCntSC400to499  OBJECT-TYPE
   SYNTAX          Counter32
   MAX-ACCESS      read-only
   STATUS          current
   DESCRIPTION     "Status code from push server in 400 to 499.
                    The applUptime epoch of the application instance 
                    should be used as reference point for this counter."
::= { sPsCntEntry 16 }

sPsCntSC500to599  OBJECT-TYPE
   SYNTAX          Counter32
   MAX-ACCESS      read-only
   STATUS          current
   DESCRIPTION     "Status code from push server in 500 to 599.
                    The applUptime epoch of the application instance 
                    should be used as reference point for this counter."
::= { sPsCntEntry 17 }

sPsAlarmTable OBJECT-TYPE
   SYNTAX          SEQUENCE OF SPsAlarmEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sPsAlarm 1 } 

sPsAlarmEntry OBJECT-TYPE
   SYNTAX          SPsAlarmEntry
   MAX-ACCESS      not-accessible
   STATUS          current
   DESCRIPTION     "Alarm for SES connects Push Server failed."
   INDEX { applIndex }
::= { sPsAlarmTable  1 }

SPsAlarmEntry  ::= SEQUENCE
{
   sPsAlarmFailAlarm ItuPerceivedSeverity
}

sPsAlarmFailAlarm  OBJECT-TYPE
   SYNTAX          ItuPerceivedSeverity
   MAX-ACCESS      read-only
   STATUS          current
   DESCRIPTION     "Ses Connects Push Server Failed or Push Server 
                    Configuration Error."
::= { sPsAlarmEntry 2 }

sExARCntTable OBJECT-TYPE
   SYNTAX          SEQUENCE OF SExARCntEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sExARCnt 1 } 

sExARCntEntry OBJECT-TYPE
   SYNTAX          SExARCntEntry
   MAX-ACCESS      not-accessible
   STATUS          current
   DESCRIPTION     "Extend Counters for SES get the response from AOG."
   INDEX { applIndex }
::= { sExARCntTable  1 }

SExARCntEntry  ::= SEQUENCE
{
   sExARCntCMDN0to1kms        Counter32,
   sExARCntCMDN1001to5kms     Counter32,
   sExARCntCMDN5001to10kms    Counter32,
   sExARCntCMDN10001toTimeout Counter32,
   sExARCntCMDNOverTimeout    Counter32,
   sExARCntQVSI0to1kms        Counter32,
   sExARCntQVSI1001to5kms     Counter32,
   sExARCntQVSI5001to10kms    Counter32,
   sExARCntQVSI10001toTimeout Counter32,
   sExARCntQVSIOverTimeout    Counter32,
   sExARCntUVSI0to1kms        Counter32,
   sExARCntUVSI1001to5kms     Counter32,
   sExARCntUVSI5001to10kms    Counter32,
   sExARCntUVSI10001toTimeout Counter32,
   sExARCntUVSIOverTimeout    Counter32,
   sExARCntBVSI0to1kms        Counter32,
   sExARCntBVSI1001to5kms     Counter32,
   sExARCntBVSI5001to10kms    Counter32,
   sExARCntBVSI10001toTimeout Counter32,
   sExARCntBVSIOverTimeout    Counter32,
   sExARCntDISI0to1kms        Counter32,
   sExARCntDISI1001to5kms     Counter32,
   sExARCntDISI5001to10kms    Counter32,
   sExARCntDISI10001toTimeout Counter32,
   sExARCntDISIOverTimeout    Counter32,
   sExARCntUISI0to1kms        Counter32,
   sExARCntUISI1001to5kms     Counter32,
   sExARCntUISI5001to10kms    Counter32,
   sExARCntUISI10001toTimeout Counter32,
   sExARCntUISIOverTimeout    Counter32,
   sExARCntCV0to1kms          Counter32,
   sExARCntCV1001to5kms       Counter32,
   sExARCntCV5001to10kms      Counter32,
   sExARCntCV10001toTimeout   Counter32,
   sExARCntCVOverTimeout      Counter32,
   sExARCntMC0to1kms          Counter32,
   sExARCntMC1001to5kms       Counter32,
   sExARCntMC5001to10kms      Counter32,
   sExARCntMC10001toTimeout   Counter32,
   sExARCntMCOverTimeout      Counter32,
   sExARCntAVS0to1kms         Counter32,
   sExARCntAVS1001to5kms      Counter32,
   sExARCntAVS5001to10kms     Counter32,
   sExARCntAVS10001toTimeout  Counter32,
   sExARCntAVSOverTimeout     Counter32,
   sExARCntRVS0to1kms         Counter32,
   sExARCntRVS1001to5kms      Counter32,
   sExARCntRVS5001to10kms     Counter32,
   sExARCntRVS10001toTimeout  Counter32,
   sExARCntRVSOverTimeout     Counter32,
   sExARCntRMVS0to1kms        Counter32,
   sExARCntRMVS1001to5kms     Counter32,
   sExARCntRMVS5001to10kms    Counter32,
   sExARCntRMVS10001toTimeout Counter32,
   sExARCntRMVSOverTimeout    Counter32,
   sExARCntQVS0to1kms         Counter32,
   sExARCntQVS1001to5kms      Counter32,
   sExARCntQVS5001to10kms     Counter32,
   sExARCntQVS10001toTimeout  Counter32,
   sExARCntQVSOverTimeout     Counter32,
   sExARCntAFNR0to1kms        Counter32,
   sExARCntAFNR1001to5kms     Counter32,
   sExARCntAFNR5001to10kms    Counter32,
   sExARCntAFNR10001toTimeout Counter32,
   sExARCntAFNROverTimeout    Counter32
}

sExARCntCMDN0to1kms  OBJECT-TYPE
   SYNTAX          Counter32
   MAX-ACCESS      read-only
   STATUS          current
   DESCRIPTION     "Change MSISDN Response from AOG in 0 to 1k ms.
                    The applUptime epoch of the application instance 
                    should be used as reference point for this counter."
::= { sExARCntEntry 2 }

sExARCntCMDN1001to5kms  OBJECT-TYPE
   SYNTAX          Counter32
   MAX-ACCESS      read-only
   STATUS          current
   DESCRIPTION     "Change MSISDN Response from AOG in 1001 to 5k ms.
                    The applUptime epoch of the application instance 
                    should be used as reference point for this counter."
::= { sExARCntEntry 3 }

sExARCntCMDN5001to10kms  OBJECT-TYPE
   SYNTAX          Counter32
   MAX-ACCESS      read-only
   STATUS          current
   DESCRIPTION     "Change MSISDN Response from AOG in 5001 to 10k ms.
                    The applUptime epoch of the application instance 
                    should be used as reference point for this counter."
::= { sExARCntEntry 4 }

sExARCntCMDN10001toTimeout  OBJECT-TYPE
   SYNTAX          Counter32
   MAX-ACCESS      read-only
   STATUS          current
   DESCRIPTION     "Change MSISDN Response from AOG in 10001 to Timeout.
                    The applUptime epoch of the application instance 
                    should be used as reference point for this counter."
::= { sExARCntEntry 5 }

sExARCntCMDNOverTimeout  OBJECT-TYPE
   SYNTAX          Counter32
   MAX-ACCESS      read-only
   STATUS          current
   DESCRIPTION     "Change MSISDN Response from AOG in over Timeout.
                    The applUptime epoch of the application instance 
                    should be used as reference point for this counter."
::= { sExARCntEntry 6 }

sExARCntQVSI0to1kms  OBJECT-TYPE
   SYNTAX          Counter32
   MAX-ACCESS      read-only
   STATUS          current
   DESCRIPTION     "Query vIMSI Response from AOG in 0 to 1k ms.
                    The applUptime epoch of the application instance 
                    should be used as reference point for this counter."
::= { sExARCntEntry 7 }

sExARCntQVSI1001to5kms  OBJECT-TYPE
   SYNTAX          Counter32
   MAX-ACCESS      read-only
   STATUS          current
   DESCRIPTION     "Query vIMSI Response from AOG in 1001 to 5k ms.
                    The applUptime epoch of the application instance 
                    should be used as reference point for this counter."
::= { sExARCntEntry 8 }

sExARCntQVSI5001to10kms  OBJECT-TYPE
   SYNTAX          Counter32
   MAX-ACCESS      read-only
   STATUS          current
   DESCRIPTION     "Query vIMSI Response from AOG in 5001 to 10k ms.
                    The applUptime epoch of the application instance 
                    should be used as reference point for this counter."
::= { sExARCntEntry 9 }

sExARCntQVSI10001toTimeout  OBJECT-TYPE
   SYNTAX          Counter32
   MAX-ACCESS      read-only
   STATUS          current
   DESCRIPTION     "Query vIMSI Response from AOG in 10001 to Timeout.
                    The applUptime epoch of the application instance 
                    should be used as reference point for this counter."
::= { sExARCntEntry 10 }

sExARCntQVSIOverTimeout  OBJECT-TYPE
   SYNTAX          Counter32
   MAX-ACCESS      read-only
   STATUS          current
   DESCRIPTION     "Query vIMSI Response from AOG over Timeout.
                    The applUptime epoch of the application instance 
                    should be used as reference point for this counter."
::= { sExARCntEntry 11 }

sExARCntUVSI0to1kms  OBJECT-TYPE
   SYNTAX          Counter32
   MAX-ACCESS      read-only
   STATUS          current
   DESCRIPTION     "Update vIMSI Response from AOG in 0 to 1k ms.
                    The applUptime epoch of the application instance 
                    should be used as reference point for this counter."
::= { sExARCntEntry 12 }

sExARCntUVSI1001to5kms  OBJECT-TYPE
   SYNTAX          Counter32
   MAX-ACCESS      read-only
   STATUS          current
   DESCRIPTION     "Update vIMSI Response from AOG in 1001 to 5k ms.
                    The applUptime epoch of the application instance 
                    should be used as reference point for this counter."
::= { sExARCntEntry 13 }

sExARCntUVSI5001to10kms  OBJECT-TYPE
   SYNTAX          Counter32
   MAX-ACCESS      read-only
   STATUS          current
   DESCRIPTION     "Update vIMSI Response from AOG in 5001 to 10k ms.
                    The applUptime epoch of the application instance 
                    should be used as reference point for this counter."
::= { sExARCntEntry 14 }

sExARCntUVSI10001toTimeout  OBJECT-TYPE
   SYNTAX          Counter32
   MAX-ACCESS      read-only
   STATUS          current
   DESCRIPTION     "Update vIMSI Response from AOG in 10001 to Timeout.
                    The applUptime epoch of the application instance 
                    should be used as reference point for this counter."
::= { sExARCntEntry 15 }

sExARCntUVSIOverTimeout  OBJECT-TYPE
   SYNTAX          Counter32
   MAX-ACCESS      read-only
   STATUS          current
   DESCRIPTION     "Update vIMSI Response from AOG over Timeout.
                    The applUptime epoch of the application instance 
                    should be used as reference point for this counter."
::= { sExARCntEntry 16 }

sExARCntBVSI0to1kms  OBJECT-TYPE
   SYNTAX          Counter32
   MAX-ACCESS      read-only
   STATUS          current
   DESCRIPTION     "Batch Update vIMSI Response from AOG in 0 to 1k ms.
                    The applUptime epoch of the application instance 
                    should be used as reference point for this counter."
::= { sExARCntEntry 17 }

sExARCntBVSI1001to5kms  OBJECT-TYPE
   SYNTAX          Counter32
   MAX-ACCESS      read-only
   STATUS          current
   DESCRIPTION     "Batch Update vIMSI Response from AOG in 1001 to 5k 
                    ms.
                    The applUptime epoch of the application instance 
                    should be used as reference point for this counter."
::= { sExARCntEntry 18 }

sExARCntBVSI5001to10kms  OBJECT-TYPE
   SYNTAX          Counter32
   MAX-ACCESS      read-only
   STATUS          current
   DESCRIPTION     "Batch Update vIMSI Response from AOG in 5001 to 10k 
                    ms.
                    The applUptime epoch of the application instance 
                    should be used as reference point for this counter."
::= { sExARCntEntry 19 }

sExARCntBVSI10001toTimeout  OBJECT-TYPE
   SYNTAX          Counter32
   MAX-ACCESS      read-only
   STATUS          current
   DESCRIPTION     "Batch Update vIMSI Response from AOG in 10001 to 
                    Timeout.
                    The applUptime epoch of the application instance 
                    should be used as reference point for this counter."
::= { sExARCntEntry 20 }

sExARCntBVSIOverTimeout  OBJECT-TYPE
   SYNTAX          Counter32
   MAX-ACCESS      read-only
   STATUS          current
   DESCRIPTION     "Batch Update vIMSI Response from AOG over Timeout.
                    The applUptime epoch of the application instance 
                    should be used as reference point for this counter."
::= { sExARCntEntry 21 }

sExARCntDISI0to1kms  OBJECT-TYPE
   SYNTAX          Counter32
   MAX-ACCESS      read-only
   STATUS          current
   DESCRIPTION     "Delete IMSI Response from AOG in 0 to 1k ms.
                    The applUptime epoch of the application instance 
                    should be used as reference point for this counter."
::= { sExARCntEntry 22 }

sExARCntDISI1001to5kms  OBJECT-TYPE
   SYNTAX          Counter32
   MAX-ACCESS      read-only
   STATUS          current
   DESCRIPTION     "Delete IMSI Response from AOG in 1001 to 5k ms.
                    The applUptime epoch of the application instance 
                    should be used as reference point for this counter."
::= { sExARCntEntry 23 }

sExARCntDISI5001to10kms  OBJECT-TYPE
   SYNTAX          Counter32
   MAX-ACCESS      read-only
   STATUS          current
   DESCRIPTION     "Delete IMSI Response from AOG in 5001 to 10k ms.
                    The applUptime epoch of the application instance 
                    should be used as reference point for this counter."
::= { sExARCntEntry 24 }

sExARCntDISI10001toTimeout  OBJECT-TYPE
   SYNTAX          Counter32
   MAX-ACCESS      read-only
   STATUS          current
   DESCRIPTION     "Delete IMSI Response from AOG in 10001 to Timeout.
                    The applUptime epoch of the application instance 
                    should be used as reference point for this counter."
::= { sExARCntEntry 25 }

sExARCntDISIOverTimeout  OBJECT-TYPE
   SYNTAX          Counter32
   MAX-ACCESS      read-only
   STATUS          current
   DESCRIPTION     "Delete IMSI Response from AOG over Timeout.
                    The applUptime epoch of the application instance 
                    should be used as reference point for this counter."
::= { sExARCntEntry 26 }

sExARCntUISI0to1kms  OBJECT-TYPE
   SYNTAX          Counter32
   MAX-ACCESS      read-only
   STATUS          current
   DESCRIPTION     "Update IMSI Response from AOG in 0 to 1k ms.
                    The applUptime epoch of the application instance 
                    should be used as reference point for this counter."
::= { sExARCntEntry 27 }

sExARCntUISI1001to5kms  OBJECT-TYPE
   SYNTAX          Counter32
   MAX-ACCESS      read-only
   STATUS          current
   DESCRIPTION     "Update IMSI Response from AOG in 1001 to 5k ms.
                    The applUptime epoch of the application instance 
                    should be used as reference point for this counter."
::= { sExARCntEntry 28 }

sExARCntUISI5001to10kms  OBJECT-TYPE
   SYNTAX          Counter32
   MAX-ACCESS      read-only
   STATUS          current
   DESCRIPTION     "Update IMSI Response from AOG in 5001 to 10k ms.
                    The applUptime epoch of the application instance 
                    should be used as reference point for this counter."
::= { sExARCntEntry 29 }

sExARCntUISI10001toTimeout  OBJECT-TYPE
   SYNTAX          Counter32
   MAX-ACCESS      read-only
   STATUS          current
   DESCRIPTION     "Update IMSI Response from AOG in 10001 to Timeout.
                    The applUptime epoch of the application instance 
                    should be used as reference point for this counter."
::= { sExARCntEntry 30 }

sExARCntUISIOverTimeout  OBJECT-TYPE
   SYNTAX          Counter32
   MAX-ACCESS      read-only
   STATUS          current
   DESCRIPTION     "Update IMSI Response from AOG over Timeout.
                    The applUptime epoch of the application instance 
                    should be used as reference point for this counter."
::= { sExARCntEntry 31 }

sExARCntCV0to1kms  OBJECT-TYPE
   SYNTAX          Counter32
   MAX-ACCESS      read-only
   STATUS          current
   DESCRIPTION     "Generic device create VIMSI response from AOG in 0 to 
                    1k ms.
                    The applUptime epoch of the application instance 
                    should be used as reference point for this counter."
::= { sExARCntEntry 32 }

sExARCntCV1001to5kms  OBJECT-TYPE
   SYNTAX          Counter32
   MAX-ACCESS      read-only
   STATUS          current
   DESCRIPTION     "Generic device create VIMSI response from AOG in 1001 
                    to 5k ms.
                    The applUptime epoch of the application instance 
                    should be used as reference point for this counter."
::= { sExARCntEntry 33 }

sExARCntCV5001to10kms  OBJECT-TYPE
   SYNTAX          Counter32
   MAX-ACCESS      read-only
   STATUS          current
   DESCRIPTION     "Generic device create VIMSI response from AOG in 5001 
                    to 10k ms.
                    The applUptime epoch of the application instance 
                    should be used as reference point for this counter."
::= { sExARCntEntry 34 }

sExARCntCV10001toTimeout  OBJECT-TYPE
   SYNTAX          Counter32
   MAX-ACCESS      read-only
   STATUS          current
   DESCRIPTION     "Generic device create VIMSI response from AOG in 
                    10001 to Timeout.
                    The applUptime epoch of the application instance 
                    should be used as reference point for this counter."
::= { sExARCntEntry 35 }

sExARCntCVOverTimeout  OBJECT-TYPE
   SYNTAX          Counter32
   MAX-ACCESS      read-only
   STATUS          current
   DESCRIPTION     "Generic device create VIMSI response from AOG over 
                    Timeout.
                    The applUptime epoch of the application instance 
                    should be used as reference point for this counter."
::= { sExARCntEntry 36 }

sExARCntMC0to1kms  OBJECT-TYPE
   SYNTAX          Counter32
   MAX-ACCESS      read-only
   STATUS          current
   DESCRIPTION     "Generic device manage connectivity response from AOG 
                    in 0 to 1k ms.
                    The applUptime epoch of the application instance 
                    should be used as reference point for this counter."
::= { sExARCntEntry 37 }

sExARCntMC1001to5kms  OBJECT-TYPE
   SYNTAX          Counter32
   MAX-ACCESS      read-only
   STATUS          current
   DESCRIPTION     "Generic device manage connectivity response from AOG 
                    in 1001 to 5k ms.
                    The applUptime epoch of the application instance 
                    should be used as reference point for this counter."
::= { sExARCntEntry 38 }

sExARCntMC5001to10kms  OBJECT-TYPE
   SYNTAX          Counter32
   MAX-ACCESS      read-only
   STATUS          current
   DESCRIPTION     "Generic device manage connectivity response from AOG 
                    in 5001 to 10k ms.
                    The applUptime epoch of the application instance 
                    should be used as reference point for this counter."
::= { sExARCntEntry 39 }

sExARCntMC10001toTimeout  OBJECT-TYPE
   SYNTAX          Counter32
   MAX-ACCESS      read-only
   STATUS          current
   DESCRIPTION     "Generic device manage connectivity response from AOG 
                    in 10001 to Timeout.
                    The applUptime epoch of the application instance 
                    should be used as reference point for this counter."
::= { sExARCntEntry 40 }

sExARCntMCOverTimeout  OBJECT-TYPE
   SYNTAX          Counter32
   MAX-ACCESS      read-only
   STATUS          current
   DESCRIPTION     "Generic device manage connectivity response from AOG 
                    over Timeout.
                    The applUptime epoch of the application instance 
                    should be used as reference point for this counter."
::= { sExARCntEntry 41 }

sExARCntAVS0to1kms  OBJECT-TYPE
   SYNTAX          Counter32
   MAX-ACCESS      read-only
   STATUS          current
   DESCRIPTION     "Generic device activate VoWiFi service response from 
                    AOG in 0 to 1k ms.
                    The applUptime epoch of the application instance 
                    should be used as reference point for this counter."
::= { sExARCntEntry 42 }

sExARCntAVS1001to5kms  OBJECT-TYPE
   SYNTAX          Counter32
   MAX-ACCESS      read-only
   STATUS          current
   DESCRIPTION     "Generic device activate VoWiFi service response from 
                    AOG in 1001 to 5k ms.
                    The applUptime epoch of the application instance 
                    should be used as reference point for this counter."
::= { sExARCntEntry 43 }

sExARCntAVS5001to10kms  OBJECT-TYPE
   SYNTAX          Counter32
   MAX-ACCESS      read-only
   STATUS          current
   DESCRIPTION     "Generic device activate VoWiFi service response from 
                    AOG in 5001 to 10k ms.
                    The applUptime epoch of the application instance 
                    should be used as reference point for this counter."
::= { sExARCntEntry 44 }

sExARCntAVS10001toTimeout  OBJECT-TYPE
   SYNTAX          Counter32
   MAX-ACCESS      read-only
   STATUS          current
   DESCRIPTION     "Generic device activate VoWiFi service response from 
                    AOG in 10001 to Timeout.
                    The applUptime epoch of the application instance 
                    should be used as reference point for this counter."
::= { sExARCntEntry 45 }

sExARCntAVSOverTimeout  OBJECT-TYPE
   SYNTAX          Counter32
   MAX-ACCESS      read-only
   STATUS          current
   DESCRIPTION     "Generic device activate VoWiFi service response from 
                    AOG over Timeout.
                    The applUptime epoch of the application instance 
                    should be used as reference point for this counter."
::= { sExARCntEntry 46 }

sExARCntRVS0to1kms  OBJECT-TYPE
   SYNTAX          Counter32
   MAX-ACCESS      read-only
   STATUS          current
   DESCRIPTION     "Generic device renew VoWiFi service response from AOG 
                    in 0 to 1k ms.
                    The applUptime epoch of the application instance 
                    should be used as reference point for this counter."
::= { sExARCntEntry 47 }

sExARCntRVS1001to5kms  OBJECT-TYPE
   SYNTAX          Counter32
   MAX-ACCESS      read-only
   STATUS          current
   DESCRIPTION     "Generic device renew VoWiFi service response from AOG 
                    in 1001 to 5k ms.
                    The applUptime epoch of the application instance 
                    should be used as reference point for this counter."
::= { sExARCntEntry 48 }

sExARCntRVS5001to10kms  OBJECT-TYPE
   SYNTAX          Counter32
   MAX-ACCESS      read-only
   STATUS          current
   DESCRIPTION     "Generic device renew VoWiFi service response from AOG 
                    in 5001 to 10k ms.
                    The applUptime epoch of the application instance 
                    should be used as reference point for this counter."
::= { sExARCntEntry 49 }

sExARCntRVS10001toTimeout  OBJECT-TYPE
   SYNTAX          Counter32
   MAX-ACCESS      read-only
   STATUS          current
   DESCRIPTION     "Generic device renew VoWiFi service response from AOG 
                    in 10001 to Timeout.
                    The applUptime epoch of the application instance 
                    should be used as reference point for this counter."
::= { sExARCntEntry 50 }

sExARCntRVSOverTimeout  OBJECT-TYPE
   SYNTAX          Counter32
   MAX-ACCESS      read-only
   STATUS          current
   DESCRIPTION     "Generic device renew VoWiFi service response from AOG 
                    over Timeout.
                    The applUptime epoch of the application instance 
                    should be used as reference point for this counter."
::= { sExARCntEntry 51 }

sExARCntRMVS0to1kms  OBJECT-TYPE
   SYNTAX          Counter32
   MAX-ACCESS      read-only
   STATUS          current
   DESCRIPTION     "Generic device remove VoWiFi service response from 
                    AOG in 0 to 1k ms.
                    The applUptime epoch of the application instance 
                    should be used as reference point for this counter."
::= { sExARCntEntry 52 }

sExARCntRMVS1001to5kms  OBJECT-TYPE
   SYNTAX          Counter32
   MAX-ACCESS      read-only
   STATUS          current
   DESCRIPTION     "Generic device remove VoWiFi service response from 
                    AOG in 1001 to 5k ms.
                    The applUptime epoch of the application instance 
                    should be used as reference point for this counter."
::= { sExARCntEntry 53 }

sExARCntRMVS5001to10kms  OBJECT-TYPE
   SYNTAX          Counter32
   MAX-ACCESS      read-only
   STATUS          current
   DESCRIPTION     "Generic device remove VoWiFi service response from 
                    AOG in 5001 to 10k ms.
                    The applUptime epoch of the application instance 
                    should be used as reference point for this counter."
::= { sExARCntEntry 54 }

sExARCntRMVS10001toTimeout  OBJECT-TYPE
   SYNTAX          Counter32
   MAX-ACCESS      read-only
   STATUS          current
   DESCRIPTION     "Generic device remove VoWiFi service response from 
                    AOG in 10001 to Timeout.
                    The applUptime epoch of the application instance 
                    should be used as reference point for this counter."
::= { sExARCntEntry 55 }

sExARCntRMVSOverTimeout  OBJECT-TYPE
   SYNTAX          Counter32
   MAX-ACCESS      read-only
   STATUS          current
   DESCRIPTION     "Generic device remove VoWiFi service response from 
                    AOG over Timeout.
                    The applUptime epoch of the application instance 
                    should be used as reference point for this counter."
::= { sExARCntEntry 56 }

sExARCntQVS0to1kms  OBJECT-TYPE
   SYNTAX          Counter32
   MAX-ACCESS      read-only
   STATUS          current
   DESCRIPTION     "Generic device query VoWiFi profile state response 
                    from AOG in 0 to 1k ms.
                    The applUptime epoch of the application instance 
                    should be used as reference point for this counter."
::= { sExARCntEntry 57 }

sExARCntQVS1001to5kms  OBJECT-TYPE
   SYNTAX          Counter32
   MAX-ACCESS      read-only
   STATUS          current
   DESCRIPTION     "Generic device query VoWiFi profile state response 
                    from AOG in 1001 to 5k ms.
                    The applUptime epoch of the application instance 
                    should be used as reference point for this counter."
::= { sExARCntEntry 58 }

sExARCntQVS5001to10kms  OBJECT-TYPE
   SYNTAX          Counter32
   MAX-ACCESS      read-only
   STATUS          current
   DESCRIPTION     "Generic device query VoWiFi profile state response 
                    from AOG in 5001 to 10k ms.
                    The applUptime epoch of the application instance 
                    should be used as reference point for this counter."
::= { sExARCntEntry 59 }

sExARCntQVS10001toTimeout  OBJECT-TYPE
   SYNTAX          Counter32
   MAX-ACCESS      read-only
   STATUS          current
   DESCRIPTION     "Generic device query VoWiFi profile state response 
                    from AOG in 10001 to Timeout.
                    The applUptime epoch of the application instance 
                    should be used as reference point for this counter."
::= { sExARCntEntry 60 }

sExARCntQVSOverTimeout  OBJECT-TYPE
   SYNTAX          Counter32
   MAX-ACCESS      read-only
   STATUS          current
   DESCRIPTION     "Generic device query VoWiFi profile state response 
                    from AOG over Timeout.
                    The applUptime epoch of the application instance 
                    should be used as reference point for this counter."
::= { sExARCntEntry 61 }

sExARCntAFNR0to1kms  OBJECT-TYPE
   SYNTAX          Counter32
   MAX-ACCESS      read-only
   STATUS          current
   DESCRIPTION     "Generic device assign friendly name response from AOG 
                    in 0 to 1k ms.
                    The applUptime epoch of the application instance 
                    should be used as reference point for this counter."
::= { sExARCntEntry 62 }

sExARCntAFNR1001to5kms  OBJECT-TYPE
   SYNTAX          Counter32
   MAX-ACCESS      read-only
   STATUS          current
   DESCRIPTION     "Generic device assign friendly name response from AOG 
                    in 1001 to 5k ms.
                    The applUptime epoch of the application instance 
                    should be used as reference point for this counter."
::= { sExARCntEntry 63 }

sExARCntAFNR5001to10kms  OBJECT-TYPE
   SYNTAX          Counter32
   MAX-ACCESS      read-only
   STATUS          current
   DESCRIPTION     "Generic device assign friendly name response from AOG 
                    in 5001 to 10k ms.
                    The applUptime epoch of the application instance 
                    should be used as reference point for this counter."
::= { sExARCntEntry 64 }

sExARCntAFNR10001toTimeout  OBJECT-TYPE
   SYNTAX          Counter32
   MAX-ACCESS      read-only
   STATUS          current
   DESCRIPTION     "Generic device assign friendly name response from AOG 
                    in 10001 to Timeout.
                    The applUptime epoch of the application instance 
                    should be used as reference point for this counter."
::= { sExARCntEntry 65 }

sExARCntAFNROverTimeout  OBJECT-TYPE
   SYNTAX          Counter32
   MAX-ACCESS      read-only
   STATUS          current
   DESCRIPTION     "Generic device assign friendly name response from AOG 
                    over Timeout.
                    The applUptime epoch of the application instance 
                    should be used as reference point for this counter."
::= { sExARCntEntry 66 }

sExIIARCntTable OBJECT-TYPE
   SYNTAX          SEQUENCE OF SExIIARCntEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sExIIARCnt 1 } 

sExIIARCntEntry OBJECT-TYPE
   SYNTAX          SExIIARCntEntry
   MAX-ACCESS      not-accessible
   STATUS          current
   DESCRIPTION     "Counters for SES get the response from AOG."
   INDEX { applIndex }
::= { sExIIARCntTable  1 }

SExIIARCntEntry  ::= SEQUENCE
{
   sExIIARCntAQSFGD0to1kms         Counter32,
   sExIIARCntAQSFGD1001to5kms      Counter32,
   sExIIARCntAQSFGD5001to10kms     Counter32,
   sExIIARCntAQSFGD10001toTimeout  Counter32,
   sExIIARCntAQSFGDOverTimeout     Counter32,
   sExIIARCntADVS0to1kms           Counter32,
   sExIIARCntADVS1001to5kms        Counter32,
   sExIIARCntADVS5001to10kms       Counter32,
   sExIIARCntADVS10001toTimeout    Counter32,
   sExIIARCntADVSOverTimeout       Counter32,
   sExIIARCntALUTIBO0to1kms        Counter32,
   sExIIARCntALUTIBO1001to5kms     Counter32,
   sExIIARCntALUTIBO5001to10kms    Counter32,
   sExIIARCntALUTIBO10001toTimeout Counter32,
   sExIIARCntALUTIBOOverTimeout    Counter32,
   sExIIARCntATIBV0to1kms          Counter32,
   sExIIARCntATIBV1001to5kms       Counter32,
   sExIIARCntATIBV5001to10kms      Counter32,
   sExIIARCntATIBV10001toTimeout   Counter32,
   sExIIARCntATIBVOverTimeout      Counter32,
   sExIIARCntADDBO0to1kms          Counter32,
   sExIIARCntADDBO1001to5kms       Counter32,
   sExIIARCntADDBO5001to10kms      Counter32,
   sExIIARCntADDBO10001toTimeout   Counter32,
   sExIIARCntADDBOOverTimeout      Counter32,
   sExIIARCntAUIFGD0to1kms         Counter32,
   sExIIARCntAUIFGD1001to5kms      Counter32,
   sExIIARCntAUIFGD5001to10kms     Counter32,
   sExIIARCntAUIFGD10001toTimeout  Counter32,
   sExIIARCntAUIFGDOverTimeout     Counter32,
   sExIIARCntAUMFGD0to1kms         Counter32,
   sExIIARCntAUMFGD1001to5kms      Counter32,
   sExIIARCntAUMFGD5001to10kms     Counter32,
   sExIIARCntAUMFGD10001toTimeout  Counter32,
   sExIIARCntAUMFGDOverTimeout     Counter32,
   sExIIARCntEUP0to1kms            Counter32,
   sExIIARCntEUP1001to5kms         Counter32,
   sExIIARCntEUP5001to10kms        Counter32,
   sExIIARCntEUP10001toTimeout     Counter32,
   sExIIARCntEUPOverTimeout        Counter32,
   sExIIARCntDUP0to1kms            Counter32,
   sExIIARCntDUP1001to5kms         Counter32,
   sExIIARCntDUP5001to10kms        Counter32,
   sExIIARCntDUP10001toTimeout     Counter32,
   sExIIARCntDUPOverTimeout        Counter32
}

sExIIARCntAQSFGD0to1kms  OBJECT-TYPE
   SYNTAX          Counter32
   MAX-ACCESS      read-only
   STATUS          current
   DESCRIPTION     "AOG Query Service For Generic Device SES gets 
                    response from AOG in 0 to 1k ms.
                    The applUptime epoch of the application instance 
                    should be used as reference point for this counter."
::= { sExIIARCntEntry 2 }

sExIIARCntAQSFGD1001to5kms  OBJECT-TYPE
   SYNTAX          Counter32
   MAX-ACCESS      read-only
   STATUS          current
   DESCRIPTION     "AOG Query Service For Generic Device SES gets 
                    response from AOG in 1001 to 5k ms.
                    The applUptime epoch of the application instance 
                    should be used as reference point for this counter."
::= { sExIIARCntEntry 3 }

sExIIARCntAQSFGD5001to10kms  OBJECT-TYPE
   SYNTAX          Counter32
   MAX-ACCESS      read-only
   STATUS          current
   DESCRIPTION     "AOG Query Service For Generic Device SES gets 
                    response from AOG in 5001 to 10k ms.
                    The applUptime epoch of the application instance 
                    should be used as reference point for this counter."
::= { sExIIARCntEntry 4 }

sExIIARCntAQSFGD10001toTimeout  OBJECT-TYPE
   SYNTAX          Counter32
   MAX-ACCESS      read-only
   STATUS          current
   DESCRIPTION     "AOG Query Service For Generic Device SES gets 
                    response from AOG in 10001 to Timeout.
                    The applUptime epoch of the application instance 
                    should be used as reference point for this counter."
::= { sExIIARCntEntry 5 }

sExIIARCntAQSFGDOverTimeout  OBJECT-TYPE
   SYNTAX          Counter32
   MAX-ACCESS      read-only
   STATUS          current
   DESCRIPTION     "AOG Query Service For Generic Device SES gets 
                    response from AOG over Timeout.
                    The applUptime epoch of the application instance 
                    should be used as reference point for this counter."
::= { sExIIARCntEntry 6 }

sExIIARCntADVS0to1kms  OBJECT-TYPE
   SYNTAX          Counter32
   MAX-ACCESS      read-only
   STATUS          current
   DESCRIPTION     "AOG Delete Vowifi Service SES gets response from AOG 
                    in 0 to 1k ms.
                    The applUptime epoch of the application instance 
                    should be used as reference point for this counter."
::= { sExIIARCntEntry 7 }

sExIIARCntADVS1001to5kms  OBJECT-TYPE
   SYNTAX          Counter32
   MAX-ACCESS      read-only
   STATUS          current
   DESCRIPTION     "AOG Delete Vowifi Service SES gets response from AOG 
                    in 1001 to 5k ms.
                    The applUptime epoch of the application instance 
                    should be used as reference point for this counter."
::= { sExIIARCntEntry 8 }

sExIIARCntADVS5001to10kms  OBJECT-TYPE
   SYNTAX          Counter32
   MAX-ACCESS      read-only
   STATUS          current
   DESCRIPTION     "AOG Delete Vowifi Service SES gets response from AOG 
                    in 5001 to 10k ms.
                    The applUptime epoch of the application instance 
                    should be used as reference point for this counter."
::= { sExIIARCntEntry 9 }

sExIIARCntADVS10001toTimeout  OBJECT-TYPE
   SYNTAX          Counter32
   MAX-ACCESS      read-only
   STATUS          current
   DESCRIPTION     "AOG Delete Vowifi Service SES gets response from AOG 
                    in 10001 to Timeout.
                    The applUptime epoch of the application instance 
                    should be used as reference point for this counter."
::= { sExIIARCntEntry 10 }

sExIIARCntADVSOverTimeout  OBJECT-TYPE
   SYNTAX          Counter32
   MAX-ACCESS      read-only
   STATUS          current
   DESCRIPTION     "AOG Delete Vowifi Service SES gets response from AOG 
                    over Timeout.
                    The applUptime epoch of the application instance 
                    should be used as reference point for this counter."
::= { sExIIARCntEntry 11 }

sExIIARCntALUTIBO0to1kms  OBJECT-TYPE
   SYNTAX          Counter32
   MAX-ACCESS      read-only
   STATUS          current
   DESCRIPTION     "AOG Lock Unlock Teardown Ipsec By OwnerId SES gets 
                    response from AOG in 0 to 1k ms.
                    The applUptime epoch of the application instance 
                    should be used as reference point for this counter."
::= { sExIIARCntEntry 12 }

sExIIARCntALUTIBO1001to5kms  OBJECT-TYPE
   SYNTAX          Counter32
   MAX-ACCESS      read-only
   STATUS          current
   DESCRIPTION     "AOG Lock Unlock Teardown Ipsec By OwnerId SES gets 
                    response from AOG in 1001 to 5k ms.
                    The applUptime epoch of the application instance 
                    should be used as reference point for this counter."
::= { sExIIARCntEntry 13 }

sExIIARCntALUTIBO5001to10kms  OBJECT-TYPE
   SYNTAX          Counter32
   MAX-ACCESS      read-only
   STATUS          current
   DESCRIPTION     "AOG Lock Unlock Teardown Ipsec By OwnerId SES gets 
                    response from AOG in 5001 to 10k ms.
                    The applUptime epoch of the application instance 
                    should be used as reference point for this counter."
::= { sExIIARCntEntry 14 }

sExIIARCntALUTIBO10001toTimeout  OBJECT-TYPE
   SYNTAX          Counter32
   MAX-ACCESS      read-only
   STATUS          current
   DESCRIPTION     "AOG Lock Unlock Teardown Ipsec By OwnerId SES gets 
                    response from AOG in 10001 to Timeout.
                    The applUptime epoch of the application instance 
                    should be used as reference point for this counter."
::= { sExIIARCntEntry 15 }

sExIIARCntALUTIBOOverTimeout  OBJECT-TYPE
   SYNTAX          Counter32
   MAX-ACCESS      read-only
   STATUS          current
   DESCRIPTION     "AOG Lock Unlock Teardown Ipsec By OwnerId SES gets 
                    response from AOG over Timeout.
                    The applUptime epoch of the application instance 
                    should be used as reference point for this counter."
::= { sExIIARCntEntry 16 }

sExIIARCntATIBV0to1kms  OBJECT-TYPE
   SYNTAX          Counter32
   MAX-ACCESS      read-only
   STATUS          current
   DESCRIPTION     "AOG Teardown Ipsec By VImsi SES gets response from 
                    AOG in 0 to 1k ms.
                    The applUptime epoch of the application instance 
                    should be used as reference point for this counter."
::= { sExIIARCntEntry 17 }

sExIIARCntATIBV1001to5kms  OBJECT-TYPE
   SYNTAX          Counter32
   MAX-ACCESS      read-only
   STATUS          current
   DESCRIPTION     "AOG Teardown Ipsec By VImsi SES gets response from 
                    AOG in 1001 to 5k ms.
                    The applUptime epoch of the application instance 
                    should be used as reference point for this counter."
::= { sExIIARCntEntry 18 }

sExIIARCntATIBV5001to10kms  OBJECT-TYPE
   SYNTAX          Counter32
   MAX-ACCESS      read-only
   STATUS          current
   DESCRIPTION     "AOG Teardown Ipsec By VImsi SES gets response from 
                    AOG in 5001 to 10k ms.
                    The applUptime epoch of the application instance 
                    should be used as reference point for this counter."
::= { sExIIARCntEntry 19 }

sExIIARCntATIBV10001toTimeout  OBJECT-TYPE
   SYNTAX          Counter32
   MAX-ACCESS      read-only
   STATUS          current
   DESCRIPTION     "AOG Teardown Ipsec By VImsi SES gets response from 
                    AOG in 10001 to Timeout.
                    The applUptime epoch of the application instance 
                    should be used as reference point for this counter."
::= { sExIIARCntEntry 20 }

sExIIARCntATIBVOverTimeout  OBJECT-TYPE
   SYNTAX          Counter32
   MAX-ACCESS      read-only
   STATUS          current
   DESCRIPTION     "AOG Teardown Ipsec By VImsi SES gets response from 
                    AOG over Timeout.
                    The applUptime epoch of the application instance 
                    should be used as reference point for this counter."
::= { sExIIARCntEntry 21 }

sExIIARCntADDBO0to1kms  OBJECT-TYPE
   SYNTAX          Counter32
   MAX-ACCESS      read-only
   STATUS          current
   DESCRIPTION     "AOG Delete Device By OwnerId SES gets response from 
                    AOG in 0 to 1k ms.
                    The applUptime epoch of the application instance 
                    should be used as reference point for this counter."
::= { sExIIARCntEntry 22 }

sExIIARCntADDBO1001to5kms  OBJECT-TYPE
   SYNTAX          Counter32
   MAX-ACCESS      read-only
   STATUS          current
   DESCRIPTION     "AOG Delete Device By OwnerId SES gets response from 
                    AOG in 1001 to 5k ms.
                    The applUptime epoch of the application instance 
                    should be used as reference point for this counter."
::= { sExIIARCntEntry 23 }

sExIIARCntADDBO5001to10kms  OBJECT-TYPE
   SYNTAX          Counter32
   MAX-ACCESS      read-only
   STATUS          current
   DESCRIPTION     "AOG Delete Device By OwnerId SES gets response from 
                    AOG in 5001 to 10k ms.
                    The applUptime epoch of the application instance 
                    should be used as reference point for this counter."
::= { sExIIARCntEntry 24 }

sExIIARCntADDBO10001toTimeout  OBJECT-TYPE
   SYNTAX          Counter32
   MAX-ACCESS      read-only
   STATUS          current
   DESCRIPTION     "AOG Delete Device By OwnerId SES gets response from 
                    AOG in 10001 to Timeout.
                    The applUptime epoch of the application instance 
                    should be used as reference point for this counter."
::= { sExIIARCntEntry 25 }

sExIIARCntADDBOOverTimeout  OBJECT-TYPE
   SYNTAX          Counter32
   MAX-ACCESS      read-only
   STATUS          current
   DESCRIPTION     "AOG Delete Device By OwnerId SES gets response from 
                    AOG over Timeout.
                    The applUptime epoch of the application instance 
                    should be used as reference point for this counter."
::= { sExIIARCntEntry 26 }

sExIIARCntAUIFGD0to1kms  OBJECT-TYPE
   SYNTAX          Counter32
   MAX-ACCESS      read-only
   STATUS          current
   DESCRIPTION     "AOG Update Imsi For Generic Device SES gets response 
                    from AOG in 0 to 1k ms.
                    The applUptime epoch of the application instance 
                    should be used as reference point for this counter."
::= { sExIIARCntEntry 27 }

sExIIARCntAUIFGD1001to5kms  OBJECT-TYPE
   SYNTAX          Counter32
   MAX-ACCESS      read-only
   STATUS          current
   DESCRIPTION     "AOG Update Imsi For Generic Device SES gets response 
                    from AOG in 1001 to 5k ms.
                    The applUptime epoch of the application instance 
                    should be used as reference point for this counter."
::= { sExIIARCntEntry 28 }

sExIIARCntAUIFGD5001to10kms  OBJECT-TYPE
   SYNTAX          Counter32
   MAX-ACCESS      read-only
   STATUS          current
   DESCRIPTION     "AOG Update Imsi For Generic Device SES gets response 
                    from AOG in 5001 to 10k ms.
                    The applUptime epoch of the application instance 
                    should be used as reference point for this counter."
::= { sExIIARCntEntry 29 }

sExIIARCntAUIFGD10001toTimeout  OBJECT-TYPE
   SYNTAX          Counter32
   MAX-ACCESS      read-only
   STATUS          current
   DESCRIPTION     "AOG Update Imsi For Generic Device SES gets response 
                    from AOG in 10001 to Timeout.
                    The applUptime epoch of the application instance 
                    should be used as reference point for this counter."
::= { sExIIARCntEntry 30 }

sExIIARCntAUIFGDOverTimeout  OBJECT-TYPE
   SYNTAX          Counter32
   MAX-ACCESS      read-only
   STATUS          current
   DESCRIPTION     "AOG Update Imsi For Generic Device SES gets response 
                    from AOG over Timeout.
                    The applUptime epoch of the application instance 
                    should be used as reference point for this counter."
::= { sExIIARCntEntry 31 }

sExIIARCntAUMFGD0to1kms  OBJECT-TYPE
   SYNTAX          Counter32
   MAX-ACCESS      read-only
   STATUS          current
   DESCRIPTION     "AOG Update MSISDN For Generic Device SES gets 
                    response from AOG in 0 to 1k ms.
                    The applUptime epoch of the application instance 
                    should be used as reference point for this counter."
::= { sExIIARCntEntry 32 }

sExIIARCntAUMFGD1001to5kms  OBJECT-TYPE
   SYNTAX          Counter32
   MAX-ACCESS      read-only
   STATUS          current
   DESCRIPTION     "AOG Update MSISDN For Generic Device SES gets 
                    response from AOG in 1001 to 5k ms.
                    The applUptime epoch of the application instance 
                    should be used as reference point for this counter."
::= { sExIIARCntEntry 33 }

sExIIARCntAUMFGD5001to10kms  OBJECT-TYPE
   SYNTAX          Counter32
   MAX-ACCESS      read-only
   STATUS          current
   DESCRIPTION     "AOG Update MSISDN For Generic Device SES gets 
                    response from AOG in 5001 to 10k ms.
                    The applUptime epoch of the application instance 
                    should be used as reference point for this counter."
::= { sExIIARCntEntry 34 }

sExIIARCntAUMFGD10001toTimeout  OBJECT-TYPE
   SYNTAX          Counter32
   MAX-ACCESS      read-only
   STATUS          current
   DESCRIPTION     "AOG Update MSISDN For Generic Device SES gets 
                    response from AOG in 10001 to Timeout.
                    The applUptime epoch of the application instance 
                    should be used as reference point for this counter."
::= { sExIIARCntEntry 35 }

sExIIARCntAUMFGDOverTimeout  OBJECT-TYPE
   SYNTAX          Counter32
   MAX-ACCESS      read-only
   STATUS          current
   DESCRIPTION     "AOG Update MSISDN For Generic Device SES gets 
                    response from AOG over Timeout.
                    The applUptime epoch of the application instance 
                    should be used as reference point for this counter."
::= { sExIIARCntEntry 36 }

sExIIARCntEUP0to1kms  OBJECT-TYPE
   SYNTAX          Counter32
   MAX-ACCESS      read-only
   STATUS          current
   DESCRIPTION     "SES gets enable user profile enable user profile 
                    response from AOG in 0 to 1k ms.
                    The applUptime epoch of the application instance 
                    should be used as reference point for this counter."
::= { sExIIARCntEntry 37 }

sExIIARCntEUP1001to5kms  OBJECT-TYPE
   SYNTAX          Counter32
   MAX-ACCESS      read-only
   STATUS          current
   DESCRIPTION     "SES gets enable user profile response from AOG in 
                    1001 to 5k ms.
                    The applUptime epoch of the application instance 
                    should be used as reference point for this counter."
::= { sExIIARCntEntry 38 }

sExIIARCntEUP5001to10kms  OBJECT-TYPE
   SYNTAX          Counter32
   MAX-ACCESS      read-only
   STATUS          current
   DESCRIPTION     "SES gets enable user profile response from AOG in 
                    5001 to 10k ms.
                    The applUptime epoch of the application instance 
                    should be used as reference point for this counter."
::= { sExIIARCntEntry 39 }

sExIIARCntEUP10001toTimeout  OBJECT-TYPE
   SYNTAX          Counter32
   MAX-ACCESS      read-only
   STATUS          current
   DESCRIPTION     "SES gets enable user profile response from AOG in 
                    10001 to Timeout.
                    The applUptime epoch of the application instance 
                    should be used as reference point for this counter."
::= { sExIIARCntEntry 40 }

sExIIARCntEUPOverTimeout  OBJECT-TYPE
   SYNTAX          Counter32
   MAX-ACCESS      read-only
   STATUS          current
   DESCRIPTION     "SES gets enable user profile response from AOG over 
                    Timeout.
                    The applUptime epoch of the application instance 
                    should be used as reference point for this counter."
::= { sExIIARCntEntry 41 }

sExIIARCntDUP0to1kms  OBJECT-TYPE
   SYNTAX          Counter32
   MAX-ACCESS      read-only
   STATUS          current
   DESCRIPTION     "SES gets disable user profile disable user profile 
                    response from AOG in 0 to 1k ms.
                    The applUptime epoch of the application instance 
                    should be used as reference point for this counter."
::= { sExIIARCntEntry 42 }

sExIIARCntDUP1001to5kms  OBJECT-TYPE
   SYNTAX          Counter32
   MAX-ACCESS      read-only
   STATUS          current
   DESCRIPTION     "SES gets disable user profile response from AOG in 
                    1001 to 5k ms.
                    The applUptime epoch of the application instance 
                    should be used as reference point for this counter."
::= { sExIIARCntEntry 43 }

sExIIARCntDUP5001to10kms  OBJECT-TYPE
   SYNTAX          Counter32
   MAX-ACCESS      read-only
   STATUS          current
   DESCRIPTION     "SES gets disable user profile response from AOG in 
                    5001 to 10k ms.
                    The applUptime epoch of the application instance 
                    should be used as reference point for this counter."
::= { sExIIARCntEntry 44 }

sExIIARCntDUP10001toTimeout  OBJECT-TYPE
   SYNTAX          Counter32
   MAX-ACCESS      read-only
   STATUS          current
   DESCRIPTION     "SES gets disable user profile response from AOG in 
                    10001 to Timeout.
                    The applUptime epoch of the application instance 
                    should be used as reference point for this counter."
::= { sExIIARCntEntry 45 }

sExIIARCntDUPOverTimeout  OBJECT-TYPE
   SYNTAX          Counter32
   MAX-ACCESS      read-only
   STATUS          current
   DESCRIPTION     "SES gets disable user profile response from AOG over 
                    Timeout.
                    The applUptime epoch of the application instance 
                    should be used as reference point for this counter."
::= { sExIIARCntEntry 46 }

sExERCntTable OBJECT-TYPE
   SYNTAX          SEQUENCE OF SExERCntEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sExERCnt 1 } 

sExERCntEntry OBJECT-TYPE
   SYNTAX          SExERCntEntry
   MAX-ACCESS      not-accessible
   STATUS          current
   DESCRIPTION     "Extend Counters for SES get the response from 
                    ESAdapter."
   INDEX { applIndex }
::= { sExERCntTable  1 }

SExERCntEntry  ::= SEQUENCE
{
   sExERCntGMI0to1kms        Counter32,
   sExERCntGMI1001to5kms     Counter32,
   sExERCntGMI5001to10kms    Counter32,
   sExERCntGMI10001toTimeout Counter32,
   sExERCntGMIOverTimeout    Counter32
}

sExERCntGMI0to1kms  OBJECT-TYPE
   SYNTAX          Counter32
   MAX-ACCESS      read-only
   STATUS          current
   DESCRIPTION     "GET MAPPED ID BY REQUEST ID response from ESAdapter 
                    in 0 to 1k ms.
                    The applUptime epoch of the application instance 
                    should be used as reference point for this counter."
::= { sExERCntEntry 2 }

sExERCntGMI1001to5kms  OBJECT-TYPE
   SYNTAX          Counter32
   MAX-ACCESS      read-only
   STATUS          current
   DESCRIPTION     "GET MAPPED ID BY REQUEST ID response from ESAdapter 
                    in 1001 to 5k ms.
                    The applUptime epoch of the application instance 
                    should be used as reference point for this counter."
::= { sExERCntEntry 3 }

sExERCntGMI5001to10kms  OBJECT-TYPE
   SYNTAX          Counter32
   MAX-ACCESS      read-only
   STATUS          current
   DESCRIPTION     "GET MAPPED ID BY REQUEST ID response from ESAdapter 
                    in 5001 to 10k ms.
                    The applUptime epoch of the application instance 
                    should be used as reference point for this counter."
::= { sExERCntEntry 4 }

sExERCntGMI10001toTimeout  OBJECT-TYPE
   SYNTAX          Counter32
   MAX-ACCESS      read-only
   STATUS          current
   DESCRIPTION     "GET MAPPED ID BY REQUEST ID response from ESAdapter 
                    in 10001 to Timeout.
                    The applUptime epoch of the application instance 
                    should be used as reference point for this counter."
::= { sExERCntEntry 5 }

sExERCntGMIOverTimeout  OBJECT-TYPE
   SYNTAX          Counter32
   MAX-ACCESS      read-only
   STATUS          current
   DESCRIPTION     "GET MAPPED ID BY REQUEST ID response from ESAdapter 
                    over Timeout.
                    The applUptime epoch of the application instance 
                    should be used as reference point for this counter."
::= { sExERCntEntry 6 }

sPTSCntTable OBJECT-TYPE
   SYNTAX          SEQUENCE OF SPTSCntEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sPTSCnt 1 } 

sPTSCntEntry OBJECT-TYPE
   SYNTAX          SPTSCntEntry
   MAX-ACCESS      not-accessible
   STATUS          current
   DESCRIPTION     "Counters for SES get the response from Push Token 
                    Server."
   INDEX { applIndex }
::= { sPTSCntTable  1 }

SPTSCntEntry  ::= SEQUENCE
{
   sPTSCntPAPT0to1kms        Counter32,
   sPTSCntPAPT1001to5kms     Counter32,
   sPTSCntPAPT5001to10kms    Counter32,
   sPTSCntPAPT10001toTimeout Counter32,
   sPTSCntPAPTOverTimeout    Counter32,
   sPTSCntPDPT0to1kms        Counter32,
   sPTSCntPDPT1001to5kms     Counter32,
   sPTSCntPDPT5001to10kms    Counter32,
   sPTSCntPDPT10001toTimeout Counter32,
   sPTSCntPDPTOverTimeout    Counter32,
   sPTSCntPQPT0to1kms        Counter32,
   sPTSCntPQPT1001to5kms     Counter32,
   sPTSCntPQPT5001to10kms    Counter32,
   sPTSCntPQPT10001toTimeout Counter32,
   sPTSCntPQPTOverTimeout    Counter32,
   sPTSCntPUPT0to1kms        Counter32,
   sPTSCntPUPT1001to5kms     Counter32,
   sPTSCntPUPT5001to10kms    Counter32,
   sPTSCntPUPT10001toTimeout Counter32,
   sPTSCntPUPTOverTimeout    Counter32,
   sPTSCntSC0to200           Counter32,
   sPTSCntSC200to201         Counter32,
   sPTSCntSC201to204         Counter32,
   sPTSCntSC204to304         Counter32,
   sPTSCntSC304to400         Counter32,
   sPTSCntSC400to404         Counter32
}

sPTSCntPAPT0to1kms  OBJECT-TYPE
   SYNTAX          Counter32
   MAX-ACCESS      read-only
   STATUS          current
   DESCRIPTION     "PTS ADD PUSH TOKEN SES gets response from Push Token 
                    Server in 0 to 1k ms.
                    The applUptime epoch of the application instance 
                    should be used as reference point for this counter."
::= { sPTSCntEntry 2 }

sPTSCntPAPT1001to5kms  OBJECT-TYPE
   SYNTAX          Counter32
   MAX-ACCESS      read-only
   STATUS          current
   DESCRIPTION     "PTS ADD PUSH TOKEN SES gets response from Push Token 
                    Server in 1001 to 5k ms.
                    The applUptime epoch of the application instance 
                    should be used as reference point for this counter."
::= { sPTSCntEntry 3 }

sPTSCntPAPT5001to10kms  OBJECT-TYPE
   SYNTAX          Counter32
   MAX-ACCESS      read-only
   STATUS          current
   DESCRIPTION     "PTS ADD PUSH TOKEN SES gets response from Push Token 
                    Server in 5001 to 10k ms.
                    The applUptime epoch of the application instance 
                    should be used as reference point for this counter."
::= { sPTSCntEntry 4 }

sPTSCntPAPT10001toTimeout  OBJECT-TYPE
   SYNTAX          Counter32
   MAX-ACCESS      read-only
   STATUS          current
   DESCRIPTION     "PTS ADD PUSH TOKEN SES gets response from Push Token 
                    Server in 10001 to Timeout.
                    The applUptime epoch of the application instance 
                    should be used as reference point for this counter."
::= { sPTSCntEntry 5 }

sPTSCntPAPTOverTimeout  OBJECT-TYPE
   SYNTAX          Counter32
   MAX-ACCESS      read-only
   STATUS          current
   DESCRIPTION     "PTS ADD PUSH TOKEN SES gets response from Push Token 
                    Server over Timeout.
                    The applUptime epoch of the application instance 
                    should be used as reference point for this counter."
::= { sPTSCntEntry 6 }

sPTSCntPDPT0to1kms  OBJECT-TYPE
   SYNTAX          Counter32
   MAX-ACCESS      read-only
   STATUS          current
   DESCRIPTION     "PTS DELETE PUSH TOKEN SES gets response from Push 
                    Token Server in 0 to 1k ms.
                    The applUptime epoch of the application instance 
                    should be used as reference point for this counter."
::= { sPTSCntEntry 7 }

sPTSCntPDPT1001to5kms  OBJECT-TYPE
   SYNTAX          Counter32
   MAX-ACCESS      read-only
   STATUS          current
   DESCRIPTION     "PTS DELETE PUSH TOKEN SES gets response from Push 
                    Token Server in 1001 to 5k ms.
                    The applUptime epoch of the application instance 
                    should be used as reference point for this counter."
::= { sPTSCntEntry 8 }

sPTSCntPDPT5001to10kms  OBJECT-TYPE
   SYNTAX          Counter32
   MAX-ACCESS      read-only
   STATUS          current
   DESCRIPTION     "PTS DELETE PUSH TOKEN SES gets response from Push 
                    Token Server in 5001 to 10k ms.
                    The applUptime epoch of the application instance 
                    should be used as reference point for this counter."
::= { sPTSCntEntry 9 }

sPTSCntPDPT10001toTimeout  OBJECT-TYPE
   SYNTAX          Counter32
   MAX-ACCESS      read-only
   STATUS          current
   DESCRIPTION     "PTS DELETE PUSH TOKEN SES gets response from Push 
                    Token Server in 10001 to Timeout.
                    The applUptime epoch of the application instance 
                    should be used as reference point for this counter."
::= { sPTSCntEntry 10 }

sPTSCntPDPTOverTimeout  OBJECT-TYPE
   SYNTAX          Counter32
   MAX-ACCESS      read-only
   STATUS          current
   DESCRIPTION     "PTS DELETE PUSH TOKEN SES gets response from Push 
                    Token Server over Timeout.
                    The applUptime epoch of the application instance 
                    should be used as reference point for this counter."
::= { sPTSCntEntry 11 }

sPTSCntPQPT0to1kms  OBJECT-TYPE
   SYNTAX          Counter32
   MAX-ACCESS      read-only
   STATUS          current
   DESCRIPTION     "PTS QUERY PUSH TOKEN SES gets response from Push 
                    Token Server in 0 to 1k ms.
                    The applUptime epoch of the application instance 
                    should be used as reference point for this counter."
::= { sPTSCntEntry 12 }

sPTSCntPQPT1001to5kms  OBJECT-TYPE
   SYNTAX          Counter32
   MAX-ACCESS      read-only
   STATUS          current
   DESCRIPTION     "PTS QUERY PUSH TOKEN SES gets response from Push 
                    Token Server in 1001 to 5k ms.
                    The applUptime epoch of the application instance 
                    should be used as reference point for this counter."
::= { sPTSCntEntry 13 }

sPTSCntPQPT5001to10kms  OBJECT-TYPE
   SYNTAX          Counter32
   MAX-ACCESS      read-only
   STATUS          current
   DESCRIPTION     "PTS QUERY PUSH TOKEN SES gets response from Push 
                    Token Server in 5001 to 10k ms.
                    The applUptime epoch of the application instance 
                    should be used as reference point for this counter."
::= { sPTSCntEntry 14 }

sPTSCntPQPT10001toTimeout  OBJECT-TYPE
   SYNTAX          Counter32
   MAX-ACCESS      read-only
   STATUS          current
   DESCRIPTION     "PTS QUERY PUSH TOKEN SES gets response from Push 
                    Token Server in 10001 to Timeout.
                    The applUptime epoch of the application instance 
                    should be used as reference point for this counter."
::= { sPTSCntEntry 15 }

sPTSCntPQPTOverTimeout  OBJECT-TYPE
   SYNTAX          Counter32
   MAX-ACCESS      read-only
   STATUS          current
   DESCRIPTION     "PTS QUERY PUSH TOKEN SES gets response from Push 
                    Token Server over Timeout.
                    The applUptime epoch of the application instance 
                    should be used as reference point for this counter."
::= { sPTSCntEntry 16 }

sPTSCntPUPT0to1kms  OBJECT-TYPE
   SYNTAX          Counter32
   MAX-ACCESS      read-only
   STATUS          current
   DESCRIPTION     "PTS UPDATE PUSH TOKEN SES gets response from Push 
                    Token Server in 0 to 1k ms.
                    The applUptime epoch of the application instance 
                    should be used as reference point for this counter."
::= { sPTSCntEntry 17 }

sPTSCntPUPT1001to5kms  OBJECT-TYPE
   SYNTAX          Counter32
   MAX-ACCESS      read-only
   STATUS          current
   DESCRIPTION     "PTS UPDATE PUSH TOKEN SES gets response from Push 
                    Token Server in 1001 to 5k ms.
                    The applUptime epoch of the application instance 
                    should be used as reference point for this counter."
::= { sPTSCntEntry 18 }

sPTSCntPUPT5001to10kms  OBJECT-TYPE
   SYNTAX          Counter32
   MAX-ACCESS      read-only
   STATUS          current
   DESCRIPTION     "PTS UPDATE PUSH TOKEN SES gets response from Push 
                    Token Server in 5001 to 10k ms.
                    The applUptime epoch of the application instance 
                    should be used as reference point for this counter."
::= { sPTSCntEntry 19 }

sPTSCntPUPT10001toTimeout  OBJECT-TYPE
   SYNTAX          Counter32
   MAX-ACCESS      read-only
   STATUS          current
   DESCRIPTION     "PTS UPDATE PUSH TOKEN SES gets response from Push 
                    Token Server in 10001 to Timeout.
                    The applUptime epoch of the application instance 
                    should be used as reference point for this counter."
::= { sPTSCntEntry 20 }

sPTSCntPUPTOverTimeout  OBJECT-TYPE
   SYNTAX          Counter32
   MAX-ACCESS      read-only
   STATUS          current
   DESCRIPTION     "PTS UPDATE PUSH TOKEN SES gets response from Push 
                    Token Server over Timeout.
                    The applUptime epoch of the application instance 
                    should be used as reference point for this counter."
::= { sPTSCntEntry 21 }

sPTSCntSC0to200  OBJECT-TYPE
   SYNTAX          Counter32
   MAX-ACCESS      read-only
   STATUS          current
   DESCRIPTION     "Status code from Push Token Server in 0 to 200.
                    The applUptime epoch of the application instance 
                    should be used as reference point for this counter."
::= { sPTSCntEntry 22 }

sPTSCntSC200to201  OBJECT-TYPE
   SYNTAX          Counter32
   MAX-ACCESS      read-only
   STATUS          current
   DESCRIPTION     "Status code from Push Token Server in 200 to 201.
                    The applUptime epoch of the application instance 
                    should be used as reference point for this counter."
::= { sPTSCntEntry 23 }

sPTSCntSC201to204  OBJECT-TYPE
   SYNTAX          Counter32
   MAX-ACCESS      read-only
   STATUS          current
   DESCRIPTION     "Status code from Push Token Server in 201 to 204.
                    The applUptime epoch of the application instance 
                    should be used as reference point for this counter."
::= { sPTSCntEntry 24 }

sPTSCntSC204to304  OBJECT-TYPE
   SYNTAX          Counter32
   MAX-ACCESS      read-only
   STATUS          current
   DESCRIPTION     "Status code from Push Token Server in 204 to 304.
                    The applUptime epoch of the application instance 
                    should be used as reference point for this counter."
::= { sPTSCntEntry 25 }

sPTSCntSC304to400  OBJECT-TYPE
   SYNTAX          Counter32
   MAX-ACCESS      read-only
   STATUS          current
   DESCRIPTION     "Status code from Push Token Server in 304 to 400.
                    The applUptime epoch of the application instance 
                    should be used as reference point for this counter."
::= { sPTSCntEntry 26 }

sPTSCntSC400to404  OBJECT-TYPE
   SYNTAX          Counter32
   MAX-ACCESS      read-only
   STATUS          current
   DESCRIPTION     "Status code from Push Token Server in 400 to 404.
                    The applUptime epoch of the application instance 
                    should be used as reference point for this counter."
::= { sPTSCntEntry 27 }

sPTSAlarmTable OBJECT-TYPE
   SYNTAX          SEQUENCE OF SPTSAlarmEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { sPTSAlarm 1 } 

sPTSAlarmEntry OBJECT-TYPE
   SYNTAX          SPTSAlarmEntry
   MAX-ACCESS      not-accessible
   STATUS          current
   DESCRIPTION     "Alarm for SES connects Push Token Server failed."
   INDEX { applIndex }
::= { sPTSAlarmTable  1 }

SPTSAlarmEntry  ::= SEQUENCE
{
   sPTSAlarmFailAlarm ItuPerceivedSeverity
}

sPTSAlarmFailAlarm  OBJECT-TYPE
   SYNTAX          ItuPerceivedSeverity
   MAX-ACCESS      read-only
   STATUS          current
   DESCRIPTION     "Ses Connects Push Token Server Failed or Push Token 
                    Server Configuration Error."
::= { sPTSAlarmEntry 2 }

sENSCntTable OBJECT-TYPE
   SYNTAX          SEQUENCE OF SENSCntEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sENSCnt 1 } 

sENSCntEntry OBJECT-TYPE
   SYNTAX          SENSCntEntry
   MAX-ACCESS      not-accessible
   STATUS          current
   DESCRIPTION     "Event Notification Server Response Counters"
   INDEX { applIndex }
::= { sENSCntTable  1 }

SENSCntEntry  ::= SEQUENCE
{
   sENSCntEN0to1kms        Counter32,
   sENSCntEN1001to5kms     Counter32,
   sENSCntEN5001to10kms    Counter32,
   sENSCntEN10001toTimeout Counter32,
   sENSCntENOverTimeout    Counter32,
   sENSCntSC0to200         Counter32,
   sENSCntSC200to400       Counter32,
   sENSCntSC400to500       Counter32,
   sENSCntSC501to503       Counter32
}

sENSCntEN0to1kms  OBJECT-TYPE
   SYNTAX          Counter32
   MAX-ACCESS      read-only
   STATUS          current
   DESCRIPTION     "Ses gets response from Event Notification Server in 0 
                    to 1k ms.
                    The applUptime epoch of the application instance 
                    should be used as reference point for this counter."
::= { sENSCntEntry 2 }

sENSCntEN1001to5kms  OBJECT-TYPE
   SYNTAX          Counter32
   MAX-ACCESS      read-only
   STATUS          current
   DESCRIPTION     "Ses gets response from Event Notification Server in 
                    1001 to 5k ms.
                    The applUptime epoch of the application instance 
                    should be used as reference point for this counter."
::= { sENSCntEntry 3 }

sENSCntEN5001to10kms  OBJECT-TYPE
   SYNTAX          Counter32
   MAX-ACCESS      read-only
   STATUS          current
   DESCRIPTION     "Ses gets response from Event Notification Server in 
                    5001 to 10k ms.
                    The applUptime epoch of the application instance 
                    should be used as reference point for this counter."
::= { sENSCntEntry 4 }

sENSCntEN10001toTimeout  OBJECT-TYPE
   SYNTAX          Counter32
   MAX-ACCESS      read-only
   STATUS          current
   DESCRIPTION     "Ses gets response from Event Notification Serverr in 
                    10001 to Timeout.
                    The applUptime epoch of the application instance 
                    should be used as reference point for this counter."
::= { sENSCntEntry 5 }

sENSCntENOverTimeout  OBJECT-TYPE
   SYNTAX          Counter32
   MAX-ACCESS      read-only
   STATUS          current
   DESCRIPTION     "Ses gets response from Event Notification Server over 
                    Timeout.
                    The applUptime epoch of the application instance 
                    should be used as reference point for this counter."
::= { sENSCntEntry 6 }

sENSCntSC0to200  OBJECT-TYPE
   SYNTAX          Counter32
   MAX-ACCESS      read-only
   STATUS          current
   DESCRIPTION     "Status code from Event Notification Server in 0 to 
                    200.
                    The applUptime epoch of the application instance 
                    should be used as reference point for this counter."
::= { sENSCntEntry 22 }

sENSCntSC200to400  OBJECT-TYPE
   SYNTAX          Counter32
   MAX-ACCESS      read-only
   STATUS          current
   DESCRIPTION     "Status code from Event Notification Server in 200 to 
                    400.
                    The applUptime epoch of the application instance 
                    should be used as reference point for this counter."
::= { sENSCntEntry 23 }

sENSCntSC400to500  OBJECT-TYPE
   SYNTAX          Counter32
   MAX-ACCESS      read-only
   STATUS          current
   DESCRIPTION     "Status code from Event Notification Server in 401 to 
                    501.
                    The applUptime epoch of the application instance 
                    should be used as reference point for this counter."
::= { sENSCntEntry 24 }

sENSCntSC501to503  OBJECT-TYPE
   SYNTAX          Counter32
   MAX-ACCESS      read-only
   STATUS          current
   DESCRIPTION     "Status code from Event Notification Server in 501 to 
                    503.
                    The applUptime epoch of the application instance 
                    should be used as reference point for this counter."
::= { sENSCntEntry 25 }

sENSAlarmTable OBJECT-TYPE
   SYNTAX          SEQUENCE OF SENSAlarmEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sENSAlarm 1 } 

sENSAlarmEntry OBJECT-TYPE
   SYNTAX          SENSAlarmEntry
   MAX-ACCESS      not-accessible
   STATUS          current
   DESCRIPTION     "Alarm for SES connects Event Notification server 
                    failed."
   INDEX { applIndex }
::= { sENSAlarmTable  1 }

SENSAlarmEntry  ::= SEQUENCE
{
   sENSAlarmFailedAlarm ItuPerceivedSeverity
}

sENSAlarmFailedAlarm  OBJECT-TYPE
   SYNTAX          ItuPerceivedSeverity
   MAX-ACCESS      read-only
   STATUS          current
   DESCRIPTION     "SES Connects Event Notification server Failed or 
                    Event Notification server Configuration Error."
::= { sENSAlarmEntry 2 }

sCPSCntTable OBJECT-TYPE
   SYNTAX          SEQUENCE OF SCPSCntEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sCPSCnt 1 } 

sCPSCntEntry OBJECT-TYPE
   SYNTAX          SCPSCntEntry
   MAX-ACCESS      not-accessible
   STATUS          current
   DESCRIPTION     "CPS Server Response Counters"
   INDEX { applIndex }
::= { sCPSCntTable  1 }

SCPSCntEntry  ::= SEQUENCE
{
   sCPSCntCPSS0to1kms         Counter32,
   sCPSCntCPSS1001to5kms      Counter32,
   sCPSCntCPSS5001to10kms     Counter32,
   sCPSCntCPSS10001toTimeout  Counter32,
   sCPSCntCPSSOverTimeout     Counter32,
   sCPSCntCPSAS0to1kms        Counter32,
   sCPSCntCPSAS1001to5kms     Counter32,
   sCPSCntCPSAS5001to10kms    Counter32,
   sCPSCntCPSAS10001toTimeout Counter32,
   sCPSCntCPSASOverTimeout    Counter32,
   sCPSCntCPSSSC0to200        Counter32,
   sCPSCntCPSSSC201to400      Counter32,
   sCPSCntCPSSSC401to500      Counter32,
   sCPSCntCPSSSC501to600      Counter32,
   sCPSCntCPSASSC0to200       Counter32,
   sCPSCntCPSASSC201to400     Counter32,
   sCPSCntCPSASSC401to500     Counter32,
   sCPSCntCPSASSC501to600     Counter32
}

sCPSCntCPSS0to1kms  OBJECT-TYPE
   SYNTAX          Counter32
   MAX-ACCESS      read-only
   STATUS          current
   DESCRIPTION     "Ses gets sync response from CPS Server in 0 to 1k ms.
                    The applUptime epoch of the application instance 
                    should be used as reference point for this counter."
::= { sCPSCntEntry 2 }

sCPSCntCPSS1001to5kms  OBJECT-TYPE
   SYNTAX          Counter32
   MAX-ACCESS      read-only
   STATUS          current
   DESCRIPTION     "Ses gets sync response from CPS Server in 1001 to 5k 
                    ms.
                    The applUptime epoch of the application instance 
                    should be used as reference point for this counter."
::= { sCPSCntEntry 3 }

sCPSCntCPSS5001to10kms  OBJECT-TYPE
   SYNTAX          Counter32
   MAX-ACCESS      read-only
   STATUS          current
   DESCRIPTION     "Ses gets sync response from CPS Server in 5001 to 10k 
                    ms.
                    The applUptime epoch of the application instance 
                    should be used as reference point for this counter."
::= { sCPSCntEntry 4 }

sCPSCntCPSS10001toTimeout  OBJECT-TYPE
   SYNTAX          Counter32
   MAX-ACCESS      read-only
   STATUS          current
   DESCRIPTION     "Ses gets sync response from CPS Serverr in 10001 to 
                    Timeout.
                    The applUptime epoch of the application instance 
                    should be used as reference point for this counter."
::= { sCPSCntEntry 5 }

sCPSCntCPSSOverTimeout  OBJECT-TYPE
   SYNTAX          Counter32
   MAX-ACCESS      read-only
   STATUS          current
   DESCRIPTION     "Ses gets sync response from CPS Server over Timeout.
                    The applUptime epoch of the application instance 
                    should be used as reference point for this counter."
::= { sCPSCntEntry 6 }

sCPSCntCPSAS0to1kms  OBJECT-TYPE
   SYNTAX          Counter32
   MAX-ACCESS      read-only
   STATUS          current
   DESCRIPTION     "Ses gets async response from CPS Server in 0 to 1k 
                    ms.
                    The applUptime epoch of the application instance 
                    should be used as reference point for this counter."
::= { sCPSCntEntry 7 }

sCPSCntCPSAS1001to5kms  OBJECT-TYPE
   SYNTAX          Counter32
   MAX-ACCESS      read-only
   STATUS          current
   DESCRIPTION     "Ses gets async response from CPS Server in 1001 to 5k 
                    ms.
                    The applUptime epoch of the application instance 
                    should be used as reference point for this counter."
::= { sCPSCntEntry 8 }

sCPSCntCPSAS5001to10kms  OBJECT-TYPE
   SYNTAX          Counter32
   MAX-ACCESS      read-only
   STATUS          current
   DESCRIPTION     "Ses gets async response from CPS Server in 5001 to 
                    10k ms.
                    The applUptime epoch of the application instance 
                    should be used as reference point for this counter."
::= { sCPSCntEntry 9 }

sCPSCntCPSAS10001toTimeout  OBJECT-TYPE
   SYNTAX          Counter32
   MAX-ACCESS      read-only
   STATUS          current
   DESCRIPTION     "Ses gets async response from CPS Serverr in 10001 to 
                    Timeout.
                    The applUptime epoch of the application instance 
                    should be used as reference point for this counter."
::= { sCPSCntEntry 10 }

sCPSCntCPSASOverTimeout  OBJECT-TYPE
   SYNTAX          Counter32
   MAX-ACCESS      read-only
   STATUS          current
   DESCRIPTION     "Ses gets async response from CPS Server over Timeout.
                    The applUptime epoch of the application instance 
                    should be used as reference point for this counter."
::= { sCPSCntEntry 11 }

sCPSCntCPSSSC0to200  OBJECT-TYPE
   SYNTAX          Counter32
   MAX-ACCESS      read-only
   STATUS          current
   DESCRIPTION     "Status code from CPS Server sync in 0 to 200.
                    The applUptime epoch of the application instance 
                    should be used as reference point for this counter."
::= { sCPSCntEntry 12 }

sCPSCntCPSSSC201to400  OBJECT-TYPE
   SYNTAX          Counter32
   MAX-ACCESS      read-only
   STATUS          current
   DESCRIPTION     "Status code from CPS Server sync in 201 to 400.
                    The applUptime epoch of the application instance 
                    should be used as reference point for this counter."
::= { sCPSCntEntry 13 }

sCPSCntCPSSSC401to500  OBJECT-TYPE
   SYNTAX          Counter32
   MAX-ACCESS      read-only
   STATUS          current
   DESCRIPTION     "Status code from CPS Server sync in 401 to 500.
                    The applUptime epoch of the application instance 
                    should be used as reference point for this counter."
::= { sCPSCntEntry 14 }

sCPSCntCPSSSC501to600  OBJECT-TYPE
   SYNTAX          Counter32
   MAX-ACCESS      read-only
   STATUS          current
   DESCRIPTION     "Status code from CPS Server sync in 501 to 503.
                    The applUptime epoch of the application instance 
                    should be used as reference point for this counter."
::= { sCPSCntEntry 15 }

sCPSCntCPSASSC0to200  OBJECT-TYPE
   SYNTAX          Counter32
   MAX-ACCESS      read-only
   STATUS          current
   DESCRIPTION     "Status code from CPS Server async in 0 to 200.
                    The applUptime epoch of the application instance 
                    should be used as reference point for this counter."
::= { sCPSCntEntry 16 }

sCPSCntCPSASSC201to400  OBJECT-TYPE
   SYNTAX          Counter32
   MAX-ACCESS      read-only
   STATUS          current
   DESCRIPTION     "Status code from CPS Server async in 201 to 400.
                    The applUptime epoch of the application instance 
                    should be used as reference point for this counter."
::= { sCPSCntEntry 17 }

sCPSCntCPSASSC401to500  OBJECT-TYPE
   SYNTAX          Counter32
   MAX-ACCESS      read-only
   STATUS          current
   DESCRIPTION     "Status code from CPS Server async in 401 to 500.
                    The applUptime epoch of the application instance 
                    should be used as reference point for this counter."
::= { sCPSCntEntry 18 }

sCPSCntCPSASSC501to600  OBJECT-TYPE
   SYNTAX          Counter32
   MAX-ACCESS      read-only
   STATUS          current
   DESCRIPTION     "Status code from CPS Server async in 501 to 600.
                    The applUptime epoch of the application instance 
                    should be used as reference point for this counter."
::= { sCPSCntEntry 19 }

sCPSAlarmTable OBJECT-TYPE
   SYNTAX          SEQUENCE OF SCPSAlarmEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sCPSAlarm 1 } 

sCPSAlarmEntry OBJECT-TYPE
   SYNTAX          SCPSAlarmEntry
   MAX-ACCESS      not-accessible
   STATUS          current
   DESCRIPTION     "Alarm for SES connects CPS Server failed."
   INDEX { applIndex }
::= { sCPSAlarmTable  1 }

SCPSAlarmEntry  ::= SEQUENCE
{
   sCPSAlarmFailedAlarm ItuPerceivedSeverity
}

sCPSAlarmFailedAlarm  OBJECT-TYPE
   SYNTAX          ItuPerceivedSeverity
   MAX-ACCESS      read-only
   STATUS          current
   DESCRIPTION     "SES Connects CPS Server Failed or CPS Server 
                    Configuration Error."
::= { sCPSAlarmEntry 2 }

sESIMSCntTable OBJECT-TYPE
   SYNTAX          SEQUENCE OF SESIMSCntEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sESIMSCnt 1 } 

sESIMSCntEntry OBJECT-TYPE
   SYNTAX          SESIMSCntEntry
   MAX-ACCESS      not-accessible
   STATUS          current
   DESCRIPTION     "ESIM Server Response Counters"
   INDEX { applIndex }
::= { sESIMSCntTable  1 }

SESIMSCntEntry  ::= SEQUENCE
{
   sESIMSCntvd0to1kms           Counter32,
   sESIMSCntvd1001to5kms        Counter32,
   sESIMSCntvd5001to10kms       Counter32,
   sESIMSCntvd10001toTimeoutms  Counter32,
   sESIMSCntvdOverTimeoutms     Counter32,
   sESIMSCntvdSC0to200          Counter32,
   sESIMSCntvdSC201to400        Counter32,
   sESIMSCntvdSC401to404        Counter32,
   sESIMSCntvdSC405to500        Counter32,
   sESIMSCntvdSC501to600        Counter32,
   sESIMSCntrI0to1kms           Counter32,
   sESIMSCntrI1001to5kms        Counter32,
   sESIMSCntrI5001to10kms       Counter32,
   sESIMSCntrI10001toTimeoutms  Counter32,
   sESIMSCntrIOverTimeoutms     Counter32,
   sESIMSCntrISC0to200          Counter32,
   sESIMSCntrISC201to400        Counter32,
   sESIMSCntrISC401to404        Counter32,
   sESIMSCntrISC405to500        Counter32,
   sESIMSCntrISC501to600        Counter32,
   sESIMSCnturI0to1kms          Counter32,
   sESIMSCnturI1001to5kms       Counter32,
   sESIMSCnturI5001to10kms      Counter32,
   sESIMSCnturI10001toTimeoutms Counter32,
   sESIMSCnturIOverTimeoutms    Counter32,
   sESIMSCnturISC0to200         Counter32,
   sESIMSCnturISC201to400       Counter32,
   sESIMSCnturISC401to404       Counter32,
   sESIMSCnturISC405to500       Counter32,
   sESIMSCnturISC501to600       Counter32,
   sESIMSCntbI0to1kms           Counter32,
   sESIMSCntbI1001to5kms        Counter32,
   sESIMSCntbI5001to10kms       Counter32,
   sESIMSCntbI10001toTimeoutms  Counter32,
   sESIMSCntbIOverTimeoutms     Counter32,
   sESIMSCntbISC0to200          Counter32,
   sESIMSCntbISC201to400        Counter32,
   sESIMSCntbISC401to404        Counter32,
   sESIMSCntbISC405to500        Counter32,
   sESIMSCntbISC501to600        Counter32,
   sESIMSCntubI0to1kms          Counter32,
   sESIMSCntubI1001to5kms       Counter32,
   sESIMSCntubI5001to10kms      Counter32,
   sESIMSCntubI10001toTimeoutms Counter32,
   sESIMSCntubIOverTimeoutms    Counter32,
   sESIMSCntubISC0to200         Counter32,
   sESIMSCntubISC201to400       Counter32,
   sESIMSCntubISC401to404       Counter32,
   sESIMSCntubISC405to500       Counter32,
   sESIMSCntubISC501to600       Counter32
}

sESIMSCntvd0to1kms  OBJECT-TYPE
   SYNTAX          Counter32
   MAX-ACCESS      read-only
   STATUS          current
   DESCRIPTION     "SES gets validate device response from ESIM server in 
                    0-1k ms
                    The applUptime epoch of the application instance 
                    should be used as reference point for this counter."
::= { sESIMSCntEntry 2 }

sESIMSCntvd1001to5kms  OBJECT-TYPE
   SYNTAX          Counter32
   MAX-ACCESS      read-only
   STATUS          current
   DESCRIPTION     "SES gets validate device response from ESIM server in 
                    1001-5k ms
                    The applUptime epoch of the application instance 
                    should be used as reference point for this counter."
::= { sESIMSCntEntry 3 }

sESIMSCntvd5001to10kms  OBJECT-TYPE
   SYNTAX          Counter32
   MAX-ACCESS      read-only
   STATUS          current
   DESCRIPTION     "SES gets validate device response from ESIM server in 
                    5001-10k ms
                    The applUptime epoch of the application instance 
                    should be used as reference point for this counter."
::= { sESIMSCntEntry 4 }

sESIMSCntvd10001toTimeoutms  OBJECT-TYPE
   SYNTAX          Counter32
   MAX-ACCESS      read-only
   STATUS          current
   DESCRIPTION     "SES gets validate device response from ESIM server 
                    from 10001 to time out
                    The applUptime epoch of the application instance 
                    should be used as reference point for this counter."
::= { sESIMSCntEntry 5 }

sESIMSCntvdOverTimeoutms  OBJECT-TYPE
   SYNTAX          Counter32
   MAX-ACCESS      read-only
   STATUS          current
   DESCRIPTION     "SES gets validate device response from ESIM server 
                    over time out
                    The applUptime epoch of the application instance 
                    should be used as reference point for this counter."
::= { sESIMSCntEntry 6 }

sESIMSCntvdSC0to200  OBJECT-TYPE
   SYNTAX          Counter32
   MAX-ACCESS      read-only
   STATUS          current
   DESCRIPTION     "Status code validate device response in 0-200 from 
                    ESIM server
                    The applUptime epoch of the application instance 
                    should be used as reference point for this counter."
::= { sESIMSCntEntry 7 }

sESIMSCntvdSC201to400  OBJECT-TYPE
   SYNTAX          Counter32
   MAX-ACCESS      read-only
   STATUS          current
   DESCRIPTION     "Status code validate device response in 201-400 from 
                    ESIM server
                    The applUptime epoch of the application instance 
                    should be used as reference point for this counter."
::= { sESIMSCntEntry 8 }

sESIMSCntvdSC401to404  OBJECT-TYPE
   SYNTAX          Counter32
   MAX-ACCESS      read-only
   STATUS          current
   DESCRIPTION     "Status code validate device response in 401-404 from 
                    ESIM server
                    The applUptime epoch of the application instance 
                    should be used as reference point for this counter."
::= { sESIMSCntEntry 9 }

sESIMSCntvdSC405to500  OBJECT-TYPE
   SYNTAX          Counter32
   MAX-ACCESS      read-only
   STATUS          current
   DESCRIPTION     "Status code validate device response in 405-500 from 
                    ESIM server
                    The applUptime epoch of the application instance 
                    should be used as reference point for this counter."
::= { sESIMSCntEntry 10 }

sESIMSCntvdSC501to600  OBJECT-TYPE
   SYNTAX          Counter32
   MAX-ACCESS      read-only
   STATUS          current
   DESCRIPTION     "Status code validate device response in 501-600 from 
                    ESIM server
                    The applUptime epoch of the application instance 
                    should be used as reference point for this counter."
::= { sESIMSCntEntry 11 }

sESIMSCntrI0to1kms  OBJECT-TYPE
   SYNTAX          Counter32
   MAX-ACCESS      read-only
   STATUS          current
   DESCRIPTION     "SES gets reserve ICCID response from ESIM server in 
                    0-1k ms
                    The applUptime epoch of the application instance 
                    should be used as reference point for this counter."
::= { sESIMSCntEntry 12 }

sESIMSCntrI1001to5kms  OBJECT-TYPE
   SYNTAX          Counter32
   MAX-ACCESS      read-only
   STATUS          current
   DESCRIPTION     "SES gets reserve ICCID response from ESIM server in 
                    1001-5k ms
                    The applUptime epoch of the application instance 
                    should be used as reference point for this counter."
::= { sESIMSCntEntry 13 }

sESIMSCntrI5001to10kms  OBJECT-TYPE
   SYNTAX          Counter32
   MAX-ACCESS      read-only
   STATUS          current
   DESCRIPTION     "SES gets reserve ICCID response from ESIM server in 
                    5001-10k ms
                    The applUptime epoch of the application instance 
                    should be used as reference point for this counter."
::= { sESIMSCntEntry 14 }

sESIMSCntrI10001toTimeoutms  OBJECT-TYPE
   SYNTAX          Counter32
   MAX-ACCESS      read-only
   STATUS          current
   DESCRIPTION     "SES gets reserve ICCID response from ESIM server from 
                    10001 to time out
                    The applUptime epoch of the application instance 
                    should be used as reference point for this counter."
::= { sESIMSCntEntry 15 }

sESIMSCntrIOverTimeoutms  OBJECT-TYPE
   SYNTAX          Counter32
   MAX-ACCESS      read-only
   STATUS          current
   DESCRIPTION     "SES gets reserve ICCID response from ESIM server over 
                    time out
                    The applUptime epoch of the application instance 
                    should be used as reference point for this counter."
::= { sESIMSCntEntry 16 }

sESIMSCntrISC0to200  OBJECT-TYPE
   SYNTAX          Counter32
   MAX-ACCESS      read-only
   STATUS          current
   DESCRIPTION     "Status code reserve ICCID response in 0-200 from ESIM 
                    server
                    The applUptime epoch of the application instance 
                    should be used as reference point for this counter."
::= { sESIMSCntEntry 17 }

sESIMSCntrISC201to400  OBJECT-TYPE
   SYNTAX          Counter32
   MAX-ACCESS      read-only
   STATUS          current
   DESCRIPTION     "Status code reserve ICCID response in 201-400 from 
                    ESIM server
                    The applUptime epoch of the application instance 
                    should be used as reference point for this counter."
::= { sESIMSCntEntry 18 }

sESIMSCntrISC401to404  OBJECT-TYPE
   SYNTAX          Counter32
   MAX-ACCESS      read-only
   STATUS          current
   DESCRIPTION     "Status code reserve ICCID response in 401-404 from 
                    ESIM server
                    The applUptime epoch of the application instance 
                    should be used as reference point for this counter."
::= { sESIMSCntEntry 19 }

sESIMSCntrISC405to500  OBJECT-TYPE
   SYNTAX          Counter32
   MAX-ACCESS      read-only
   STATUS          current
   DESCRIPTION     "Status code reserve ICCID response in 405-500 from 
                    ESIM server
                    The applUptime epoch of the application instance 
                    should be used as reference point for this counter."
::= { sESIMSCntEntry 20 }

sESIMSCntrISC501to600  OBJECT-TYPE
   SYNTAX          Counter32
   MAX-ACCESS      read-only
   STATUS          current
   DESCRIPTION     "Status code reserve ICCID response in 501-600 from 
                    ESIM server
                    The applUptime epoch of the application instance 
                    should be used as reference point for this counter."
::= { sESIMSCntEntry 21 }

sESIMSCnturI0to1kms  OBJECT-TYPE
   SYNTAX          Counter32
   MAX-ACCESS      read-only
   STATUS          current
   DESCRIPTION     "SES gets unreserve ICCID response from ESIM server in 
                    0-1k ms
                    The applUptime epoch of the application instance 
                    should be used as reference point for this counter."
::= { sESIMSCntEntry 22 }

sESIMSCnturI1001to5kms  OBJECT-TYPE
   SYNTAX          Counter32
   MAX-ACCESS      read-only
   STATUS          current
   DESCRIPTION     "SES gets unreserve ICCID response from ESIM server in 
                    1001-5k ms
                    The applUptime epoch of the application instance 
                    should be used as reference point for this counter."
::= { sESIMSCntEntry 23 }

sESIMSCnturI5001to10kms  OBJECT-TYPE
   SYNTAX          Counter32
   MAX-ACCESS      read-only
   STATUS          current
   DESCRIPTION     "SES gets unreserve ICCID response from ESIM server in 
                    5001-10k ms
                    The applUptime epoch of the application instance 
                    should be used as reference point for this counter."
::= { sESIMSCntEntry 24 }

sESIMSCnturI10001toTimeoutms  OBJECT-TYPE
   SYNTAX          Counter32
   MAX-ACCESS      read-only
   STATUS          current
   DESCRIPTION     "SES gets unreserve ICCID response from ESIM server 
                    from 10001 to time out
                    The applUptime epoch of the application instance 
                    should be used as reference point for this counter."
::= { sESIMSCntEntry 25 }

sESIMSCnturIOverTimeoutms  OBJECT-TYPE
   SYNTAX          Counter32
   MAX-ACCESS      read-only
   STATUS          current
   DESCRIPTION     "SES gets unreserve ICCID response from ESIM server 
                    over time out
                    The applUptime epoch of the application instance 
                    should be used as reference point for this counter."
::= { sESIMSCntEntry 26 }

sESIMSCnturISC0to200  OBJECT-TYPE
   SYNTAX          Counter32
   MAX-ACCESS      read-only
   STATUS          current
   DESCRIPTION     "Status code unreserve ICCID response in 0-200 from 
                    ESIM server
                    The applUptime epoch of the application instance 
                    should be used as reference point for this counter."
::= { sESIMSCntEntry 27 }

sESIMSCnturISC201to400  OBJECT-TYPE
   SYNTAX          Counter32
   MAX-ACCESS      read-only
   STATUS          current
   DESCRIPTION     "Status code unreserve ICCID response in 201-400 from 
                    ESIM server
                    The applUptime epoch of the application instance 
                    should be used as reference point for this counter."
::= { sESIMSCntEntry 28 }

sESIMSCnturISC401to404  OBJECT-TYPE
   SYNTAX          Counter32
   MAX-ACCESS      read-only
   STATUS          current
   DESCRIPTION     "Status code unreserve ICCID response in 401-404 from 
                    ESIM server
                    The applUptime epoch of the application instance 
                    should be used as reference point for this counter."
::= { sESIMSCntEntry 29 }

sESIMSCnturISC405to500  OBJECT-TYPE
   SYNTAX          Counter32
   MAX-ACCESS      read-only
   STATUS          current
   DESCRIPTION     "Status code unreserve ICCID response in 405-500 from 
                    ESIM server
                    The applUptime epoch of the application instance 
                    should be used as reference point for this counter."
::= { sESIMSCntEntry 30 }

sESIMSCnturISC501to600  OBJECT-TYPE
   SYNTAX          Counter32
   MAX-ACCESS      read-only
   STATUS          current
   DESCRIPTION     "Status code unreserve ICCID response in 501-600 from 
                    ESIM server
                    The applUptime epoch of the application instance 
                    should be used as reference point for this counter."
::= { sESIMSCntEntry 31 }

sESIMSCntbI0to1kms  OBJECT-TYPE
   SYNTAX          Counter32
   MAX-ACCESS      read-only
   STATUS          current
   DESCRIPTION     "SES gets bind ICCID response from ESIM server in 0-1k 
                    ms
                    The applUptime epoch of the application instance 
                    should be used as reference point for this counter."
::= { sESIMSCntEntry 32 }

sESIMSCntbI1001to5kms  OBJECT-TYPE
   SYNTAX          Counter32
   MAX-ACCESS      read-only
   STATUS          current
   DESCRIPTION     "SES gets bind ICCID response from ESIM server in 
                    1001-5k ms
                    The applUptime epoch of the application instance 
                    should be used as reference point for this counter."
::= { sESIMSCntEntry 33 }

sESIMSCntbI5001to10kms  OBJECT-TYPE
   SYNTAX          Counter32
   MAX-ACCESS      read-only
   STATUS          current
   DESCRIPTION     "SES gets bind ICCID response from ESIM server in 
                    5001-10k ms
                    The applUptime epoch of the application instance 
                    should be used as reference point for this counter."
::= { sESIMSCntEntry 34 }

sESIMSCntbI10001toTimeoutms  OBJECT-TYPE
   SYNTAX          Counter32
   MAX-ACCESS      read-only
   STATUS          current
   DESCRIPTION     "SES gets bind ICCID response from ESIM server from 
                    10001 to time out
                    The applUptime epoch of the application instance 
                    should be used as reference point for this counter."
::= { sESIMSCntEntry 35 }

sESIMSCntbIOverTimeoutms  OBJECT-TYPE
   SYNTAX          Counter32
   MAX-ACCESS      read-only
   STATUS          current
   DESCRIPTION     "SES gets bind ICCID response from ESIM server over 
                    time out
                    The applUptime epoch of the application instance 
                    should be used as reference point for this counter."
::= { sESIMSCntEntry 36 }

sESIMSCntbISC0to200  OBJECT-TYPE
   SYNTAX          Counter32
   MAX-ACCESS      read-only
   STATUS          current
   DESCRIPTION     "Status code bind ICCID response in 0-200 from ESIM 
                    server
                    The applUptime epoch of the application instance 
                    should be used as reference point for this counter."
::= { sESIMSCntEntry 37 }

sESIMSCntbISC201to400  OBJECT-TYPE
   SYNTAX          Counter32
   MAX-ACCESS      read-only
   STATUS          current
   DESCRIPTION     "Status code bind ICCID response in 201-400 from ESIM 
                    server
                    The applUptime epoch of the application instance 
                    should be used as reference point for this counter."
::= { sESIMSCntEntry 38 }

sESIMSCntbISC401to404  OBJECT-TYPE
   SYNTAX          Counter32
   MAX-ACCESS      read-only
   STATUS          current
   DESCRIPTION     "Status code bind ICCID response in 401-404 from ESIM 
                    server
                    The applUptime epoch of the application instance 
                    should be used as reference point for this counter."
::= { sESIMSCntEntry 39 }

sESIMSCntbISC405to500  OBJECT-TYPE
   SYNTAX          Counter32
   MAX-ACCESS      read-only
   STATUS          current
   DESCRIPTION     "Status code bind ICCID response in 405-500 from ESIM 
                    server
                    The applUptime epoch of the application instance 
                    should be used as reference point for this counter."
::= { sESIMSCntEntry 40 }

sESIMSCntbISC501to600  OBJECT-TYPE
   SYNTAX          Counter32
   MAX-ACCESS      read-only
   STATUS          current
   DESCRIPTION     "Status code bind ICCID response in 501-600 from ESIM 
                    server
                    The applUptime epoch of the application instance 
                    should be used as reference point for this counter."
::= { sESIMSCntEntry 41 }

sESIMSCntubI0to1kms  OBJECT-TYPE
   SYNTAX          Counter32
   MAX-ACCESS      read-only
   STATUS          current
   DESCRIPTION     "SES gets unbind ICCID response from ESIM server in 
                    0-1k ms
                    The applUptime epoch of the application instance 
                    should be used as reference point for this counter."
::= { sESIMSCntEntry 42 }

sESIMSCntubI1001to5kms  OBJECT-TYPE
   SYNTAX          Counter32
   MAX-ACCESS      read-only
   STATUS          current
   DESCRIPTION     "SES gets unbind ICCID response from ESIM server in 
                    1001-5k ms
                    The applUptime epoch of the application instance 
                    should be used as reference point for this counter."
::= { sESIMSCntEntry 43 }

sESIMSCntubI5001to10kms  OBJECT-TYPE
   SYNTAX          Counter32
   MAX-ACCESS      read-only
   STATUS          current
   DESCRIPTION     "SES gets unbind ICCID response from ESIM server in 
                    5001-10k ms
                    The applUptime epoch of the application instance 
                    should be used as reference point for this counter."
::= { sESIMSCntEntry 44 }

sESIMSCntubI10001toTimeoutms  OBJECT-TYPE
   SYNTAX          Counter32
   MAX-ACCESS      read-only
   STATUS          current
   DESCRIPTION     "SES gets unbind ICCID response from ESIM server from 
                    10001 to time out
                    The applUptime epoch of the application instance 
                    should be used as reference point for this counter."
::= { sESIMSCntEntry 45 }

sESIMSCntubIOverTimeoutms  OBJECT-TYPE
   SYNTAX          Counter32
   MAX-ACCESS      read-only
   STATUS          current
   DESCRIPTION     "SES gets unbind ICCID response from ESIM server over 
                    time out
                    The applUptime epoch of the application instance 
                    should be used as reference point for this counter."
::= { sESIMSCntEntry 46 }

sESIMSCntubISC0to200  OBJECT-TYPE
   SYNTAX          Counter32
   MAX-ACCESS      read-only
   STATUS          current
   DESCRIPTION     "Status code unbind ICCID response in 0-200 from ESIM 
                    server
                    The applUptime epoch of the application instance 
                    should be used as reference point for this counter."
::= { sESIMSCntEntry 47 }

sESIMSCntubISC201to400  OBJECT-TYPE
   SYNTAX          Counter32
   MAX-ACCESS      read-only
   STATUS          current
   DESCRIPTION     "Status code unbind ICCID response in 201-400 from 
                    ESIM server
                    The applUptime epoch of the application instance 
                    should be used as reference point for this counter."
::= { sESIMSCntEntry 48 }

sESIMSCntubISC401to404  OBJECT-TYPE
   SYNTAX          Counter32
   MAX-ACCESS      read-only
   STATUS          current
   DESCRIPTION     "Status code unbind ICCID response in 401-404 from 
                    ESIM server
                    The applUptime epoch of the application instance 
                    should be used as reference point for this counter."
::= { sESIMSCntEntry 49 }

sESIMSCntubISC405to500  OBJECT-TYPE
   SYNTAX          Counter32
   MAX-ACCESS      read-only
   STATUS          current
   DESCRIPTION     "Status code unbind ICCID response in 405-500 from 
                    ESIM server
                    The applUptime epoch of the application instance 
                    should be used as reference point for this counter."
::= { sESIMSCntEntry 50 }

sESIMSCntubISC501to600  OBJECT-TYPE
   SYNTAX          Counter32
   MAX-ACCESS      read-only
   STATUS          current
   DESCRIPTION     "Status code unbind ICCID response in 501-600 from 
                    ESIM server
                    The applUptime epoch of the application instance 
                    should be used as reference point for this counter."
::= { sESIMSCntEntry 51 }

sESIMSAlarmTable OBJECT-TYPE
   SYNTAX          SEQUENCE OF SESIMSAlarmEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sESIMSAlarm 1 } 

sESIMSAlarmEntry OBJECT-TYPE
   SYNTAX          SESIMSAlarmEntry
   MAX-ACCESS      not-accessible
   STATUS          current
   DESCRIPTION     "Alarm for SES connects ESIM server failed."
   INDEX { applIndex }
::= { sESIMSAlarmTable  1 }

SESIMSAlarmEntry  ::= SEQUENCE
{
   sESIMSAlarmFailedAlarm ItuPerceivedSeverity
}

sESIMSAlarmFailedAlarm  OBJECT-TYPE
   SYNTAX          ItuPerceivedSeverity
   MAX-ACCESS      read-only
   STATUS          current
   DESCRIPTION     "SES Connects ESIM Server Failed or ESIM Server 
                    Configuration Error."
::= { sESIMSAlarmEntry 2 }

sEMASCntTable OBJECT-TYPE
   SYNTAX          SEQUENCE OF SEMASCntEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sEMASCnt 1 } 

sEMASCntEntry OBJECT-TYPE
   SYNTAX          SEMASCntEntry
   MAX-ACCESS      not-accessible
   STATUS          current
   DESCRIPTION     "EMA Server Response Counters"
   INDEX { applIndex }
::= { sEMASCntTable  1 }

SEMASCntEntry  ::= SEQUENCE
{
   sEMASCntcEp0to1kms          Counter32,
   sEMASCntcEp1001to5kms       Counter32,
   sEMASCntcEp5001to10kms      Counter32,
   sEMASCntcEp10001toTimeoutms Counter32,
   sEMASCntcEpOverTimeoutms    Counter32,
   sEMASCntcEpSC0to200         Counter32,
   sEMASCntcEpSC201to400       Counter32,
   sEMASCntcEpSC401to404       Counter32,
   sEMASCntcEpSC405to500       Counter32,
   sEMASCntcEpSC501to600       Counter32,
   sEMASCntdEp0to1kms          Counter32,
   sEMASCntdEp1001to5kms       Counter32,
   sEMASCntdEp5001to10kms      Counter32,
   sEMASCntdEp10001toTimeoutms Counter32,
   sEMASCntdEpOverTimeoutms    Counter32,
   sEMASCntdEpSC0to200         Counter32,
   sEMASCntdEpSC201to400       Counter32,
   sEMASCntdEpSC401to404       Counter32,
   sEMASCntdEpSC405to500       Counter32,
   sEMASCntdEpSC501to600       Counter32,
   sEMASCntsEp0to1kms          Counter32,
   sEMASCntsEp1001to5kms       Counter32,
   sEMASCntsEp5001to10kms      Counter32,
   sEMASCntsEp10001toTimeoutms Counter32,
   sEMASCntsEpOverTimeoutms    Counter32,
   sEMASCntsEpSC0to200         Counter32,
   sEMASCntsEpSC201to400       Counter32,
   sEMASCntsEpSC401to404       Counter32,
   sEMASCntsEpSC405to500       Counter32,
   sEMASCntsEpSC501to600       Counter32
}

sEMASCntcEp0to1kms  OBJECT-TYPE
   SYNTAX          Counter32
   MAX-ACCESS      read-only
   STATUS          current
   DESCRIPTION     "SES gets create ESIM profile response from EMA server 
                    in 0-1k ms
                    The applUptime epoch of the application instance 
                    should be used as reference point for this counter."
::= { sEMASCntEntry 2 }

sEMASCntcEp1001to5kms  OBJECT-TYPE
   SYNTAX          Counter32
   MAX-ACCESS      read-only
   STATUS          current
   DESCRIPTION     "SES gets create ESIM profile response from EMA server 
                    in 1001-5k ms
                    The applUptime epoch of the application instance 
                    should be used as reference point for this counter."
::= { sEMASCntEntry 3 }

sEMASCntcEp5001to10kms  OBJECT-TYPE
   SYNTAX          Counter32
   MAX-ACCESS      read-only
   STATUS          current
   DESCRIPTION     "SES gets create ESIM profile response from EMA server 
                    in 5001-10k ms
                    The applUptime epoch of the application instance 
                    should be used as reference point for this counter."
::= { sEMASCntEntry 4 }

sEMASCntcEp10001toTimeoutms  OBJECT-TYPE
   SYNTAX          Counter32
   MAX-ACCESS      read-only
   STATUS          current
   DESCRIPTION     "SES gets create ESIM profile response from EMA server 
                    from 10001 to time out
                    The applUptime epoch of the application instance 
                    should be used as reference point for this counter."
::= { sEMASCntEntry 5 }

sEMASCntcEpOverTimeoutms  OBJECT-TYPE
   SYNTAX          Counter32
   MAX-ACCESS      read-only
   STATUS          current
   DESCRIPTION     "SES gets create ESIM profile response from EMA server 
                    over time out
                    The applUptime epoch of the application instance 
                    should be used as reference point for this counter."
::= { sEMASCntEntry 6 }

sEMASCntcEpSC0to200  OBJECT-TYPE
   SYNTAX          Counter32
   MAX-ACCESS      read-only
   STATUS          current
   DESCRIPTION     "Status code create ESIM profile response in 0-200 
                    from EMA server
                    The applUptime epoch of the application instance 
                    should be used as reference point for this counter."
::= { sEMASCntEntry 7 }

sEMASCntcEpSC201to400  OBJECT-TYPE
   SYNTAX          Counter32
   MAX-ACCESS      read-only
   STATUS          current
   DESCRIPTION     "Status code create ESIM profile response in 201-400 
                    from EMA server
                    The applUptime epoch of the application instance 
                    should be used as reference point for this counter."
::= { sEMASCntEntry 8 }

sEMASCntcEpSC401to404  OBJECT-TYPE
   SYNTAX          Counter32
   MAX-ACCESS      read-only
   STATUS          current
   DESCRIPTION     "Status code create ESIM profile response in 401-404 
                    from EMA server
                    The applUptime epoch of the application instance 
                    should be used as reference point for this counter."
::= { sEMASCntEntry 9 }

sEMASCntcEpSC405to500  OBJECT-TYPE
   SYNTAX          Counter32
   MAX-ACCESS      read-only
   STATUS          current
   DESCRIPTION     "Status code create ESIM profile response in 405-500 
                    from EMA server
                    The applUptime epoch of the application instance 
                    should be used as reference point for this counter."
::= { sEMASCntEntry 10 }

sEMASCntcEpSC501to600  OBJECT-TYPE
   SYNTAX          Counter32
   MAX-ACCESS      read-only
   STATUS          current
   DESCRIPTION     "Status code create ESIM profile response in 501-600 
                    from EMA server
                    The applUptime epoch of the application instance 
                    should be used as reference point for this counter."
::= { sEMASCntEntry 11 }

sEMASCntdEp0to1kms  OBJECT-TYPE
   SYNTAX          Counter32
   MAX-ACCESS      read-only
   STATUS          current
   DESCRIPTION     "SES gets delete ESIM profile response from EMA server 
                    in 0-1k ms
                    The applUptime epoch of the application instance 
                    should be used as reference point for this counter."
::= { sEMASCntEntry 12 }

sEMASCntdEp1001to5kms  OBJECT-TYPE
   SYNTAX          Counter32
   MAX-ACCESS      read-only
   STATUS          current
   DESCRIPTION     "SES gets delete ESIM profile response from EMA server 
                    in 1001-5k ms
                    The applUptime epoch of the application instance 
                    should be used as reference point for this counter."
::= { sEMASCntEntry 13 }

sEMASCntdEp5001to10kms  OBJECT-TYPE
   SYNTAX          Counter32
   MAX-ACCESS      read-only
   STATUS          current
   DESCRIPTION     "SES gets delete ESIM profile response from EMA server 
                    in 5001-10k ms
                    The applUptime epoch of the application instance 
                    should be used as reference point for this counter."
::= { sEMASCntEntry 14 }

sEMASCntdEp10001toTimeoutms  OBJECT-TYPE
   SYNTAX          Counter32
   MAX-ACCESS      read-only
   STATUS          current
   DESCRIPTION     "SES gets delete ESIM profile response from EMA server 
                    from 10001 to time out
                    The applUptime epoch of the application instance 
                    should be used as reference point for this counter."
::= { sEMASCntEntry 15 }

sEMASCntdEpOverTimeoutms  OBJECT-TYPE
   SYNTAX          Counter32
   MAX-ACCESS      read-only
   STATUS          current
   DESCRIPTION     "SES gets delete ESIM profile response from EMA server 
                    over time out
                    The applUptime epoch of the application instance 
                    should be used as reference point for this counter."
::= { sEMASCntEntry 16 }

sEMASCntdEpSC0to200  OBJECT-TYPE
   SYNTAX          Counter32
   MAX-ACCESS      read-only
   STATUS          current
   DESCRIPTION     "Status code delete ESIM profile response in 0-200 
                    from EMA server
                    The applUptime epoch of the application instance 
                    should be used as reference point for this counter."
::= { sEMASCntEntry 17 }

sEMASCntdEpSC201to400  OBJECT-TYPE
   SYNTAX          Counter32
   MAX-ACCESS      read-only
   STATUS          current
   DESCRIPTION     "Status code delete ESIM profile response in 201-400 
                    from EMA server
                    The applUptime epoch of the application instance 
                    should be used as reference point for this counter."
::= { sEMASCntEntry 18 }

sEMASCntdEpSC401to404  OBJECT-TYPE
   SYNTAX          Counter32
   MAX-ACCESS      read-only
   STATUS          current
   DESCRIPTION     "Status code delete ESIM profile response in 401-404 
                    from EMA server
                    The applUptime epoch of the application instance 
                    should be used as reference point for this counter."
::= { sEMASCntEntry 19 }

sEMASCntdEpSC405to500  OBJECT-TYPE
   SYNTAX          Counter32
   MAX-ACCESS      read-only
   STATUS          current
   DESCRIPTION     "Status code delete ESIM profile response in 405-500 
                    from EMA server
                    The applUptime epoch of the application instance 
                    should be used as reference point for this counter."
::= { sEMASCntEntry 20 }

sEMASCntdEpSC501to600  OBJECT-TYPE
   SYNTAX          Counter32
   MAX-ACCESS      read-only
   STATUS          current
   DESCRIPTION     "Status code delete ESIM profile response in 501-600 
                    from EMA server
                    The applUptime epoch of the application instance 
                    should be used as reference point for this counter."
::= { sEMASCntEntry 21 }

sEMASCntsEp0to1kms  OBJECT-TYPE
   SYNTAX          Counter32
   MAX-ACCESS      read-only
   STATUS          current
   DESCRIPTION     "SES gets set ESIM profile response from EMA server in 
                    0-1k ms
                    The applUptime epoch of the application instance 
                    should be used as reference point for this counter."
::= { sEMASCntEntry 22 }

sEMASCntsEp1001to5kms  OBJECT-TYPE
   SYNTAX          Counter32
   MAX-ACCESS      read-only
   STATUS          current
   DESCRIPTION     "SES gets set ESIM profile response from EMA server in 
                    1001-5k ms
                    The applUptime epoch of the application instance 
                    should be used as reference point for this counter."
::= { sEMASCntEntry 23 }

sEMASCntsEp5001to10kms  OBJECT-TYPE
   SYNTAX          Counter32
   MAX-ACCESS      read-only
   STATUS          current
   DESCRIPTION     "SES gets set ESIM profile response from EMA server in 
                    5001-10k ms
                    The applUptime epoch of the application instance 
                    should be used as reference point for this counter."
::= { sEMASCntEntry 24 }

sEMASCntsEp10001toTimeoutms  OBJECT-TYPE
   SYNTAX          Counter32
   MAX-ACCESS      read-only
   STATUS          current
   DESCRIPTION     "SES gets set ESIM profile response from EMA server 
                    from 10001 to time out
                    The applUptime epoch of the application instance 
                    should be used as reference point for this counter."
::= { sEMASCntEntry 25 }

sEMASCntsEpOverTimeoutms  OBJECT-TYPE
   SYNTAX          Counter32
   MAX-ACCESS      read-only
   STATUS          current
   DESCRIPTION     "SES gets set ESIM profile response from EMA server 
                    over time out
                    The applUptime epoch of the application instance 
                    should be used as reference point for this counter."
::= { sEMASCntEntry 26 }

sEMASCntsEpSC0to200  OBJECT-TYPE
   SYNTAX          Counter32
   MAX-ACCESS      read-only
   STATUS          current
   DESCRIPTION     "Status code set ESIM profile response in 0-200 from 
                    EMA server
                    The applUptime epoch of the application instance 
                    should be used as reference point for this counter."
::= { sEMASCntEntry 27 }

sEMASCntsEpSC201to400  OBJECT-TYPE
   SYNTAX          Counter32
   MAX-ACCESS      read-only
   STATUS          current
   DESCRIPTION     "Status code set ESIM profile response in 201-400 from 
                    EMA server
                    The applUptime epoch of the application instance 
                    should be used as reference point for this counter."
::= { sEMASCntEntry 28 }

sEMASCntsEpSC401to404  OBJECT-TYPE
   SYNTAX          Counter32
   MAX-ACCESS      read-only
   STATUS          current
   DESCRIPTION     "Status code set ESIM profile response in 401-404 from 
                    EMA server
                    The applUptime epoch of the application instance 
                    should be used as reference point for this counter."
::= { sEMASCntEntry 29 }

sEMASCntsEpSC405to500  OBJECT-TYPE
   SYNTAX          Counter32
   MAX-ACCESS      read-only
   STATUS          current
   DESCRIPTION     "Status code set ESIM profile response in 405-500 from 
                    EMA server
                    The applUptime epoch of the application instance 
                    should be used as reference point for this counter."
::= { sEMASCntEntry 30 }

sEMASCntsEpSC501to600  OBJECT-TYPE
   SYNTAX          Counter32
   MAX-ACCESS      read-only
   STATUS          current
   DESCRIPTION     "Status code set ESIM profile response in 501-600 from 
                    EMA server
                    The applUptime epoch of the application instance 
                    should be used as reference point for this counter."
::= { sEMASCntEntry 31 }

sEMASAlarmTable OBJECT-TYPE
   SYNTAX          SEQUENCE OF SEMASAlarmEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sEMASAlarm 1 } 

sEMASAlarmEntry OBJECT-TYPE
   SYNTAX          SEMASAlarmEntry
   MAX-ACCESS      not-accessible
   STATUS          current
   DESCRIPTION     "Alarm for SES connects EMA server failed."
   INDEX { applIndex }
::= { sEMASAlarmTable  1 }

SEMASAlarmEntry  ::= SEQUENCE
{
   sEMASAlarmFailedAlarm ItuPerceivedSeverity
}

sEMASAlarmFailedAlarm  OBJECT-TYPE
   SYNTAX          ItuPerceivedSeverity
   MAX-ACCESS      read-only
   STATUS          current
   DESCRIPTION     "SES Connects EMA Server Failed or EMA Server 
                    Configuration Error."
::= { sEMASAlarmEntry 2 }

sQISCntTable OBJECT-TYPE
   SYNTAX          SEQUENCE OF SQISCntEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sQISCnt 1 } 

sQISCntEntry OBJECT-TYPE
   SYNTAX          SQISCntEntry
   MAX-ACCESS      not-accessible
   STATUS          current
   DESCRIPTION     "Query IMSI Server Response Counters"
   INDEX { applIndex }
::= { sQISCntTable  1 }

SQISCntEntry  ::= SEQUENCE
{
   sQISCntqIbI0to1kms          Counter32,
   sQISCntqIbI1001to5kms       Counter32,
   sQISCntqIbI5001to10kms      Counter32,
   sQISCntqIbI10001toTimeoutms Counter32,
   sQISCntqIbIOverTimeoutms    Counter32,
   sQISCntqIbISC0to200         Counter32,
   sQISCntqIbISC201to400       Counter32,
   sQISCntqIbISC401to404       Counter32,
   sQISCntqIbISC405to500       Counter32,
   sQISCntqIbISC501to600       Counter32
}

sQISCntqIbI0to1kms  OBJECT-TYPE
   SYNTAX          Counter32
   MAX-ACCESS      read-only
   STATUS          current
   DESCRIPTION     "SES gets query IMSI by ICCID response from Query IMSI 
                    server in 0-1k ms
                    The applUptime epoch of the application instance 
                    should be used as reference point for this counter."
::= { sQISCntEntry 2 }

sQISCntqIbI1001to5kms  OBJECT-TYPE
   SYNTAX          Counter32
   MAX-ACCESS      read-only
   STATUS          current
   DESCRIPTION     "SES gets query IMSI by ICCID response from Query IMSI 
                    server in 1001-5k ms
                    The applUptime epoch of the application instance 
                    should be used as reference point for this counter."
::= { sQISCntEntry 3 }

sQISCntqIbI5001to10kms  OBJECT-TYPE
   SYNTAX          Counter32
   MAX-ACCESS      read-only
   STATUS          current
   DESCRIPTION     "SES gets query IMSI by ICCID response from Query IMSI 
                    server in 5001-10k ms
                    The applUptime epoch of the application instance 
                    should be used as reference point for this counter."
::= { sQISCntEntry 4 }

sQISCntqIbI10001toTimeoutms  OBJECT-TYPE
   SYNTAX          Counter32
   MAX-ACCESS      read-only
   STATUS          current
   DESCRIPTION     "SES gets query IMSI by ICCID response from Query IMSI 
                    server from 10001 to time out
                    The applUptime epoch of the application instance 
                    should be used as reference point for this counter."
::= { sQISCntEntry 5 }

sQISCntqIbIOverTimeoutms  OBJECT-TYPE
   SYNTAX          Counter32
   MAX-ACCESS      read-only
   STATUS          current
   DESCRIPTION     "SES gets query IMSI by ICCID response from Query IMSI 
                    server over time out
                    The applUptime epoch of the application instance 
                    should be used as reference point for this counter."
::= { sQISCntEntry 6 }

sQISCntqIbISC0to200  OBJECT-TYPE
   SYNTAX          Counter32
   MAX-ACCESS      read-only
   STATUS          current
   DESCRIPTION     "Status code query IMSI by ICCID response in 0-200 
                    from Query IMSI server
                    The applUptime epoch of the application instance 
                    should be used as reference point for this counter."
::= { sQISCntEntry 7 }

sQISCntqIbISC201to400  OBJECT-TYPE
   SYNTAX          Counter32
   MAX-ACCESS      read-only
   STATUS          current
   DESCRIPTION     "Status code query IMSI by ICCID response in 201-400 
                    from Query IMSI server
                    The applUptime epoch of the application instance 
                    should be used as reference point for this counter."
::= { sQISCntEntry 8 }

sQISCntqIbISC401to404  OBJECT-TYPE
   SYNTAX          Counter32
   MAX-ACCESS      read-only
   STATUS          current
   DESCRIPTION     "Status code query IMSI by ICCID response in 401-404 
                    from Query IMSI server
                    The applUptime epoch of the application instance 
                    should be used as reference point for this counter."
::= { sQISCntEntry 9 }

sQISCntqIbISC405to500  OBJECT-TYPE
   SYNTAX          Counter32
   MAX-ACCESS      read-only
   STATUS          current
   DESCRIPTION     "Status code query IMSI by ICCID response in 405-500 
                    from Query IMSI server
                    The applUptime epoch of the application instance 
                    should be used as reference point for this counter."
::= { sQISCntEntry 10 }

sQISCntqIbISC501to600  OBJECT-TYPE
   SYNTAX          Counter32
   MAX-ACCESS      read-only
   STATUS          current
   DESCRIPTION     "Status code query IMSI by ICCID response in 501-600 
                    from Query IMSI server
                    The applUptime epoch of the application instance 
                    should be used as reference point for this counter."
::= { sQISCntEntry 11 }

sQISAlarmTable OBJECT-TYPE
   SYNTAX          SEQUENCE OF SQISAlarmEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sQISAlarm 1 } 

sQISAlarmEntry OBJECT-TYPE
   SYNTAX          SQISAlarmEntry
   MAX-ACCESS      not-accessible
   STATUS          current
   DESCRIPTION     "Alarm for SES connects Query IMSI server failed."
   INDEX { applIndex }
::= { sQISAlarmTable  1 }

SQISAlarmEntry  ::= SEQUENCE
{
   sQISAlarmFailedAlarm ItuPerceivedSeverity
}

sQISAlarmFailedAlarm  OBJECT-TYPE
   SYNTAX          ItuPerceivedSeverity
   MAX-ACCESS      read-only
   STATUS          current
   DESCRIPTION     "SES Connects Query IMSI Server Failed or Query IMSI 
                    Server Configuration Error."
::= { sQISAlarmEntry 2 }

sAMSCntTable OBJECT-TYPE
   SYNTAX          SEQUENCE OF SAMSCntEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sAMSCnt 1 } 

sAMSCntEntry OBJECT-TYPE
   SYNTAX          SAMSCntEntry
   MAX-ACCESS      not-accessible
   STATUS          current
   DESCRIPTION     "Allocate MSISDN Server Response Counters"
   INDEX { applIndex }
::= { sAMSCntTable  1 }

SAMSCntEntry  ::= SEQUENCE
{
   sAMSCntaMbI0to1kms          Counter32,
   sAMSCntaMbI1001to5kms       Counter32,
   sAMSCntaMbI5001to10kms      Counter32,
   sAMSCntaMbI10001toTimeoutms Counter32,
   sAMSCntaMbIOverTimeoutms    Counter32,
   sAMSCntaMbISC0to200         Counter32,
   sAMSCntaMbISC201to400       Counter32,
   sAMSCntaMbISC401to404       Counter32,
   sAMSCntaMbISC405to500       Counter32,
   sAMSCntaMbISC501to600       Counter32
}

sAMSCntaMbI0to1kms  OBJECT-TYPE
   SYNTAX          Counter32
   MAX-ACCESS      read-only
   STATUS          current
   DESCRIPTION     "SES gets allocate MSISDN by IMSI response from 
                    Allocate MSISDN server in 0-1k ms
                    The applUptime epoch of the application instance 
                    should be used as reference point for this counter."
::= { sAMSCntEntry 2 }

sAMSCntaMbI1001to5kms  OBJECT-TYPE
   SYNTAX          Counter32
   MAX-ACCESS      read-only
   STATUS          current
   DESCRIPTION     "SES gets allocate MSISDN by IMSI response from 
                    Allocate MSISDN server in 1001-5k ms
                    The applUptime epoch of the application instance 
                    should be used as reference point for this counter."
::= { sAMSCntEntry 3 }

sAMSCntaMbI5001to10kms  OBJECT-TYPE
   SYNTAX          Counter32
   MAX-ACCESS      read-only
   STATUS          current
   DESCRIPTION     "SES gets allocate MSISDN by IMSI response from 
                    Allocate MSISDN server in 5001-10k ms
                    The applUptime epoch of the application instance 
                    should be used as reference point for this counter."
::= { sAMSCntEntry 4 }

sAMSCntaMbI10001toTimeoutms  OBJECT-TYPE
   SYNTAX          Counter32
   MAX-ACCESS      read-only
   STATUS          current
   DESCRIPTION     "SES gets allocate MSISDN by IMSI response from 
                    Allocate MSISDN server from 10001 to time out
                    The applUptime epoch of the application instance 
                    should be used as reference point for this counter."
::= { sAMSCntEntry 5 }

sAMSCntaMbIOverTimeoutms  OBJECT-TYPE
   SYNTAX          Counter32
   MAX-ACCESS      read-only
   STATUS          current
   DESCRIPTION     "SES gets allocate MSISDN by IMSI response from 
                    Allocate MSISDN server over time out
                    The applUptime epoch of the application instance 
                    should be used as reference point for this counter."
::= { sAMSCntEntry 6 }

sAMSCntaMbISC0to200  OBJECT-TYPE
   SYNTAX          Counter32
   MAX-ACCESS      read-only
   STATUS          current
   DESCRIPTION     "Status code allocate MSISDN by IMSI response in 0-200 
                    from Allocate MSISDN server
                    The applUptime epoch of the application instance 
                    should be used as reference point for this counter."
::= { sAMSCntEntry 7 }

sAMSCntaMbISC201to400  OBJECT-TYPE
   SYNTAX          Counter32
   MAX-ACCESS      read-only
   STATUS          current
   DESCRIPTION     "Status code allocate MSISDN by IMSI response in 
                    201-400 from Allocate MSISDN server
                    The applUptime epoch of the application instance 
                    should be used as reference point for this counter."
::= { sAMSCntEntry 8 }

sAMSCntaMbISC401to404  OBJECT-TYPE
   SYNTAX          Counter32
   MAX-ACCESS      read-only
   STATUS          current
   DESCRIPTION     "Status code allocate MSISDN by IMSI response in 
                    401-404 from Allocate MSISDN server
                    The applUptime epoch of the application instance 
                    should be used as reference point for this counter."
::= { sAMSCntEntry 9 }

sAMSCntaMbISC405to500  OBJECT-TYPE
   SYNTAX          Counter32
   MAX-ACCESS      read-only
   STATUS          current
   DESCRIPTION     "Status code allocate MSISDN by IMSI response in 
                    405-500 from Allocate MSISDN server
                    The applUptime epoch of the application instance 
                    should be used as reference point for this counter."
::= { sAMSCntEntry 10 }

sAMSCntaMbISC501to600  OBJECT-TYPE
   SYNTAX          Counter32
   MAX-ACCESS      read-only
   STATUS          current
   DESCRIPTION     "Status code allocate MSISDN by IMSI response in 
                    501-600 from Allocate MSISDN server
                    The applUptime epoch of the application instance 
                    should be used as reference point for this counter."
::= { sAMSCntEntry 11 }

sAMSAlarmTable OBJECT-TYPE
   SYNTAX          SEQUENCE OF SAMSAlarmEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sAMSAlarm 1 } 

sAMSAlarmEntry OBJECT-TYPE
   SYNTAX          SAMSAlarmEntry
   MAX-ACCESS      not-accessible
   STATUS          current
   DESCRIPTION     "Alarm for SES connects Allocate MSISDN server failed."
   INDEX { applIndex }
::= { sAMSAlarmTable  1 }

SAMSAlarmEntry  ::= SEQUENCE
{
   sAMSAlarmFailedAlarm ItuPerceivedSeverity
}

sAMSAlarmFailedAlarm  OBJECT-TYPE
   SYNTAX          ItuPerceivedSeverity
   MAX-ACCESS      read-only
   STATUS          current
   DESCRIPTION     "SES Connects Allocate MSISDN Server Failed or 
                    Allocate MSISDN Server Configuration Error."
::= { sAMSAlarmEntry 2 }

sRMSCntTable OBJECT-TYPE
   SYNTAX          SEQUENCE OF SRMSCntEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sRMSCnt 1 } 

sRMSCntEntry OBJECT-TYPE
   SYNTAX          SRMSCntEntry
   MAX-ACCESS      not-accessible
   STATUS          current
   DESCRIPTION     "Release MSISDN Server Response Counters"
   INDEX { applIndex }
::= { sRMSCntTable  1 }

SRMSCntEntry  ::= SEQUENCE
{
   sRMSCntrMbI0to1kms          Counter32,
   sRMSCntrMbI1001to5kms       Counter32,
   sRMSCntrMbI5001to10kms      Counter32,
   sRMSCntrMbI10001toTimeoutms Counter32,
   sRMSCntrMbIOverTimeoutms    Counter32,
   sRMSCntrMbISC0to200         Counter32,
   sRMSCntrMbISC201to400       Counter32,
   sRMSCntrMbISC401to404       Counter32,
   sRMSCntrMbISC405to500       Counter32,
   sRMSCntrMbISC501to600       Counter32
}

sRMSCntrMbI0to1kms  OBJECT-TYPE
   SYNTAX          Counter32
   MAX-ACCESS      read-only
   STATUS          current
   DESCRIPTION     "SES gets release MSISDN by IMSI response from Release 
                    MSISDN server in 0-1k ms
                    The applUptime epoch of the application instance 
                    should be used as reference point for this counter."
::= { sRMSCntEntry 2 }

sRMSCntrMbI1001to5kms  OBJECT-TYPE
   SYNTAX          Counter32
   MAX-ACCESS      read-only
   STATUS          current
   DESCRIPTION     "SES gets release MSISDN by IMSI response from Release 
                    MSISDN server in 1001-5k ms
                    The applUptime epoch of the application instance 
                    should be used as reference point for this counter."
::= { sRMSCntEntry 3 }

sRMSCntrMbI5001to10kms  OBJECT-TYPE
   SYNTAX          Counter32
   MAX-ACCESS      read-only
   STATUS          current
   DESCRIPTION     "SES gets release MSISDN by IMSI response from Release 
                    MSISDN server in 5001-10k ms
                    The applUptime epoch of the application instance 
                    should be used as reference point for this counter."
::= { sRMSCntEntry 4 }

sRMSCntrMbI10001toTimeoutms  OBJECT-TYPE
   SYNTAX          Counter32
   MAX-ACCESS      read-only
   STATUS          current
   DESCRIPTION     "SES gets release MSISDN by IMSI response from Release 
                    MSISDN server from 10001 to time out
                    The applUptime epoch of the application instance 
                    should be used as reference point for this counter."
::= { sRMSCntEntry 5 }

sRMSCntrMbIOverTimeoutms  OBJECT-TYPE
   SYNTAX          Counter32
   MAX-ACCESS      read-only
   STATUS          current
   DESCRIPTION     "SES gets release MSISDN by IMSI response from Release 
                    MSISDN server over time out
                    The applUptime epoch of the application instance 
                    should be used as reference point for this counter."
::= { sRMSCntEntry 6 }

sRMSCntrMbISC0to200  OBJECT-TYPE
   SYNTAX          Counter32
   MAX-ACCESS      read-only
   STATUS          current
   DESCRIPTION     "Status code release MSISDN by IMSI response in 0-200 
                    from Release MSISDN server
                    The applUptime epoch of the application instance 
                    should be used as reference point for this counter."
::= { sRMSCntEntry 7 }

sRMSCntrMbISC201to400  OBJECT-TYPE
   SYNTAX          Counter32
   MAX-ACCESS      read-only
   STATUS          current
   DESCRIPTION     "Status code release MSISDN by IMSI response in 
                    201-400 from Release MSISDN server
                    The applUptime epoch of the application instance 
                    should be used as reference point for this counter."
::= { sRMSCntEntry 8 }

sRMSCntrMbISC401to404  OBJECT-TYPE
   SYNTAX          Counter32
   MAX-ACCESS      read-only
   STATUS          current
   DESCRIPTION     "Status code release MSISDN by IMSI response in 
                    401-404 from Release MSISDN server
                    The applUptime epoch of the application instance 
                    should be used as reference point for this counter."
::= { sRMSCntEntry 9 }

sRMSCntrMbISC405to500  OBJECT-TYPE
   SYNTAX          Counter32
   MAX-ACCESS      read-only
   STATUS          current
   DESCRIPTION     "Status code release MSISDN by IMSI response in 
                    405-500 from Release MSISDN server
                    The applUptime epoch of the application instance 
                    should be used as reference point for this counter."
::= { sRMSCntEntry 10 }

sRMSCntrMbISC501to600  OBJECT-TYPE
   SYNTAX          Counter32
   MAX-ACCESS      read-only
   STATUS          current
   DESCRIPTION     "Status code release MSISDN by IMSI response in 
                    501-600 from Release MSISDN server
                    The applUptime epoch of the application instance 
                    should be used as reference point for this counter."
::= { sRMSCntEntry 11 }

sRMSAlarmTable OBJECT-TYPE
   SYNTAX          SEQUENCE OF SRMSAlarmEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sRMSAlarm 1 } 

sRMSAlarmEntry OBJECT-TYPE
   SYNTAX          SRMSAlarmEntry
   MAX-ACCESS      not-accessible
   STATUS          current
   DESCRIPTION     "Alarm for SES connects Release MSISDN server failed."
   INDEX { applIndex }
::= { sRMSAlarmTable  1 }

SRMSAlarmEntry  ::= SEQUENCE
{
   sRMSAlarmFailedAlarm ItuPerceivedSeverity
}

sRMSAlarmFailedAlarm  OBJECT-TYPE
   SYNTAX          ItuPerceivedSeverity
   MAX-ACCESS      read-only
   STATUS          current
   DESCRIPTION     "SES Connects Release MSISDN Server Failed or Release 
                    MSISDN Server Configuration Error."
::= { sRMSAlarmEntry 2 }

sCANCELPSCntTable OBJECT-TYPE
   SYNTAX          SEQUENCE OF SCANCELPSCntEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sCANCELPSCnt 1 } 

sCANCELPSCntEntry OBJECT-TYPE
   SYNTAX          SCANCELPSCntEntry
   MAX-ACCESS      not-accessible
   STATUS          current
   DESCRIPTION     "Cancel Plan Server Response Counters"
   INDEX { applIndex }
::= { sCANCELPSCntTable  1 }

SCANCELPSCntEntry  ::= SEQUENCE
{
   sCANCELPSCntCp0to1kms          Counter32,
   sCANCELPSCntCp1001to5kms       Counter32,
   sCANCELPSCntCp5001to10kms      Counter32,
   sCANCELPSCntCp10001toTimeoutms Counter32,
   sCANCELPSCntCpOverTimeoutms    Counter32,
   sCANCELPSCntCpSC0to200         Counter32,
   sCANCELPSCntCpSC201to400       Counter32,
   sCANCELPSCntCpSC401to404       Counter32,
   sCANCELPSCntCpSC405to500       Counter32,
   sCANCELPSCntCpSC501to600       Counter32
}

sCANCELPSCntCp0to1kms  OBJECT-TYPE
   SYNTAX          Counter32
   MAX-ACCESS      read-only
   STATUS          current
   DESCRIPTION     "SES gets Cancel plan response from Cancel Plan server 
                    in 0-1k ms
                    The applUptime epoch of the application instance 
                    should be used as reference point for this counter."
::= { sCANCELPSCntEntry 2 }

sCANCELPSCntCp1001to5kms  OBJECT-TYPE
   SYNTAX          Counter32
   MAX-ACCESS      read-only
   STATUS          current
   DESCRIPTION     "SES gets Cancel plan response from Cancel Plan server 
                    in 1001-5k ms
                    The applUptime epoch of the application instance 
                    should be used as reference point for this counter."
::= { sCANCELPSCntEntry 3 }

sCANCELPSCntCp5001to10kms  OBJECT-TYPE
   SYNTAX          Counter32
   MAX-ACCESS      read-only
   STATUS          current
   DESCRIPTION     "SES gets Cancel plan response from Cancel Plan server 
                    in 5001-10k ms
                    The applUptime epoch of the application instance 
                    should be used as reference point for this counter."
::= { sCANCELPSCntEntry 4 }

sCANCELPSCntCp10001toTimeoutms  OBJECT-TYPE
   SYNTAX          Counter32
   MAX-ACCESS      read-only
   STATUS          current
   DESCRIPTION     "SES gets Cancel plan response from Cancel Plan server 
                    from 10001 to time out
                    The applUptime epoch of the application instance 
                    should be used as reference point for this counter."
::= { sCANCELPSCntEntry 5 }

sCANCELPSCntCpOverTimeoutms  OBJECT-TYPE
   SYNTAX          Counter32
   MAX-ACCESS      read-only
   STATUS          current
   DESCRIPTION     "SES gets Cancel plan response from Cancel Plan server 
                    over time out
                    The applUptime epoch of the application instance 
                    should be used as reference point for this counter."
::= { sCANCELPSCntEntry 6 }

sCANCELPSCntCpSC0to200  OBJECT-TYPE
   SYNTAX          Counter32
   MAX-ACCESS      read-only
   STATUS          current
   DESCRIPTION     "Status code Cancel plan response in 0-200 from Cancel 
                    Plan server
                    The applUptime epoch of the application instance 
                    should be used as reference point for this counter."
::= { sCANCELPSCntEntry 7 }

sCANCELPSCntCpSC201to400  OBJECT-TYPE
   SYNTAX          Counter32
   MAX-ACCESS      read-only
   STATUS          current
   DESCRIPTION     "Status code Cancel plan response in 201-400 from 
                    Cancel Plan server
                    The applUptime epoch of the application instance 
                    should be used as reference point for this counter."
::= { sCANCELPSCntEntry 8 }

sCANCELPSCntCpSC401to404  OBJECT-TYPE
   SYNTAX          Counter32
   MAX-ACCESS      read-only
   STATUS          current
   DESCRIPTION     "Status code Cancel plan response in 401-404 from 
                    Cancel Plan server
                    The applUptime epoch of the application instance 
                    should be used as reference point for this counter."
::= { sCANCELPSCntEntry 9 }

sCANCELPSCntCpSC405to500  OBJECT-TYPE
   SYNTAX          Counter32
   MAX-ACCESS      read-only
   STATUS          current
   DESCRIPTION     "Status code Cancel plan response in 405-500 from 
                    Cancel Plan server
                    The applUptime epoch of the application instance 
                    should be used as reference point for this counter."
::= { sCANCELPSCntEntry 10 }

sCANCELPSCntCpSC501to600  OBJECT-TYPE
   SYNTAX          Counter32
   MAX-ACCESS      read-only
   STATUS          current
   DESCRIPTION     "Status code Cancel plan response in 501-600 from 
                    Cancel Plan server
                    The applUptime epoch of the application instance 
                    should be used as reference point for this counter."
::= { sCANCELPSCntEntry 11 }

sCANCELPSAlarmTable OBJECT-TYPE
   SYNTAX          SEQUENCE OF SCANCELPSAlarmEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sCANCELPSAlarm 1 } 

sCANCELPSAlarmEntry OBJECT-TYPE
   SYNTAX          SCANCELPSAlarmEntry
   MAX-ACCESS      not-accessible
   STATUS          current
   DESCRIPTION     "Alarm for SES connects Cancel Plan server failed."
   INDEX { applIndex }
::= { sCANCELPSAlarmTable  1 }

SCANCELPSAlarmEntry  ::= SEQUENCE
{
   sCANCELPSAlarmFailedAlarm ItuPerceivedSeverity
}

sCANCELPSAlarmFailedAlarm  OBJECT-TYPE
   SYNTAX          ItuPerceivedSeverity
   MAX-ACCESS      read-only
   STATUS          current
   DESCRIPTION     "SES Connects Cancel Plan Server Failed or Cancel Plan 
                    Server Configuration Error."
::= { sCANCELPSAlarmEntry 2 }

sROAMINGSCntTable OBJECT-TYPE
   SYNTAX          SEQUENCE OF SROAMINGSCntEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sROAMINGSCnt 1 } 

sROAMINGSCntEntry OBJECT-TYPE
   SYNTAX          SROAMINGSCntEntry
   MAX-ACCESS      not-accessible
   STATUS          current
   DESCRIPTION     "Roaming Server Response Counters"
   INDEX { applIndex }
::= { sROAMINGSCntTable  1 }

SROAMINGSCntEntry  ::= SEQUENCE
{
   sROAMINGSCnt0to1kms          Counter32,
   sROAMINGSCnt1001to5kms       Counter32,
   sROAMINGSCnt5001to10kms      Counter32,
   sROAMINGSCnt10001toTimeoutms Counter32,
   sROAMINGSCntOverTimeoutms    Counter32,
   sROAMINGSCntSC0to200         Counter32,
   sROAMINGSCntSC201to400       Counter32,
   sROAMINGSCntSC401to404       Counter32,
   sROAMINGSCntSC405to500       Counter32,
   sROAMINGSCntSC501to600       Counter32
}

sROAMINGSCnt0to1kms  OBJECT-TYPE
   SYNTAX          Counter32
   MAX-ACCESS      read-only
   STATUS          current
   DESCRIPTION     "SES gets roaming response from roaming server in 0-1k 
                    ms
                    The applUptime epoch of the application instance 
                    should be used as reference point for this counter."
::= { sROAMINGSCntEntry 2 }

sROAMINGSCnt1001to5kms  OBJECT-TYPE
   SYNTAX          Counter32
   MAX-ACCESS      read-only
   STATUS          current
   DESCRIPTION     "SES gets roaming response from roaming server in 
                    1001-5k ms
                    The applUptime epoch of the application instance 
                    should be used as reference point for this counter."
::= { sROAMINGSCntEntry 3 }

sROAMINGSCnt5001to10kms  OBJECT-TYPE
   SYNTAX          Counter32
   MAX-ACCESS      read-only
   STATUS          current
   DESCRIPTION     "SES gets roaming response from roaming server in 
                    5001-10k ms
                    The applUptime epoch of the application instance 
                    should be used as reference point for this counter."
::= { sROAMINGSCntEntry 4 }

sROAMINGSCnt10001toTimeoutms  OBJECT-TYPE
   SYNTAX          Counter32
   MAX-ACCESS      read-only
   STATUS          current
   DESCRIPTION     "SES gets roaming response from roaming server from 
                    10001 to time out
                    The applUptime epoch of the application instance 
                    should be used as reference point for this counter."
::= { sROAMINGSCntEntry 5 }

sROAMINGSCntOverTimeoutms  OBJECT-TYPE
   SYNTAX          Counter32
   MAX-ACCESS      read-only
   STATUS          current
   DESCRIPTION     "SES gets roaming response from roaming server over 
                    time out
                    The applUptime epoch of the application instance 
                    should be used as reference point for this counter."
::= { sROAMINGSCntEntry 6 }

sROAMINGSCntSC0to200  OBJECT-TYPE
   SYNTAX          Counter32
   MAX-ACCESS      read-only
   STATUS          current
   DESCRIPTION     "Status code roaming response in 0-200 from roaming 
                    server
                    The applUptime epoch of the application instance 
                    should be used as reference point for this counter."
::= { sROAMINGSCntEntry 7 }

sROAMINGSCntSC201to400  OBJECT-TYPE
   SYNTAX          Counter32
   MAX-ACCESS      read-only
   STATUS          current
   DESCRIPTION     "Status code roaming response in 201-400 from roaming 
                    server
                    The applUptime epoch of the application instance 
                    should be used as reference point for this counter."
::= { sROAMINGSCntEntry 8 }

sROAMINGSCntSC401to404  OBJECT-TYPE
   SYNTAX          Counter32
   MAX-ACCESS      read-only
   STATUS          current
   DESCRIPTION     "Status code roaming response in 401-404 from roaming 
                    server
                    The applUptime epoch of the application instance 
                    should be used as reference point for this counter."
::= { sROAMINGSCntEntry 9 }

sROAMINGSCntSC405to500  OBJECT-TYPE
   SYNTAX          Counter32
   MAX-ACCESS      read-only
   STATUS          current
   DESCRIPTION     "Status code roaming response in 405-500 from roaming 
                    server
                    The applUptime epoch of the application instance 
                    should be used as reference point for this counter."
::= { sROAMINGSCntEntry 10 }

sROAMINGSCntSC501to600  OBJECT-TYPE
   SYNTAX          Counter32
   MAX-ACCESS      read-only
   STATUS          current
   DESCRIPTION     "Status code roaming response in 501-600 from roaming 
                    server
                    The applUptime epoch of the application instance 
                    should be used as reference point for this counter."
::= { sROAMINGSCntEntry 11 }

sROAMINGSAlarmTable OBJECT-TYPE
   SYNTAX          SEQUENCE OF SROAMINGSAlarmEntry
   MAX-ACCESS      not-accessible
   STATUS          current
   DESCRIPTION     "One entry is created for each application that 
                    contains the pull proxy module(1=Secure Connection Oriented, 
                    2=Secure Connectionless, 3=Connection-Oriented, 
                    4=Connectionless, 5=W-HTTP)."
::= { sROAMINGSAlarm 1 } 

sROAMINGSAlarmEntry OBJECT-TYPE
   SYNTAX          SROAMINGSAlarmEntry
   MAX-ACCESS      not-accessible
   STATUS          current
   DESCRIPTION     "Alarm for SES connects roaming server failed."
   INDEX { applIndex }
::= { sROAMINGSAlarmTable  1 }

SROAMINGSAlarmEntry  ::= SEQUENCE
{
   sROAMINGSAlarmFailedAlarm ItuPerceivedSeverity
}

sROAMINGSAlarmFailedAlarm  OBJECT-TYPE
   SYNTAX          ItuPerceivedSeverity
   MAX-ACCESS      read-only
   STATUS          current
   DESCRIPTION     "SES Connects Roaming Server Failed or Roaming Server 
                    Configuration Error."
::= { sROAMINGSAlarmEntry 2 }

sGSTable OBJECT-TYPE
   SYNTAX          SEQUENCE OF SGSEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sGS 1 } 

sGSEntry OBJECT-TYPE
   SYNTAX          SGSEntry
   MAX-ACCESS      not-accessible
   STATUS          current
   DESCRIPTION     "GetDeviceConfiguration Server Response Counters"
   INDEX { applIndex }
::= { sGSTable  1 }

SGSEntry  ::= SEQUENCE
{
   sGSEN0to1kms           Counter32,
   sGSCntEN1001to5kms     Counter32,
   sGSCntEN5001to10kms    Counter32,
   sGSCntEN10001toTimeout Counter32,
   sGSCntENOverTimeout    Counter32,
   sGSCntSC0to200         Counter32,
   sGSCntSC200to400       Counter32,
   sGSCntSC400to500       Counter32,
   sGSCntSC501to503       Counter32
}

sGSEN0to1kms  OBJECT-TYPE
   SYNTAX          Counter32
   MAX-ACCESS      read-only
   STATUS          current
   DESCRIPTION     "Ses get device configuration response from 
                    GetDeviceConfiguration Server in 0 to 1k ms.
                    The applUptime epoch of the application instance 
                    should be used as reference point for this counter."
::= { sGSEntry 2 }

sGSCntEN1001to5kms  OBJECT-TYPE
   SYNTAX          Counter32
   MAX-ACCESS      read-only
   STATUS          current
   DESCRIPTION     "Ses get device configuration response from 
                    GetDeviceConfiguration Server in 1001 to 5k ms.
                    The applUptime epoch of the application instance 
                    should be used as reference point for this counter."
::= { sGSEntry 3 }

sGSCntEN5001to10kms  OBJECT-TYPE
   SYNTAX          Counter32
   MAX-ACCESS      read-only
   STATUS          current
   DESCRIPTION     "Ses get device configuration response from 
                    GetDeviceConfiguration Server in 5001 to 10k ms.
                    The applUptime epoch of the application instance 
                    should be used as reference point for this counter."
::= { sGSEntry 4 }

sGSCntEN10001toTimeout  OBJECT-TYPE
   SYNTAX          Counter32
   MAX-ACCESS      read-only
   STATUS          current
   DESCRIPTION     "Ses get device configuration response from 
                    GetDeviceConfiguration in 10001 to Timeout.
                    The applUptime epoch of the application instance 
                    should be used as reference point for this counter."
::= { sGSEntry 5 }

sGSCntENOverTimeout  OBJECT-TYPE
   SYNTAX          Counter32
   MAX-ACCESS      read-only
   STATUS          current
   DESCRIPTION     "Ses get device configuration response from 
                    GetDeviceConfiguration Server over Timeout.
                    The applUptime epoch of the application instance 
                    should be used as reference point for this counter."
::= { sGSEntry 6 }

sGSCntSC0to200  OBJECT-TYPE
   SYNTAX          Counter32
   MAX-ACCESS      read-only
   STATUS          current
   DESCRIPTION     "Status code from GetDeviceConfiguration Server in 0 
                    to 200.
                    The applUptime epoch of the application instance 
                    should be used as reference point for this counter."
::= { sGSEntry 22 }

sGSCntSC200to400  OBJECT-TYPE
   SYNTAX          Counter32
   MAX-ACCESS      read-only
   STATUS          current
   DESCRIPTION     "Status code from GetDeviceConfiguration Server in 200 
                    to 400.
                    The applUptime epoch of the application instance 
                    should be used as reference point for this counter."
::= { sGSEntry 23 }

sGSCntSC400to500  OBJECT-TYPE
   SYNTAX          Counter32
   MAX-ACCESS      read-only
   STATUS          current
   DESCRIPTION     "Status code from GetDeviceConfiguration Server in 401 
                    to 501.
                    The applUptime epoch of the application instance 
                    should be used as reference point for this counter."
::= { sGSEntry 24 }

sGSCntSC501to503  OBJECT-TYPE
   SYNTAX          Counter32
   MAX-ACCESS      read-only
   STATUS          current
   DESCRIPTION     "Status code from GetDeviceConfiguration Server in 501 
                    to 503.
                    The applUptime epoch of the application instance 
                    should be used as reference point for this counter."
::= { sGSEntry 25 }

sGSAlarmTable OBJECT-TYPE
   SYNTAX          SEQUENCE OF SGSAlarmEntry
   MAX-ACCESS      not-accessible
   STATUS          current
   DESCRIPTION     "One entry is created for each application that 
                    contains the pull proxy module
                    (1=Secure Connection Oriented, 2=Secure 
                    Connectionless, 3=Connection-Oriented, 4=Connectionless, 5=W-HTTP)."
::= { sGSAlarm 1 } 

sGSAlarmEntry OBJECT-TYPE
   SYNTAX          SGSAlarmEntry
   MAX-ACCESS      not-accessible
   STATUS          current
   DESCRIPTION     "Alarm for SES connects GetDeviceConfiguration server 
                    failed."
   INDEX { applIndex }
::= { sGSAlarmTable  1 }

SGSAlarmEntry  ::= SEQUENCE
{
   sGSAlarmFailedAlarm ItuPerceivedSeverity
}

sGSAlarmFailedAlarm  OBJECT-TYPE
   SYNTAX          ItuPerceivedSeverity
   MAX-ACCESS      read-only
   STATUS          current
   DESCRIPTION     "SES Connects GetDeviceConfiguration server Failed or 
                    GetDeviceConfiguration server Configuration Error."
::= { sGSAlarmEntry 2 }

-- Compliance Statements

responseSesCompliance MODULE-COMPLIANCE
   STATUS          current
   DESCRIPTION     "The compliance statement for response ses."
   MODULE          -- this module
   MANDATORY-GROUPS {responseSesConfGroup}
::= { responseSesPmCompliances 1 }

-- Units of Conformance

responseSesConfGroup OBJECT-GROUP
   OBJECTS { sARCntAIP0to1kms,
             sARCntAIP1001to5kms,
             sARCntAIP5001to10kms,
             sARCntAIP10001toTimeout,
             sARCntAIPOverTimeout,
             sARCntAIA0to1kms,
             sARCntAIA1001to5kms,
             sARCntAIA5001to10kms,
             sARCntAIA10001toTimeout,
             sARCntAIAOverTimeout,
             sARCntAV0to1kms,
             sARCntAV1001to5kms,
             sARCntAV5001to10kms,
             sARCntAV10001toTimeout,
             sARCntAVOverTimeout,
             sARCntAVI0to1kms,
             sARCntAVI1001to5kms,
             sARCntAVI5001to10kms,
             sARCntAVI10001toTimeout,
             sARCntAVIOverTimeout,
             sARCntAVNSV0to1kms,
             sARCntAVNSV1001to5kms,
             sARCntAVNSV5001to10kms,
             sARCntAVNSV10001toTimeout,
             sARCntAVNSVOverTimeout,
             sARCntAIAS0to1kms,
             sARCntAIAS1001to5kms,
             sARCntAIAS5001to10kms,
             sARCntAIAS10001toTimeout,
             sARCntAIASOverTimeout,
             sARCntAA0to1kms,
             sARCntAA1001to5kms,
             sARCntAA5001to10kms,
             sARCntAA10001toTimeout,
             sARCntAAOverTimeout,
             sARCntAS0to1kms,
             sARCntAS1001to5kms,
             sARCntAS5001to10kms,
             sARCntAS10001toTimeout,
             sARCntASOverTimeout,
             sARCntPSAS0to1kms,
             sARCntPSAS1001to5kms,
             sARCntPSAS5001to10kms,
             sARCntPSAS10001toTimeout,
             sARCntPSASOverTimeout,
             sARCntSC0to199,
             sARCntSC200,
             sARCntSC201to299,
             sARCntSC300to399,
             sARCntSC400to499,
             sARCntSC500to599,
             sARAlarmFailAlarm,
             sERCntAV0to1kms,
             sERCntAV1001to5kms,
             sERCntAV5001to10kms,
             sERCntAV10001toTimeout,
             sERCntAVOverTimeout,
             sERCntET0to1kms,
             sERCntET1001to5kms,
             sERCntET5001to10kms,
             sERCntET10001toTimeout,
             sERCntETOverTimeout,
             sERCntMI0to1kms,
             sERCntMI1001to5kms,
             sERCntMI5001to10kms,
             sERCntMI10001toTimeout,
             sERCntMIOverTimeout,
             sERCntIP0to1kms,
             sERCntIP1001to5kms,
             sERCntIP5001to10kms,
             sERCntIP10001toTimeout,
             sERCntIPOverTimeout,
             sERCntIM0to1kms,
             sERCntIM1001to5kms,
             sERCntIM5001to10kms,
             sERCntIM10001toTimeout,
             sERCntIMOverTimeout,
             sERCntDI0to1kms,
             sERCntDI1001to5kms,
             sERCntDI5001to10kms,
             sERCntDI10001toTimeout,
             sERCntDIOverTimeout,
             sERCntSU0to1kms,
             sERCntSU1001to5kms,
             sERCntSU5001to10kms,
             sERCntSU10001toTimeout,
             sERCntSUOverTimeout,
             sERCntSC0to199,
             sERCntSC200,
             sERCntSC201to299,
             sERCntSC300to399,
             sERCntSC400to499,
             sERCntSC500to599,
             sERCntGCI0to1kms,
             sERCntGCI1001to5kms,
             sERCntGCI5001to10kms,
             sERCntGCI10001toTimeout,
             sERCntGCIOverTimeout,
             sERCntGRM0to1kms,
             sERCntGRM1001to5kms,
             sERCntGRM5001to10kms,
             sERCntGRM10001toTimeout,
             sERCntGRMOverTimeout,
             sERCntMO2I0to1kms,
             sERCntMO2I1001to5kms,
             sERCntMO2I5001to10kms,
             sERCntMO2I10001toTimeout,
             sERCntMO2IOverTimeout,
             sERCntCSP0to1kms,
             sERCntCSP1001to5kms,
             sERCntCSP5001to10kms,
             sERCntCSP10001toTimeout,
             sERCntCSPOverTimeout,
             sERAlarmFailedAlarm,
             sTcLocCntTL0to1kms,
             sTcLocCntTL1001to5kms,
             sTcLocCntTL5001to10kms,
             sTcLocCntTL10001toTimeout,
             sTcLocCntTLOverTimeout,
             sTcLocCntSC0to199,
             sTcLocCntSC200,
             sTcLocCntSC201to299,
             sTcLocCntSC300to399,
             sTcLocCntSC400to499,
             sTcLocCntSC500to599,
             sTcLocAlarmFailedAlarm,
             sNSCntNANSE0to1kms,
             sNSCntNANSE1001to5kms,
             sNSCntNANSE5001to10kms,
             sNSCntNANSE10001toTimeout,
             sNSCntNANSEOverTimeout,
             sNSCntNDNSE0to1kms,
             sNSCntNDNSE1001to5kms,
             sNSCntNDNSE5001to10kms,
             sNSCntNDNSE10001toTimeout,
             sNSCntNDNSEOverTimeout,
             sNSCntNDNSD0to1kms,
             sNSCntNDNSD1001to5kms,
             sNSCntNDNSD5001to10kms,
             sNSCntNDNSD10001toTimeout,
             sNSCntNDNSDOverTimeout,
             sNSCntSC0to200,
             sNSCntSC200to201,
             sNSCntSC201to204,
             sNSCntSC204to304,
             sNSCntSC304to400,
             sNSCntSC400to404,
             sNSAlarmFailAlarm,
             sIAMCntIaAT0to1kms,
             sIAMCntIaAT1001to5kms,
             sIAMCntIaAT5001to10kms,
             sIAMCntIaAT10001toTimeout,
             sIAMCntIaATOverTimeout,
             sIAMCntVAT0to1kms,
             sIAMCntVAT1001to5kms,
             sIAMCntVAT5001to10kms,
             sIAMCntVAT10001toTimeout,
             sIAMCntVATOverTimeout,
             sIAMCntQUP0to1kms,
             sIAMCntQUP1001to5kms,
             sIAMCntQUP5001to10kms,
             sIAMCntQUP10001toTimeout,
             sIAMCntQUPOverTimeout,
             sIAMCntSC0to200,
             sIAMCntSC200to400,
             sIAMCntSC400to404,
             sIAMCntSC404to422,
             sIAMCntSC422to500,
             sIAMCntSC500to503,
             sIAMAlarmFailAlarm,
             sPsCntCEN0to1kms,
             sPsCntCEN1001to5kms,
             sPsCntCEN5001to10kms,
             sPsCntCEN10001toTimeout,
             sPsCntCENOverTimeout,
             sPsCntSTE0to1kms,
             sPsCntSTE1001to5kms,
             sPsCntSTE5001to10kms,
             sPsCntSTE10001toTimeout,
             sPsCntSTEOverTimeout,
             sPsCntSC0to199,
             sPsCntSC200,
             sPsCntSC201to299,
             sPsCntSC300to399,
             sPsCntSC400to499,
             sPsCntSC500to599,
             sPsAlarmFailAlarm,
             sExARCntCMDN0to1kms,
             sExARCntCMDN1001to5kms,
             sExARCntCMDN5001to10kms,
             sExARCntCMDN10001toTimeout,
             sExARCntCMDNOverTimeout,
             sExARCntQVSI0to1kms,
             sExARCntQVSI1001to5kms,
             sExARCntQVSI5001to10kms,
             sExARCntQVSI10001toTimeout,
             sExARCntQVSIOverTimeout,
             sExARCntUVSI0to1kms,
             sExARCntUVSI1001to5kms,
             sExARCntUVSI5001to10kms,
             sExARCntUVSI10001toTimeout,
             sExARCntUVSIOverTimeout,
             sExARCntBVSI0to1kms,
             sExARCntBVSI1001to5kms,
             sExARCntBVSI5001to10kms,
             sExARCntBVSI10001toTimeout,
             sExARCntBVSIOverTimeout,
             sExARCntDISI0to1kms,
             sExARCntDISI1001to5kms,
             sExARCntDISI5001to10kms,
             sExARCntDISI10001toTimeout,
             sExARCntDISIOverTimeout,
             sExARCntUISI0to1kms,
             sExARCntUISI1001to5kms,
             sExARCntUISI5001to10kms,
             sExARCntUISI10001toTimeout,
             sExARCntUISIOverTimeout,
             sExARCntCV0to1kms,
             sExARCntCV1001to5kms,
             sExARCntCV5001to10kms,
             sExARCntCV10001toTimeout,
             sExARCntCVOverTimeout,
             sExARCntMC0to1kms,
             sExARCntMC1001to5kms,
             sExARCntMC5001to10kms,
             sExARCntMC10001toTimeout,
             sExARCntMCOverTimeout,
             sExARCntAVS0to1kms,
             sExARCntAVS1001to5kms,
             sExARCntAVS5001to10kms,
             sExARCntAVS10001toTimeout,
             sExARCntAVSOverTimeout,
             sExARCntRVS0to1kms,
             sExARCntRVS1001to5kms,
             sExARCntRVS5001to10kms,
             sExARCntRVS10001toTimeout,
             sExARCntRVSOverTimeout,
             sExARCntRMVS0to1kms,
             sExARCntRMVS1001to5kms,
             sExARCntRMVS5001to10kms,
             sExARCntRMVS10001toTimeout,
             sExARCntRMVSOverTimeout,
             sExARCntQVS0to1kms,
             sExARCntQVS1001to5kms,
             sExARCntQVS5001to10kms,
             sExARCntQVS10001toTimeout,
             sExARCntQVSOverTimeout,
             sExARCntAFNR0to1kms,
             sExARCntAFNR1001to5kms,
             sExARCntAFNR5001to10kms,
             sExARCntAFNR10001toTimeout,
             sExARCntAFNROverTimeout,
             sExIIARCntAQSFGD0to1kms,
             sExIIARCntAQSFGD1001to5kms,
             sExIIARCntAQSFGD5001to10kms,
             sExIIARCntAQSFGD10001toTimeout,
             sExIIARCntAQSFGDOverTimeout,
             sExIIARCntADVS0to1kms,
             sExIIARCntADVS1001to5kms,
             sExIIARCntADVS5001to10kms,
             sExIIARCntADVS10001toTimeout,
             sExIIARCntADVSOverTimeout,
             sExIIARCntALUTIBO0to1kms,
             sExIIARCntALUTIBO1001to5kms,
             sExIIARCntALUTIBO5001to10kms,
             sExIIARCntALUTIBO10001toTimeout,
             sExIIARCntALUTIBOOverTimeout,
             sExIIARCntATIBV0to1kms,
             sExIIARCntATIBV1001to5kms,
             sExIIARCntATIBV5001to10kms,
             sExIIARCntATIBV10001toTimeout,
             sExIIARCntATIBVOverTimeout,
             sExIIARCntADDBO0to1kms,
             sExIIARCntADDBO1001to5kms,
             sExIIARCntADDBO5001to10kms,
             sExIIARCntADDBO10001toTimeout,
             sExIIARCntADDBOOverTimeout,
             sExIIARCntAUIFGD0to1kms,
             sExIIARCntAUIFGD1001to5kms,
             sExIIARCntAUIFGD5001to10kms,
             sExIIARCntAUIFGD10001toTimeout,
             sExIIARCntAUIFGDOverTimeout,
             sExIIARCntAUMFGD0to1kms,
             sExIIARCntAUMFGD1001to5kms,
             sExIIARCntAUMFGD5001to10kms,
             sExIIARCntAUMFGD10001toTimeout,
             sExIIARCntAUMFGDOverTimeout,
             sExIIARCntEUP0to1kms,
             sExIIARCntEUP1001to5kms,
             sExIIARCntEUP5001to10kms,
             sExIIARCntEUP10001toTimeout,
             sExIIARCntEUPOverTimeout,
             sExIIARCntDUP0to1kms,
             sExIIARCntDUP1001to5kms,
             sExIIARCntDUP5001to10kms,
             sExIIARCntDUP10001toTimeout,
             sExIIARCntDUPOverTimeout,
             sExERCntGMI0to1kms,
             sExERCntGMI1001to5kms,
             sExERCntGMI5001to10kms,
             sExERCntGMI10001toTimeout,
             sExERCntGMIOverTimeout,
             sPTSCntPAPT0to1kms,
             sPTSCntPAPT1001to5kms,
             sPTSCntPAPT5001to10kms,
             sPTSCntPAPT10001toTimeout,
             sPTSCntPAPTOverTimeout,
             sPTSCntPDPT0to1kms,
             sPTSCntPDPT1001to5kms,
             sPTSCntPDPT5001to10kms,
             sPTSCntPDPT10001toTimeout,
             sPTSCntPDPTOverTimeout,
             sPTSCntPQPT0to1kms,
             sPTSCntPQPT1001to5kms,
             sPTSCntPQPT5001to10kms,
             sPTSCntPQPT10001toTimeout,
             sPTSCntPQPTOverTimeout,
             sPTSCntPUPT0to1kms,
             sPTSCntPUPT1001to5kms,
             sPTSCntPUPT5001to10kms,
             sPTSCntPUPT10001toTimeout,
             sPTSCntPUPTOverTimeout,
             sPTSCntSC0to200,
             sPTSCntSC200to201,
             sPTSCntSC201to204,
             sPTSCntSC204to304,
             sPTSCntSC304to400,
             sPTSCntSC400to404,
             sPTSAlarmFailAlarm,
             sENSCntEN0to1kms,
             sENSCntEN1001to5kms,
             sENSCntEN5001to10kms,
             sENSCntEN10001toTimeout,
             sENSCntENOverTimeout,
             sENSCntSC0to200,
             sENSCntSC200to400,
             sENSCntSC400to500,
             sENSCntSC501to503,
             sENSAlarmFailedAlarm,
             sCPSCntCPSS0to1kms,
             sCPSCntCPSS1001to5kms,
             sCPSCntCPSS5001to10kms,
             sCPSCntCPSS10001toTimeout,
             sCPSCntCPSSOverTimeout,
             sCPSCntCPSAS0to1kms,
             sCPSCntCPSAS1001to5kms,
             sCPSCntCPSAS5001to10kms,
             sCPSCntCPSAS10001toTimeout,
             sCPSCntCPSASOverTimeout,
             sCPSCntCPSSSC0to200,
             sCPSCntCPSSSC201to400,
             sCPSCntCPSSSC401to500,
             sCPSCntCPSSSC501to600,
             sCPSCntCPSASSC0to200,
             sCPSCntCPSASSC201to400,
             sCPSCntCPSASSC401to500,
             sCPSCntCPSASSC501to600,
             sCPSAlarmFailedAlarm,
             sESIMSCntvd0to1kms,
             sESIMSCntvd1001to5kms,
             sESIMSCntvd5001to10kms,
             sESIMSCntvd10001toTimeoutms,
             sESIMSCntvdOverTimeoutms,
             sESIMSCntvdSC0to200,
             sESIMSCntvdSC201to400,
             sESIMSCntvdSC401to404,
             sESIMSCntvdSC405to500,
             sESIMSCntvdSC501to600,
             sESIMSCntrI0to1kms,
             sESIMSCntrI1001to5kms,
             sESIMSCntrI5001to10kms,
             sESIMSCntrI10001toTimeoutms,
             sESIMSCntrIOverTimeoutms,
             sESIMSCntrISC0to200,
             sESIMSCntrISC201to400,
             sESIMSCntrISC401to404,
             sESIMSCntrISC405to500,
             sESIMSCntrISC501to600,
             sESIMSCnturI0to1kms,
             sESIMSCnturI1001to5kms,
             sESIMSCnturI5001to10kms,
             sESIMSCnturI10001toTimeoutms,
             sESIMSCnturIOverTimeoutms,
             sESIMSCnturISC0to200,
             sESIMSCnturISC201to400,
             sESIMSCnturISC401to404,
             sESIMSCnturISC405to500,
             sESIMSCnturISC501to600,
             sESIMSCntbI0to1kms,
             sESIMSCntbI1001to5kms,
             sESIMSCntbI5001to10kms,
             sESIMSCntbI10001toTimeoutms,
             sESIMSCntbIOverTimeoutms,
             sESIMSCntbISC0to200,
             sESIMSCntbISC201to400,
             sESIMSCntbISC401to404,
             sESIMSCntbISC405to500,
             sESIMSCntbISC501to600,
             sESIMSCntubI0to1kms,
             sESIMSCntubI1001to5kms,
             sESIMSCntubI5001to10kms,
             sESIMSCntubI10001toTimeoutms,
             sESIMSCntubIOverTimeoutms,
             sESIMSCntubISC0to200,
             sESIMSCntubISC201to400,
             sESIMSCntubISC401to404,
             sESIMSCntubISC405to500,
             sESIMSCntubISC501to600,
             sESIMSAlarmFailedAlarm,
             sEMASCntcEp0to1kms,
             sEMASCntcEp1001to5kms,
             sEMASCntcEp5001to10kms,
             sEMASCntcEp10001toTimeoutms,
             sEMASCntcEpOverTimeoutms,
             sEMASCntcEpSC0to200,
             sEMASCntcEpSC201to400,
             sEMASCntcEpSC401to404,
             sEMASCntcEpSC405to500,
             sEMASCntcEpSC501to600,
             sEMASCntdEp0to1kms,
             sEMASCntdEp1001to5kms,
             sEMASCntdEp5001to10kms,
             sEMASCntdEp10001toTimeoutms,
             sEMASCntdEpOverTimeoutms,
             sEMASCntdEpSC0to200,
             sEMASCntdEpSC201to400,
             sEMASCntdEpSC401to404,
             sEMASCntdEpSC405to500,
             sEMASCntdEpSC501to600,
             sEMASCntsEp0to1kms,
             sEMASCntsEp1001to5kms,
             sEMASCntsEp5001to10kms,
             sEMASCntsEp10001toTimeoutms,
             sEMASCntsEpOverTimeoutms,
             sEMASCntsEpSC0to200,
             sEMASCntsEpSC201to400,
             sEMASCntsEpSC401to404,
             sEMASCntsEpSC405to500,
             sEMASCntsEpSC501to600,
             sEMASAlarmFailedAlarm,
             sQISCntqIbI0to1kms,
             sQISCntqIbI1001to5kms,
             sQISCntqIbI5001to10kms,
             sQISCntqIbI10001toTimeoutms,
             sQISCntqIbIOverTimeoutms,
             sQISCntqIbISC0to200,
             sQISCntqIbISC201to400,
             sQISCntqIbISC401to404,
             sQISCntqIbISC405to500,
             sQISCntqIbISC501to600,
             sQISAlarmFailedAlarm,
             sAMSCntaMbI0to1kms,
             sAMSCntaMbI1001to5kms,
             sAMSCntaMbI5001to10kms,
             sAMSCntaMbI10001toTimeoutms,
             sAMSCntaMbIOverTimeoutms,
             sAMSCntaMbISC0to200,
             sAMSCntaMbISC201to400,
             sAMSCntaMbISC401to404,
             sAMSCntaMbISC405to500,
             sAMSCntaMbISC501to600,
             sAMSAlarmFailedAlarm,
             sRMSCntrMbI0to1kms,
             sRMSCntrMbI1001to5kms,
             sRMSCntrMbI5001to10kms,
             sRMSCntrMbI10001toTimeoutms,
             sRMSCntrMbIOverTimeoutms,
             sRMSCntrMbISC0to200,
             sRMSCntrMbISC201to400,
             sRMSCntrMbISC401to404,
             sRMSCntrMbISC405to500,
             sRMSCntrMbISC501to600,
             sRMSAlarmFailedAlarm,
             sCANCELPSCntCp0to1kms,
             sCANCELPSCntCp1001to5kms,
             sCANCELPSCntCp5001to10kms,
             sCANCELPSCntCp10001toTimeoutms,
             sCANCELPSCntCpOverTimeoutms,
             sCANCELPSCntCpSC0to200,
             sCANCELPSCntCpSC201to400,
             sCANCELPSCntCpSC401to404,
             sCANCELPSCntCpSC405to500,
             sCANCELPSCntCpSC501to600,
             sCANCELPSAlarmFailedAlarm,
             sROAMINGSCnt0to1kms,
             sROAMINGSCnt1001to5kms,
             sROAMINGSCnt5001to10kms,
             sROAMINGSCnt10001toTimeoutms,
             sROAMINGSCntOverTimeoutms,
             sROAMINGSCntSC0to200,
             sROAMINGSCntSC201to400,
             sROAMINGSCntSC401to404,
             sROAMINGSCntSC405to500,
             sROAMINGSCntSC501to600,
             sROAMINGSAlarmFailedAlarm,
             sGSEN0to1kms,
             sGSCntEN1001to5kms,
             sGSCntEN5001to10kms,
             sGSCntEN10001toTimeout,
             sGSCntENOverTimeout,
             sGSCntSC0to200,
             sGSCntSC200to400,
             sGSCntSC400to500,
             sGSCntSC501to503,
             sGSAlarmFailedAlarm}
   STATUS          current
   DESCRIPTION     "A collection of objects providing performance and 
                    fault management information about a response ses."
::= { responseSesPmGroups 1 }
END

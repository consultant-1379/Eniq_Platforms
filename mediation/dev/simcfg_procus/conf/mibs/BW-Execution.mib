-- File Name : BW-Execution.mib

BW-Execution DEFINITIONS ::= BEGIN
  IMPORTS
    DateAndTime, DisplayString 
      FROM SNMPv2-TC
    MODULE-COMPLIANCE, OBJECT-GROUP 
      FROM SNMPv2-CONF
    enterprises, MODULE-IDENTITY, OBJECT-TYPE, Gauge32, Counter32, Integer32, Unsigned32 
      FROM SNMPv2-SMI;

  broadsoft MODULE-IDENTITY
    LAST-UPDATED "200912230000Z"
    ORGANIZATION "Broadsoft, Inc"
    CONTACT-INFO  "Broadsoft, Inc.
9737 Washingtonian Blvd
Suite 350
Gaithersburg , MD 20878
Tel: +1-301-977-9440"
    DESCRIPTION
      "This is the System Management Information structure for the BroadSoft enterprise."

    REVISION "200912230000Z"
      DESCRIPTION "Added counters for FR52198 - Session Data Replication"
    REVISION "200909100000Z"
      DESCRIPTION "Added counters for FR95361 - Diameter Stack"
    REVISION "200907210000Z"
      DESCRIPTION "Creation of the Execution MIB based on the defunct BW-BroadworksApplicationServer MIB."
    ::= { enterprises 6431 }

  broadworks OBJECT IDENTIFIER
    ::= { broadsoft 1 }

  executionServer OBJECT IDENTIFIER
    ::= { broadworks 2 }

-- Execution Server modules  ...........................................

  mgcpModule OBJECT IDENTIFIER
    ::= { executionServer 1 }

  imsModule OBJECT IDENTIFIER
    ::= { executionServer 4 }

  databaseModule OBJECT IDENTIFIER
    ::= { executionServer 5 }

  callpModule OBJECT IDENTIFIER
    ::= { executionServer 7 }

  smtpModule OBJECT IDENTIFIER
    ::= { executionServer 8 }

  sipModule OBJECT IDENTIFIER
    ::= { executionServer 9 }

  services OBJECT IDENTIFIER
    ::= { executionServer 11 }

  mssModule OBJECT IDENTIFIER
    ::= { executionServer 12 }

  nrsModule OBJECT IDENTIFIER
    ::= { executionServer 13 }

  pmtModule OBJECT IDENTIFIER
    ::= { executionServer 15 }

  systemModule OBJECT IDENTIFIER
    ::= { executionServer 16 }

  management OBJECT IDENTIFIER
    ::= { executionServer 17 }

  redundancyModule OBJECT IDENTIFIER
    ::= { executionServer 18 }

  capModule OBJECT IDENTIFIER
    ::= { executionServer 19 }

  smdiModule OBJECT IDENTIFIER
    ::= { executionServer 20 }

  mediaModule OBJECT IDENTIFIER
    ::= { executionServer 21 }

  wspModule OBJECT IDENTIFIER
    ::= { executionServer 22 }

  realtimeAccountingModule OBJECT IDENTIFIER
    ::= { executionServer 23 }

  externalCallLogsModule OBJECT IDENTIFIER
    ::= { executionServer 24 }

  commonCommModule OBJECT IDENTIFIER
    ::= { executionServer 25 }

  tcpModule OBJECT IDENTIFIER
    ::= { executionServer 26 }

  concurrentModule OBJECT IDENTIFIER
    ::= { executionServer 27 }

  soapModule OBJECT IDENTIFIER
    ::= { executionServer 28 }

  smppModule OBJECT IDENTIFIER
    ::= { executionServer 29 }

  dnsModule OBJECT IDENTIFIER
    ::= { executionServer 30 }

  offlineChargingModule OBJECT IDENTIFIER
    ::= { executionServer 31 }

  ocicModule OBJECT IDENTIFIER
    ::= { executionServer 32 }

  onlineChargingModule OBJECT IDENTIFIER
    ::= { executionServer 33 }

  diameterModule OBJECT IDENTIFIER
    ::= { executionServer 34 }

  shRelayInterfaceModule OBJECT IDENTIFIER
    ::= { executionServer 35 }

  mobilityModule OBJECT IDENTIFIER
    ::= { executionServer 36 }

  bwExecutionMibConformance OBJECT IDENTIFIER
    ::= { executionServer 1000 }

-- Stats and other modules.

  mgcpStats OBJECT IDENTIFIER
    ::= { mgcpModule 1 }

  imsStats OBJECT IDENTIFIER
    ::= { imsModule 1 }

  databaseStats OBJECT IDENTIFIER
    ::= { databaseModule 1 }

  callpStats OBJECT IDENTIFIER
    ::= { callpModule 1 }

  smtpStats OBJECT IDENTIFIER
    ::= { smtpModule 1 }

  sipStats OBJECT IDENTIFIER
    ::= { sipModule 1 }

  congestionManagement OBJECT IDENTIFIER
    ::= { sipModule 2 }

  capStats OBJECT IDENTIFIER
    ::= { capModule 1 }

  smdiStats OBJECT IDENTIFIER
    ::= { smdiModule 1 }

  mediaStats OBJECT IDENTIFIER
    ::= { mediaModule 1 }

  crStats OBJECT IDENTIFIER
    ::= { mediaModule 2 }

  wspStats OBJECT IDENTIFIER
    ::= { wspModule 1 }

  realtimeAccountingStats OBJECT IDENTIFIER
    ::= { realtimeAccountingModule 1 }

  externalCallLogsStats OBJECT IDENTIFIER
    ::= { externalCallLogsModule 1 }

  commonCommStats OBJECT IDENTIFIER
    ::= { commonCommModule 1 }

  tcpStats OBJECT IDENTIFIER
    ::= { tcpModule 1 }
                
  concurrentStats OBJECT IDENTIFIER
    ::= { concurrentModule 1 }
                
  soapStats OBJECT IDENTIFIER
    ::= { soapModule 1 }

  smppStats OBJECT IDENTIFIER
    ::= { smppModule 1 }

  dnsStats OBJECT IDENTIFIER
    ::= { dnsModule 1 }

  offlineChargingStats OBJECT IDENTIFIER
    ::= { offlineChargingModule 1 }

  ocicStats OBJECT IDENTIFIER
    ::= { ocicModule 1 }

  onlineChargingStats OBJECT IDENTIFIER
    ::= { onlineChargingModule 1 }

  accountCodes OBJECT IDENTIFIER
    ::= { services 1 }

  anonymousCallRejection OBJECT IDENTIFIER
    ::= { services 2 }

  authentication OBJECT IDENTIFIER
    ::= { services 3 }

  autoAttendant OBJECT IDENTIFIER
    ::= { services 4 }

  callCapacity OBJECT IDENTIFIER
    ::= { services 5 }

  callForwardingAlways OBJECT IDENTIFIER
    ::= { services 6 }

  callForwardingBusy OBJECT IDENTIFIER
    ::= { services 7 }

  callForwardingNoAnswer OBJECT IDENTIFIER
    ::= { services 8 }

  callNotify OBJECT IDENTIFIER
    ::= { services 9 }

  callPark OBJECT IDENTIFIER
    ::= { services 10 }

  callPickup OBJECT IDENTIFIER
    ::= { services 11 }

  callReturn OBJECT IDENTIFIER
    ::= { services 12 }

  commPilotCallManager OBJECT IDENTIFIER
    ::= { services 13 }

  doNotDisturb OBJECT IDENTIFIER
    ::= { services 14 }

  flashCallTransfer OBJECT IDENTIFIER
    ::= { services 15 }

  flashCallWaiting OBJECT IDENTIFIER
    ::= { services 16 }

  flashConsultation OBJECT IDENTIFIER
    ::= { services 17 }

  flashThreeWayCall OBJECT IDENTIFIER
    ::= { services 18 }

  huntGroups OBJECT IDENTIFIER
    ::= { services 19 }

  incomingCallingPlan OBJECT IDENTIFIER
    ::= { services 20 }

  ipPhone OBJECT IDENTIFIER
    ::= { services 21 }

  lastNumberRedial OBJECT IDENTIFIER
    ::= { services 22 }

  outgoingCallingPlan OBJECT IDENTIFIER
    ::= { services 23 }

  priorityAlert OBJECT IDENTIFIER
    ::= { services 24 }

  selectiveCallAcceptance OBJECT IDENTIFIER
    ::= { services 25 }

  selectiveCallForward OBJECT IDENTIFIER
    ::= { services 26 }

  selectiveCallRejection OBJECT IDENTIFIER
    ::= { services 27 }

  simRingPersonal OBJECT IDENTIFIER
    ::= { services 28 }

  voiceMessaging OBJECT IDENTIFIER
    ::= { services 29 }

  seriesCompletion OBJECT IDENTIFIER
    ::= { services 30 }

  intercept OBJECT IDENTIFIER
    ::= { services 31 }

  instantConferencing OBJECT IDENTIFIER
    ::= { services 32 }

  callingLineIDDeliveryBlock OBJECT IDENTIFIER
    ::= { services 33 }

  sessionAudit OBJECT IDENTIFIER
    ::= { services 34 }

  windowsMessaging OBJECT IDENTIFIER
    ::= { services 35 }

  callWaiting OBJECT IDENTIFIER
    ::= { services 36 }

  alternateNumbers OBJECT IDENTIFIER
    ::= { services 37 }

  cot OBJECT IDENTIFIER
    ::= { services 38 }

  sd8 OBJECT IDENTIFIER
    ::= { services 39 }

  musicOnHold OBJECT IDENTIFIER
    ::= { services 40 }

  callingNameRetrieval OBJECT IDENTIFIER
    ::= { services 41 }

  thirdPartyMWIControl OBJECT IDENTIFIER
    ::= { services 42 }

  callCenter OBJECT IDENTIFIER
    ::= { services 43 }

  callForwardGroupNoAnswer OBJECT IDENTIFIER
    ::= { services 44 }

  sd100 OBJECT IDENTIFIER
    ::= { services 45 }

  thirdPartyVMail OBJECT IDENTIFIER
    ::= { services 46 }

  directedCallPickup OBJECT IDENTIFIER
    ::= { services 47 }

  flashCallHold OBJECT IDENTIFIER
    ::= { services 48 }

  emergencyZones OBJECT IDENTIFIER
    ::= { services 49 }

  dpubi OBJECT IDENTIFIER
    ::= { services 50 }

  acb OBJECT IDENTIFIER
    ::= { services 51 }

  sequentialRing OBJECT IDENTIFIER
    ::= { services 52 }

  ringTimeout OBJECT IDENTIFIER
    ::= { services 53 }

  videoAddOn OBJECT IDENTIFIER
    ::= { services 54 }

  mct OBJECT IDENTIFIER
    ::= { services 55 }

  pushToTalk OBJECT IDENTIFIER
    ::= { services 56 }

  hoteling OBJECT IDENTIFIER
    ::= { services 57 }

  preferredCarrier OBJECT IDENTIFIER
    ::= { services 58 }
  
  familySimRing OBJECT IDENTIFIER
    ::= { services 59 }

  diversionInhibitor OBJECT IDENTIFIER
    ::= { services 60 }

  instantGroupCall OBJECT IDENTIFIER
    ::= { services 61 }
          
  automaticHoldRetrieve OBJECT IDENTIFIER
    ::= { services 62 }

  trunkGroup OBJECT IDENTIFIER
    ::= { services 63 }

  customRingback OBJECT IDENTIFIER
    ::= { services 64 }

  physicalLocation   OBJECT IDENTIFIER
    ::= { services 65 }

  faxMessaging   OBJECT IDENTIFIER
    ::= { services 66 }
          
  externalemergencyrouting OBJECT IDENTIFIER
    ::= { services 67 }

  twoStageDialing OBJECT IDENTIFIER
    ::= { services 68 }

  callForwardingNotReachable OBJECT IDENTIFIER
    ::= { services 69 }

  mwiDeliveryToMobile OBJECT IDENTIFIER
    ::= { services 70 }

--  Obsoleted, keeping the constant locked down so it does not get used anymore
--  sharedCallAppearance OBJECT IDENTIFIER
--    ::= { services 71 }

  externalCustomRingback OBJECT IDENTIFIER
    ::= { services 72 }

  inCallServiceActivation OBJECT IDENTIFIER
    ::= { services 73 }

  expensiveCallNotification OBJECT IDENTIFIER
    ::= { services 74 }

  locationControl OBJECT IDENTIFIER
    ::= { services 75 }

  callRetrieve OBJECT IDENTIFIER
    ::= { services 76 }

  broadworksAnywhere OBJECT IDENTIFIER
    ::= { services 77 }

  zoneCallingRestrictions OBJECT IDENTIFIER
    ::= { services 78 }

  communicationBarring OBJECT IDENTIFIER
    ::= { services 79 }

  callBridge OBJECT IDENTIFIER
    ::= { services 80 }

  directoryNumberHunting OBJECT IDENTIFIER
    ::= { services 81 }

  adviceOfCharge OBJECT IDENTIFIER
    ::= { services 82 }

  sessionAdmissionControl OBJECT IDENTIFIER
    ::= { services 83 }

  virtualOnNet OBJECT IDENTIFIER
    ::= { services 84 }

  preAlertingAnnouncement OBJECT IDENTIFIER
    ::= { services 85 }

  locationCallingRestrictions OBJECT IDENTIFIER
    ::= { services 86 }

  routePoint OBJECT IDENTIFIER
    ::= { services 87 }

  groupPaging OBJECT IDENTIFIER
    ::= { services 88 }

  meetmeConferencing OBJECT IDENTIFIER
    ::= { services 89 }

  shortMessageService OBJECT IDENTIFIER
    ::= { services 90 }

  callMeNow OBJECT IDENTIFIER
    ::= { services 91 }

  callLogs OBJECT IDENTIFIER
    ::= { services 92 }

  callForwardingGroupNotReachable OBJECT IDENTIFIER
    ::= { services 93 }

  callRecording OBJECT IDENTIFIER
    ::= { services 94 }

  findMeFollowMe OBJECT IDENTIFIER
    ::= { services 95 }

  groupNightForwarding OBJECT IDENTIFIER
    ::= { services 96 }

  executive OBJECT IDENTIFIER
    ::= { services 97 }

  flexibleseating OBJECT IDENTIFIER
    ::= { services 98 }

  numberPortability OBJECT IDENTIFIER
    ::= { services 99 }

  numberPortabilityAnnc OBJECT IDENTIFIER
    ::= { services 100 }

  personalAssistant OBJECT IDENTIFIER
    ::= { services 101 }

  collaborate OBJECT IDENTIFIER
    ::= { services 102 }

  callForwardingAlwaysSecondary OBJECT IDENTIFIER
    ::= { services 103}

  callLogQueue OBJECT IDENTIFIER
    ::= { callLogs 1 }

  callLogProcessors OBJECT IDENTIFIER
    ::= { callLogs 2 }

  mssStats OBJECT IDENTIFIER
    ::= { mssModule 1 }

  nrsStats OBJECT IDENTIFIER
    ::= { nrsModule 1 }

  pmtStats OBJECT IDENTIFIER
    ::= { pmtModule 1 }

  systemStats OBJECT IDENTIFIER
    ::= { systemModule 1 }

  redundancyStats OBJECT IDENTIFIER
    ::= { redundancyModule 1 }

  diameterStats OBJECT IDENTIFIER
    ::= { diameterModule 1 }

  shRelayInterfaceStats OBJECT IDENTIFIER
    ::= { shRelayInterfaceModule 1 }

  mobilityStats OBJECT IDENTIFIER
    ::= { mobilityModule 1 }

-- Protocol :: MGCP ...........................................

  bwMGCPStatsMGCPCommandOuts OBJECT-TYPE
    SYNTAX      Counter32
    MAX-ACCESS  read-write
    STATUS      current
    DESCRIPTION 
        "This counter reflects the number of MGCP commands sent out by BroadWorks"
    ::= { mgcpStats 1 }

  bwMGCPStatsMGCPCommandIns OBJECT-TYPE
    SYNTAX      Counter32
    MAX-ACCESS  read-write
    STATUS      current
    DESCRIPTION 
        "This counter reflects the total number of MGCP commands received by BroadWorks"
    ::= { mgcpStats 2 }

  bwMGCPStatsMGCPResponseOuts OBJECT-TYPE
    SYNTAX      Counter32
    MAX-ACCESS  read-write
    STATUS      current
    DESCRIPTION 
        "This counter reflects the total number of MGCP responses sent by BroadWorks"
    ::= { mgcpStats 3 }

  bwMGCPStatsMGCPResponseIns OBJECT-TYPE
    SYNTAX      Counter32
    MAX-ACCESS  read-write
    STATUS      current
    DESCRIPTION 
        "This counter reflects the total number of MGCP responses recevied by BroadWorks"
    ::= { mgcpStats 4 }

  bwMGCPStatsAuditConnectionOuts OBJECT-TYPE
    SYNTAX      Counter32
    MAX-ACCESS  read-write
    STATUS      current
    DESCRIPTION 
        "This counter reflects the number of Audit Connection commands sent by Broadworks"
    ::= { mgcpStats 5 }

  bwMGCPStatsAuditEndpointOuts OBJECT-TYPE
    SYNTAX      Counter32
    MAX-ACCESS  read-write
    STATUS      current
    DESCRIPTION 
        "This counter reflects the number of Audit Endpoint commands sent by BroadWorks"
    ::= { mgcpStats 6 }

  bwMGCPStatsCreateConnectionOuts OBJECT-TYPE
    SYNTAX      Counter32
    MAX-ACCESS  read-write
    STATUS      current
    DESCRIPTION 
        "This counter reflects the number of Create Connection commands sent by BroadWorks"
    ::= { mgcpStats 7 }

  bwMGCPStatsDeleteAgentConnectionOuts OBJECT-TYPE
    SYNTAX      Counter32
    MAX-ACCESS  read-write
    STATUS      current
    DESCRIPTION 
        "This counter reflects the number of Delete Agent Connections sent by BroadWorks"
    ::= { mgcpStats 8 }

  bwMGCPStatsDeleteConnectionOuts OBJECT-TYPE
    SYNTAX      Counter32
    MAX-ACCESS  read-write
    STATUS      current
    DESCRIPTION 
        "This counter reflects the number of Delete Connection commands sent by BroadWorks"
    ::= { mgcpStats 9 }

  bwMGCPStatsDeleteGatewayConnectionIns OBJECT-TYPE
    SYNTAX      Counter32
    MAX-ACCESS  read-write
    STATUS      current
    DESCRIPTION 
        "This counter reflects the number of Delete Gateway Connection commands received by BroadWorks"
    ::= { mgcpStats 10 }

  bwMGCPStatsEndpointConfigurationOuts OBJECT-TYPE
    SYNTAX      Counter32
    MAX-ACCESS  read-write
    STATUS      current
    DESCRIPTION 
        "This counter reflects the number of Endpoint Configuration commands sent by Broadworks"
    ::= { mgcpStats 11 }

  bwMGCPStatsExtraCommandOuts OBJECT-TYPE
    SYNTAX      Counter32
    MAX-ACCESS  read-write
    STATUS      current
    DESCRIPTION 
        "This counter reflects the number of Extra Commands sent by BroadWorks"
    ::= { mgcpStats 12 }

  bwMGCPStatsModifyConnectionOuts OBJECT-TYPE
    SYNTAX      Counter32
    MAX-ACCESS  read-write
    STATUS      current
    DESCRIPTION 
        "This counter reflects the number of Modify Connection commands sent by BroadWorks"
    ::= { mgcpStats 13 }

  bwMGCPStatsNotificationRequestOuts OBJECT-TYPE
    SYNTAX      Counter32
    MAX-ACCESS  read-write
    STATUS      current
    DESCRIPTION 
        "This counter reflects the number of Notification Request commands sent by BroadWorks"
    ::= { mgcpStats 14 }

  bwMGCPStatsNotifyIns OBJECT-TYPE
    SYNTAX      Counter32
    MAX-ACCESS  read-write
    STATUS      current
    DESCRIPTION 
        "This counter reflects the number of Notify commands received by BroadWorks"
    ::= { mgcpStats 15 }

  bwMGCPStatsRestartInProgressIns OBJECT-TYPE
    SYNTAX      Counter32
    MAX-ACCESS  read-write
    STATUS      current
    DESCRIPTION 
        "This counter reflects the number of Restarts In Progress received by BroadWorks"
    ::= { mgcpStats 16 }

  bwMGCPStatsMGCPCommandResponseTable OBJECT-TYPE
    SYNTAX      SEQUENCE OF BwMGCPStatsMGCPCommandResponseEntry
    MAX-ACCESS  not-accessible
    STATUS      current
    DESCRIPTION 
        "This table contains the counters for all MGCP responses sent or received by BroadWorks.  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 17 }

  bwMGCPStatsMGCPCommandResponseEntry OBJECT-TYPE
    SYNTAX      BwMGCPStatsMGCPCommandResponseEntry
    MAX-ACCESS  not-accessible
    STATUS      current
    DESCRIPTION 
        "This row contains information on a particular MGCP status code received or sent in response to a MGCP command."
    INDEX       { bwMGCPStatsMGCPCommandResponseCodeValue }
    ::= { bwMGCPStatsMGCPCommandResponseTable 1 }

  BwMGCPStatsMGCPCommandResponseEntry ::= SEQUENCE {
    bwMGCPStatsMGCPCommandResponseCodeValue     Integer32,
    bwMGCPStatsMGCPCommandResponseOuts          Counter32,
    bwMGCPStatsMGCPCommandResponseIns           Counter32
  }

  bwMGCPStatsMGCPCommandResponseCodeValue OBJECT-TYPE
    SYNTAX      Integer32 (100..999)
    MAX-ACCESS  not-accessible
    STATUS      current
    DESCRIPTION 
        "This integer represents an MGCP status code.  The rest of the information in this row is related to this value."
    ::= { bwMGCPStatsMGCPCommandResponseEntry 1 }

  bwMGCPStatsMGCPCommandResponseOuts OBJECT-TYPE
    SYNTAX      Counter32
    MAX-ACCESS  read-write
    STATUS      current
    DESCRIPTION 
        "This counter represents the number of MGCP responses sent by BroadWorks in response to an MGCP command received."
    ::= { bwMGCPStatsMGCPCommandResponseEntry 2 }

  bwMGCPStatsMGCPCommandResponseIns OBJECT-TYPE
    SYNTAX      Counter32
    MAX-ACCESS  read-write
    STATUS      current
    DESCRIPTION 
        "This counter represents the number of MGCP responses received by BroadWorks in response to an MGCP command"
    ::= { bwMGCPStatsMGCPCommandResponseEntry 3 }

  bwMGCPStatsAuditConnectionResponseTable OBJECT-TYPE
    SYNTAX      SEQUENCE OF BwMGCPStatsAuditConnectionResponseEntry
    MAX-ACCESS  not-accessible
    STATUS      current
    DESCRIPTION 
        "This table contains the counters for MGCP responses received by BroadWorks to an Audit Connection command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 18 }

  bwMGCPStatsAuditConnectionResponseEntry OBJECT-TYPE
    SYNTAX      BwMGCPStatsAuditConnectionResponseEntry
    MAX-ACCESS  not-accessible
    STATUS      current
    DESCRIPTION 
        "This row contains information on a particular MGCP status code received or sent in response to a MGCP command."
    INDEX       { bwMGCPStatsAuditConnectionResponseCodeValue }
    ::= { bwMGCPStatsAuditConnectionResponseTable 1 }

  BwMGCPStatsAuditConnectionResponseEntry ::= SEQUENCE {
    bwMGCPStatsAuditConnectionResponseCodeValue     Integer32,
    bwMGCPStatsAuditConnectionResponseIns           Counter32
  }

  bwMGCPStatsAuditConnectionResponseCodeValue OBJECT-TYPE
    SYNTAX      Integer32 (100..999)
    MAX-ACCESS  not-accessible
    STATUS      current
    DESCRIPTION 
        "This integer represents an MGCP status code.  The rest of the information in this row is related to this value."
    ::= { bwMGCPStatsAuditConnectionResponseEntry 1 }

  bwMGCPStatsAuditConnectionResponseIns OBJECT-TYPE
    SYNTAX      Counter32
    MAX-ACCESS  read-write
    STATUS      current
    DESCRIPTION 
        "This counter represents the number of MGCP responses received by BroadWorks in response to an Audit Connection command sent."
    ::= { bwMGCPStatsAuditConnectionResponseEntry 2 }

  bwMGCPStatsAuditEndpointResponseTable OBJECT-TYPE
    SYNTAX      SEQUENCE OF BwMGCPStatsAuditEndpointResponseEntry
    MAX-ACCESS  not-accessible
    STATUS      current
    DESCRIPTION 
        "This table contains the counters for MGCP responses received by BroadWorks to an Audit Endpoint command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 19 }

  bwMGCPStatsAuditEndpointResponseEntry OBJECT-TYPE
    SYNTAX      BwMGCPStatsAuditEndpointResponseEntry
    MAX-ACCESS  not-accessible
    STATUS      current
    DESCRIPTION 
        "This row contains information on a particular MGCP status code received or sent in response to an Audit Endpoint command."
    INDEX       { bwMGCPStatsAuditEndpointResponseCodeValue }
    ::= { bwMGCPStatsAuditEndpointResponseTable 1 }

  BwMGCPStatsAuditEndpointResponseEntry ::= SEQUENCE {
    bwMGCPStatsAuditEndpointResponseCodeValue   Integer32,
    bwMGCPStatsAuditEndpointResponseIns         Counter32
  }

  bwMGCPStatsAuditEndpointResponseCodeValue OBJECT-TYPE
    SYNTAX      Integer32 (100..999)
    MAX-ACCESS  not-accessible
    STATUS      current
    DESCRIPTION 
        "This integer represents an MGCP status code.  The rest of the information in this row is related to this value."
    ::= { bwMGCPStatsAuditEndpointResponseEntry 1 }

  bwMGCPStatsAuditEndpointResponseIns OBJECT-TYPE
    SYNTAX      Counter32
    MAX-ACCESS  read-write
    STATUS      current
    DESCRIPTION 
        "This counter represents the number of MGCP responses received by BroadWorks in response to an Audit Endpoint command sent."
    ::= { bwMGCPStatsAuditEndpointResponseEntry 2 }

  bwMGCPStatsCreateConnectionResponseTable OBJECT-TYPE
    SYNTAX      SEQUENCE OF BwMGCPStatsCreateConnectionResponseEntry
    MAX-ACCESS  not-accessible
    STATUS      current
    DESCRIPTION 
        "This table contains the counters for MGCP responses received by BroadWorks to an Create Connection command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 20 }

  bwMGCPStatsCreateConnectionResponseEntry OBJECT-TYPE
    SYNTAX      BwMGCPStatsCreateConnectionResponseEntry
    MAX-ACCESS  not-accessible
    STATUS      current
    DESCRIPTION 
        "This row contains information on a particular MGCP status code received or sent in response to an Create Connection command."
    INDEX       { bwMGCPStatsCreateConnectionResponseCodeValue }
    ::= { bwMGCPStatsCreateConnectionResponseTable 1 }

  BwMGCPStatsCreateConnectionResponseEntry ::= SEQUENCE {
    bwMGCPStatsCreateConnectionResponseCodeValue    Integer32,
    bwMGCPStatsCreateConnectionResponseIns          Counter32
  }

  bwMGCPStatsCreateConnectionResponseCodeValue OBJECT-TYPE
    SYNTAX      Integer32 (100..999)
    MAX-ACCESS  not-accessible
    STATUS      current
    DESCRIPTION 
        "This integer represents an MGCP status code.  The rest of the information in this row is related to this value."
    ::= { bwMGCPStatsCreateConnectionResponseEntry 1 }

  bwMGCPStatsCreateConnectionResponseIns OBJECT-TYPE
    SYNTAX      Counter32
    MAX-ACCESS  read-write
    STATUS      current
    DESCRIPTION 
        "This counter represents the number of MGCP responses received by BroadWorks in response to an Create Connection command sent."
    ::= { bwMGCPStatsCreateConnectionResponseEntry 2 }

  bwMGCPStatsDeleteConnectionResponseTable OBJECT-TYPE
    SYNTAX      SEQUENCE OF BwMGCPStatsDeleteConnectionResponseEntry
    MAX-ACCESS  not-accessible
    STATUS      current
    DESCRIPTION 
        "This table contains the counters for MGCP responses received by BroadWorks to an Create Connection command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 21 }

  bwMGCPStatsDeleteConnectionResponseEntry OBJECT-TYPE
    SYNTAX      BwMGCPStatsDeleteConnectionResponseEntry
    MAX-ACCESS  not-accessible
    STATUS      current
    DESCRIPTION 
        "This row contains information on a particular MGCP status code received or sent in response to an Create Connection command."
    INDEX       { bwMGCPStatsDeleteConnectionResponseCodeValue }
    ::= { bwMGCPStatsDeleteConnectionResponseTable 1 }

  BwMGCPStatsDeleteConnectionResponseEntry ::= SEQUENCE {
    bwMGCPStatsDeleteConnectionResponseCodeValue    Integer32,
    bwMGCPStatsDeleteAgentConnectionResponseIns     Counter32,
    bwMGCPStatsDeleteConnectionResponseIns          Counter32,
    bwMGCPStatsDeleteGatewayConnectionResponseOuts  Counter32
  }

  bwMGCPStatsDeleteConnectionResponseCodeValue OBJECT-TYPE
    SYNTAX      Integer32 (100..999)
    MAX-ACCESS  not-accessible
    STATUS      current
    DESCRIPTION 
        "This integer represents an MGCP status code.  The rest of the information in this row is related to this value."
    ::= { bwMGCPStatsDeleteConnectionResponseEntry 1 }

  bwMGCPStatsDeleteAgentConnectionResponseIns OBJECT-TYPE
    SYNTAX      Counter32
    MAX-ACCESS  read-write
    STATUS      current
    DESCRIPTION 
        "This counter represents the number of MGCP responses received by BroadWorks in response to a Delete Agent Connection command sent."
    ::= { bwMGCPStatsDeleteConnectionResponseEntry 2 }

  bwMGCPStatsDeleteConnectionResponseIns OBJECT-TYPE
    SYNTAX      Counter32
    MAX-ACCESS  read-write
    STATUS      current
    DESCRIPTION 
        "This counter represents the number of MGCP responses received by BroadWorks in response to a Delete Connection command sent."
    ::= { bwMGCPStatsDeleteConnectionResponseEntry 3 }

  bwMGCPStatsDeleteGatewayConnectionResponseOuts OBJECT-TYPE
    SYNTAX      Counter32
    MAX-ACCESS  read-write
    STATUS      current
    DESCRIPTION 
        "This counter represents the number of MGCP responses received by BroadWorks in response to a Delete Gateway Connection command sent."
    ::= { bwMGCPStatsDeleteConnectionResponseEntry 4 }

  bwMGCPStatsEndpointConfigurationResponseTable OBJECT-TYPE
    SYNTAX      SEQUENCE OF BwMGCPStatsEndpointConfigurationResponseEntry
    MAX-ACCESS  not-accessible
    STATUS      current
    DESCRIPTION 
        "This table contains the counters for MGCP responses received by BroadWorks to an Endpoint Configuration command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 22 }

  bwMGCPStatsEndpointConfigurationResponseEntry OBJECT-TYPE
    SYNTAX      BwMGCPStatsEndpointConfigurationResponseEntry
    MAX-ACCESS  not-accessible
    STATUS      current
    DESCRIPTION 
        "This row contains information on a particular MGCP status code received or sent in response to an Endpoint Configuration command."
    INDEX       { bwMGCPStatsEndpointConfigurationResponseCodeValue }
    ::= { bwMGCPStatsEndpointConfigurationResponseTable 1 }

  BwMGCPStatsEndpointConfigurationResponseEntry ::= SEQUENCE {
    bwMGCPStatsEndpointConfigurationResponseCodeValue   Integer32,
    bwMGCPStatsEndpointConfigurationResponseIns         Counter32
  }

  bwMGCPStatsEndpointConfigurationResponseCodeValue OBJECT-TYPE
    SYNTAX      Integer32 (100..999)
    MAX-ACCESS  not-accessible
    STATUS      current
    DESCRIPTION 
        "This integer represents an MGCP status code.  The rest of the information in this row is related to this value."
    ::= { bwMGCPStatsEndpointConfigurationResponseEntry 1 }

  bwMGCPStatsEndpointConfigurationResponseIns OBJECT-TYPE
    SYNTAX      Counter32
    MAX-ACCESS  read-write
    STATUS      current
    DESCRIPTION 
        "This counter represents the number of MGCP responses received by BroadWorks in response to an Endpoint Configuration command sent."
    ::= { bwMGCPStatsEndpointConfigurationResponseEntry 2 }

  bwMGCPStatsExtraCommandResponseTable OBJECT-TYPE
    SYNTAX      SEQUENCE OF BwMGCPStatsExtraCommandResponseEntry
    MAX-ACCESS  not-accessible
    STATUS      current
    DESCRIPTION 
        "This table contains the counters for MGCP responses received by BroadWorks to an Extra Command command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 23 }

  bwMGCPStatsExtraCommandResponseEntry OBJECT-TYPE
    SYNTAX      BwMGCPStatsExtraCommandResponseEntry
    MAX-ACCESS  not-accessible
    STATUS      current
    DESCRIPTION 
        "This row contains information on a particular MGCP status code received or sent in response to an Extra Command command."
    INDEX       { bwMGCPStatsExtraCommandResponseCodeValue }
    ::= { bwMGCPStatsExtraCommandResponseTable 1 }

  BwMGCPStatsExtraCommandResponseEntry ::= SEQUENCE {
    bwMGCPStatsExtraCommandResponseCodeValue    Integer32,
    bwMGCPStatsExtraCommandResponseIns          Counter32
  }

  bwMGCPStatsExtraCommandResponseCodeValue OBJECT-TYPE
    SYNTAX      Integer32 (100..999)
    MAX-ACCESS  not-accessible
    STATUS      current
    DESCRIPTION 
        "This integer represents an MGCP status code.  The rest of the information in this row is related to this value."
    ::= { bwMGCPStatsExtraCommandResponseEntry 1 }

  bwMGCPStatsExtraCommandResponseIns OBJECT-TYPE
    SYNTAX      Counter32
    MAX-ACCESS  read-write
    STATUS      current
    DESCRIPTION 
        "This counter represents the number of MGCP responses received by BroadWorks in response to an Extra Command command sent."
    ::= { bwMGCPStatsExtraCommandResponseEntry 2 }

  bwMGCPStatsModifyConnectionResponseTable OBJECT-TYPE
    SYNTAX      SEQUENCE OF BwMGCPStatsModifyConnectionResponseEntry
    MAX-ACCESS  not-accessible
    STATUS      current
    DESCRIPTION 
        "This table contains the counters for MGCP responses received by BroadWorks to a Modify Connection command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 24 }

  bwMGCPStatsModifyConnectionResponseEntry OBJECT-TYPE
    SYNTAX      BwMGCPStatsModifyConnectionResponseEntry
    MAX-ACCESS  not-accessible
    STATUS      current
    DESCRIPTION 
        "This row contains information on a particular MGCP status code received or sent in response to a Modify Connection command."
    INDEX       { bwMGCPStatsModifyConnectionResponseCodeValue }
    ::= { bwMGCPStatsModifyConnectionResponseTable 1 }

  BwMGCPStatsModifyConnectionResponseEntry ::= SEQUENCE {
    bwMGCPStatsModifyConnectionResponseCodeValue    Integer32,
    bwMGCPStatsModifyConnectionResponseIns          Counter32
  }

  bwMGCPStatsModifyConnectionResponseCodeValue OBJECT-TYPE
    SYNTAX      Integer32 (100..999)
    MAX-ACCESS  not-accessible
    STATUS      current
    DESCRIPTION 
        "This integer represents an MGCP status code.  The rest of the information in this row is related to this value."
    ::= { bwMGCPStatsModifyConnectionResponseEntry 1 }

  bwMGCPStatsModifyConnectionResponseIns OBJECT-TYPE
    SYNTAX      Counter32
    MAX-ACCESS  read-write
    STATUS      current
    DESCRIPTION 
        "This counter represents the number of MGCP responses received by BroadWorks in response to a Modify Connection command sent."
    ::= { bwMGCPStatsModifyConnectionResponseEntry 2 }

  bwMGCPStatsNotificationRequestResponseTable OBJECT-TYPE
    SYNTAX      SEQUENCE OF BwMGCPStatsNotificationRequestResponseEntry
    MAX-ACCESS  not-accessible
    STATUS      current
    DESCRIPTION 
        "This table contains the counters for MGCP responses received by BroadWorks to a Notification Request command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 25 }

  bwMGCPStatsNotificationRequestResponseEntry OBJECT-TYPE
    SYNTAX      BwMGCPStatsNotificationRequestResponseEntry
    MAX-ACCESS  not-accessible
    STATUS      current
    DESCRIPTION 
        "This row contains information on a particular MGCP status code received or sent in response to a Notification Request command."
    INDEX       { bwMGCPStatsNotificationRequestResponseCodeValue }
    ::= { bwMGCPStatsNotificationRequestResponseTable 1 }

  BwMGCPStatsNotificationRequestResponseEntry ::= SEQUENCE {
    bwMGCPStatsNotificationRequestResponseCodeValue     Integer32,
    bwMGCPStatsNotificationRequestResponseIns           Counter32
  }

  bwMGCPStatsNotificationRequestResponseCodeValue OBJECT-TYPE
    SYNTAX      Integer32 (100..999)
    MAX-ACCESS  not-accessible
    STATUS      current
    DESCRIPTION 
        "This integer represents an MGCP status code.  The rest of the information in this row is related to this value."
    ::= { bwMGCPStatsNotificationRequestResponseEntry 1 }

  bwMGCPStatsNotificationRequestResponseIns OBJECT-TYPE
    SYNTAX      Counter32
    MAX-ACCESS  read-write
    STATUS      current
    DESCRIPTION 
        "This counter represents the number of MGCP responses received by BroadWorks in response to a Notification Request command sent."
    ::= { bwMGCPStatsNotificationRequestResponseEntry 2 }

  bwMGCPStatsNotifyResponseTable OBJECT-TYPE
    SYNTAX      SEQUENCE OF BwMGCPStatsNotifyResponseEntry
    MAX-ACCESS  not-accessible
    STATUS      current
    DESCRIPTION 
        "This table contains the counters for MGCP responses sent by BroadWorks to a Notify command received by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 26 }

  bwMGCPStatsNotifyResponseEntry OBJECT-TYPE
    SYNTAX      BwMGCPStatsNotifyResponseEntry
    MAX-ACCESS  not-accessible
    STATUS      current
    DESCRIPTION 
        "This row contains information on a particular MGCP status code sent in response to a Notify command."
    INDEX       { bwMGCPStatsNotifyResponseCodeValue }
    ::= { bwMGCPStatsNotifyResponseTable 1 }

  BwMGCPStatsNotifyResponseEntry ::= SEQUENCE {
    bwMGCPStatsNotifyResponseCodeValue  Integer32,
    bwMGCPStatsNotifyResponseOuts       Counter32
  }

  bwMGCPStatsNotifyResponseCodeValue OBJECT-TYPE
    SYNTAX      Integer32 (100..999)
    MAX-ACCESS  not-accessible
    STATUS      current
    DESCRIPTION 
        "This integer represents an MGCP status code.  The rest of the information in this row is related to this value."
    ::= { bwMGCPStatsNotifyResponseEntry 1 }

  bwMGCPStatsNotifyResponseOuts OBJECT-TYPE
    SYNTAX      Counter32
    MAX-ACCESS  read-write
    STATUS      current
    DESCRIPTION 
        "This counter represents the number of MGCP responses sent by BroadWorks in response to a Notify command received."
    ::= { bwMGCPStatsNotifyResponseEntry 2 }

  bwMGCPStatsRestartInProgressResponseTable OBJECT-TYPE
    SYNTAX      SEQUENCE OF BwMGCPStatsRestartInProgressResponseEntry
    MAX-ACCESS  not-accessible
    STATUS      current
    DESCRIPTION 
        "This table contains the counters for MGCP responses sent by BroadWorks to a Restart In Progress command received by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
    ::= { mgcpStats 27 }

  bwMGCPStatsRestartInProgressResponseEntry OBJECT-TYPE
    SYNTAX      BwMGCPStatsRestartInProgressResponseEntry
    MAX-ACCESS  not-accessible
    STATUS      current
    DESCRIPTION 
        "This row contains information on a particular MGCP status code sent in response to a Restart In Progress command."
    INDEX       { bwMGCPStatsRestartInProgressResponseCodeValue }
    ::= { bwMGCPStatsRestartInProgressResponseTable 1 }

  BwMGCPStatsRestartInProgressResponseEntry ::= SEQUENCE {
    bwMGCPStatsRestartInProgressResponseCodeValue   Integer32,
    bwMGCPStatsRestartInProgressResponseOuts        Counter32
  }

  bwMGCPStatsRestartInProgressResponseCodeValue OBJECT-TYPE
    SYNTAX      Integer32 (100..999)
    MAX-ACCESS  not-accessible
    STATUS      current
    DESCRIPTION 
        "This integer represents an MGCP status code.  The rest of the information in this row is related to this value."
    ::= { bwMGCPStatsRestartInProgressResponseEntry 1 }

  bwMGCPStatsRestartInProgressResponseOuts OBJECT-TYPE
    SYNTAX      Counter32
    MAX-ACCESS  read-write
    STATUS      current
    DESCRIPTION 
        "This counter represents the number of MGCP responses sent by BroadWorks in response to a Restart In Progress command received."
    ::= { bwMGCPStatsRestartInProgressResponseEntry 2 }

  bwMGCPStatsDialToneDelay OBJECT-TYPE
    SYNTAX      Gauge32
    MAX-ACCESS  read-write
    STATUS      current
    DESCRIPTION 
        "This gauge measures the average time (in milliseconds) between receipt of NTFY indicating off-hook and transmission of RQNT indicating dial-tone and request for digits"
    ::= { mgcpStats 28 }

  bwMGCPStatsMinDialToneDelay OBJECT-TYPE
    SYNTAX      Gauge32
    MAX-ACCESS  read-write
    STATUS      current
    DESCRIPTION 
        "This measures the shortest MGCP dial-tone delay sampled since the system was started or since this measurement was cleared"
    ::= { mgcpStats 29 }

  bwMGCPStatsMaxDialToneDelay OBJECT-TYPE
    SYNTAX      Gauge32
    MAX-ACCESS  read-write
    STATUS      current
    DESCRIPTION 
        "This measures the longest MGCP dial-tone delay sampled since the system was started or since this measurement was cleared"
    ::= { mgcpStats 30 }

  bwMGCPStatsSetupSignalDelay OBJECT-TYPE
    SYNTAX      Gauge32
    MAX-ACCESS  read-write
    STATUS      current
    DESCRIPTION 
        "This gauge is applicable to MGCP originated calls.  It measures the average time (in milliseconds) it takes between the receipt of a NTFY message with digits dialed for the origination of a new call and the transmission of an INVITE (Sip terminator), RQNT (MGCP terminator with in-band ringback), or CRCX (MGCP terminator without in-band ringback) to the primary device of the original called party (in the case of intra-group call) or to the network element of the original called party (in the case of a call to the PSTN).  Delays incurred by a dip to the Network Server are removed from the measurement.  This measurement is intended to reflect internal queuing, scheduling, and processing delays.
         The same clarifications as for bwSipStatsSetupSignalDelay apply to bwMGCPStatsSetupSignalDelay"
    ::= { mgcpStats 31 }

  bwMGCPStatsMinSetupSignalDelay OBJECT-TYPE
    SYNTAX      Gauge32
    MAX-ACCESS  read-write
    STATUS      current
    DESCRIPTION 
        "This measures the shortest MGCP setup-signal delay sampled since the system was started or since this measurement was cleared"
    ::= { mgcpStats 32 }

  bwMGCPStatsMaxSetupSignalDelay OBJECT-TYPE
    SYNTAX      Gauge32
    MAX-ACCESS  read-write
    STATUS      current
    DESCRIPTION 
        "This measures the shortest MGCP setup-signal delay sampled since the system was started or since this measurement was cleared"
    ::= { mgcpStats 33 }

  bwMGCPStatsAnswerSignalDelay OBJECT-TYPE
    SYNTAX      Gauge32
    MAX-ACCESS  read-write
    STATUS      current
    DESCRIPTION 
        "This gauge measures the average time (in milliseconds) between the receipt of a 200 OK message indicating answer or a NTFY off-hook indicating answer and the transmission of a MDCX indicating answer to the originator.   This measurement is intended to reflect internal queuing, scheduling, and processing delays.
         This gauge is applicable to only the MGCP originated calls for which the setup-signal delay is measured.  Answer signal delay is not measured when the call has been forwarded, redirected, or when the call has encountered route advancing."
    ::= { mgcpStats 34 }

  bwMGCPStatsMinAnswerSignalDelay OBJECT-TYPE
    SYNTAX      Gauge32
    MAX-ACCESS  read-write
    STATUS      current
    DESCRIPTION 
        "This measures the shortest MGCP answer-signal delay sampled since the system was started or since this measurement was cleared."
    ::= { mgcpStats 35 }

  bwMGCPStatsMaxAnswerSignalDelay OBJECT-TYPE
    SYNTAX      Gauge32
    MAX-ACCESS  read-write
    STATUS      current
    DESCRIPTION 
        "This measures the longest MGCP answer-signal delay sampled since the system was started or since this measurement was cleared."
    ::= { mgcpStats 36 }

  bwMGCPStatsMessageRetryPercentage OBJECT-TYPE
    SYNTAX      Gauge32
    MAX-ACCESS  read-only
    STATUS      current
    DESCRIPTION 
        "This gauge measures the percentage of MGCP requests sent due to retry.  Of up to the last 100 requests sent, this gauge calculates the percentage sent due to retransmission (i.e. gauge = MGCP request retransmissions  / (MGCP request initial transmissions + MGCP request retransmissions)."
    ::= { mgcpStats 37 }

-- Protocol :: Incoming Mail Server ...........................................

  bwIMSSuccessfulConnectionAttempts OBJECT-TYPE
    SYNTAX      Counter32
    MAX-ACCESS  read-write
    STATUS      current
    DESCRIPTION 
        "This counter reflects the number of successful connection to incoming mail server."
    ::= { imsStats 1 }

  bwIMSUnsuccessfulConnectionAttempts OBJECT-TYPE
    SYNTAX      Counter32
    MAX-ACCESS  read-write
    STATUS      current
    DESCRIPTION 
        "This counter reflects the total number of unsuccessful connection to incoming mail server."
    ::= { imsStats 2 }

  bwIMSSuccessfulDownLoadAttempts OBJECT-TYPE
    SYNTAX      Counter32
    MAX-ACCESS  read-write
    STATUS      current
    DESCRIPTION 
        "This counter reflects the number of messages downloaded  from incoming mail server."
    ::= { imsStats 3 }

  bwIMSUnsuccessfulDownLoadAttempts OBJECT-TYPE
    SYNTAX      Counter32
    MAX-ACCESS  read-write
    STATUS      current
    DESCRIPTION 
        "This counter reflects the number of unsuccessful   message download attempted on incoming mail server."
    ::= { imsStats 4 }

  bwIMSMaxSessions OBJECT-TYPE
    SYNTAX      Gauge32
    MAX-ACCESS  read-only
    STATUS      current
    DESCRIPTION 
        "Maximum number of incoming mail server sessions simultaneously active since the system was started. A session is defined as a complete dialog between the execution server and the incoming mail server, and includes elements such as mailbox information requests, message download requests, and idle time."
    ::= { imsStats 5 }

  bwIMSAvgSessions OBJECT-TYPE
    SYNTAX      Gauge32
    MAX-ACCESS  read-only
    STATUS      current
    DESCRIPTION 
        "Average number of incoming mail server sessions simultaneously active, based on a rolling average over the last 100 sessions.  Each data point is computed right after the creation of a session. A session is defined as a complete dialog between the execution server and the incoming mail server, and includes elements such as mailbox information requests, message download requests, and idle time."
    ::= { imsStats 6 }

  bwIMSMaxThreads OBJECT-TYPE
    SYNTAX      Gauge32
    MAX-ACCESS  read-only
    STATUS      current
    DESCRIPTION 
        "Maximum number of incoming mail server threads simultaneously active since the system was started.  IMS threads are used when a session actively communicates with an IMS, and waits for a response.  A session does not use an IMS thread while it is idle, e.g. prompting or waiting for user input."
    ::= { imsStats 7 }

  bwIMSAvgThreads OBJECT-TYPE
    SYNTAX      Gauge32
    MAX-ACCESS  read-only
    STATUS      current
    DESCRIPTION 
        "Average number of incoming mail server threads simultaneously active, based on a rolling average over the last 100 sessions. Each data point is computed right after the creation of a session. IMS threads are used when a session actively communicates with an IMS, and waits for a response.  A session does not use an IMS thread while it is idle, e.g. prompting or waiting for user input."
    ::= { imsStats 8 }

  bwIMSMaxServiceTime OBJECT-TYPE
    SYNTAX      Gauge32
    MAX-ACCESS  read-only
    STATUS      current
    DESCRIPTION 
        "Maximum time in milliseconds required to process an incoming mail server request, since the system was started.  This service time includes any queuing time if applicable.  This time also includes the time required by the IMS to respond to a request such as a mailbox information request, or a message download request."
    ::= { imsStats 9 }

  bwIMSAvgServiceTime OBJECT-TYPE
    SYNTAX      Gauge32
    MAX-ACCESS  read-only
    STATUS      current
    DESCRIPTION 
        "Average time in milliseconds required to process an incoming mail server request, based on a rolling average over the last 100 requests.  This service time includes any queuing time if applicable.  This time also includes the time required by the IMS to respond to a request such as a mailbox information request, or a message download request."
    ::= { imsStats 10 }

  bwIMSNumKeepAlive OBJECT-TYPE
    SYNTAX      Counter32
    MAX-ACCESS  read-write
    STATUS      current
    DESCRIPTION 
        "Number of times a keep-alive message was sent to an incoming mail server.  Such a keep-alive message is sent when an IMS session lasts several minutes."
    ::= { imsStats 11 }

  bwIMSNumDroppedRequests OBJECT-TYPE
    SYNTAX      Counter32
    MAX-ACCESS  read-write
    STATUS      current
    DESCRIPTION 
        "Number of incoming mail server requests dropped because the number of IMS threads was too low, and the queue was full.  Note that a single session can make several requests to the IMS."
    ::= { imsStats 12 }

-- Persistence :: TimesTen  ...........................................

  timesTen OBJECT IDENTIFIER
    ::= { databaseStats 1 }

  ttNbConnectionsCreated OBJECT-TYPE
    SYNTAX      Counter32
    MAX-ACCESS  read-write
    STATUS      current
    DESCRIPTION 
        "Number of total transaction created to the database"
    ::= { timesTen 1 }

  ttConnectionPoolSize OBJECT-TYPE
    SYNTAX      Gauge32
    MAX-ACCESS  read-only
    STATUS      current
    DESCRIPTION 
        "Current size of the database connection pool"
    ::= { timesTen 2 }

  xsRemoteXla OBJECT IDENTIFIER
    ::= { timesTen 5 }

  xsRemoteXlaNbTimesConnected OBJECT-TYPE
    SYNTAX      Counter32
    MAX-ACCESS  read-write
    STATUS      current
    DESCRIPTION 
        "Number of times a connection was made to the RemoteXla server"
    ::= { xsRemoteXla 1 }

  xsRemoteXlaNbTimesDisconnected OBJECT-TYPE
    SYNTAX      Counter32
    MAX-ACCESS  read-write
    STATUS      current
    DESCRIPTION 
        "Number of times the process was disconnected from the RemoteXla server"
    ::= { xsRemoteXla 2 }

  xsRemoteXlaUpdatesProcessed OBJECT-TYPE
    SYNTAX      Counter32
    MAX-ACCESS  read-write
    STATUS      current
    DESCRIPTION 
        "Number of XLA updates processed"
    ::= { xsRemoteXla 3 }

  xsRemoteXlaUpdatesPending OBJECT-TYPE
    SYNTAX      Gauge32
    MAX-ACCESS  read-write
    STATUS      current
    DESCRIPTION 
        "Number of XLA updates pending to be processed"
    ::= { xsRemoteXla 4 }

  bwXSAvgUpdateTime OBJECT-TYPE
    SYNTAX      Gauge32
    MAX-ACCESS  read-only
    STATUS      current
    DESCRIPTION 
        "Average DB update time in milliseconds"
    ::= { timesTen 6 }

  bwXSAvgRowsUpdated OBJECT-TYPE
    SYNTAX      Gauge32
    MAX-ACCESS  read-only
    STATUS      current
    DESCRIPTION 
        "Average number of rows affected in DB updates"
    ::= { timesTen 7 }

  bwXSAvgQueryTime OBJECT-TYPE
    SYNTAX      Gauge32
    MAX-ACCESS  read-only
    STATUS      current
    DESCRIPTION 
        "Average DB query time in milliseconds"
    ::= { timesTen 8 }

  bwXSAvgRowsQueried OBJECT-TYPE
    SYNTAX      Gauge32
    MAX-ACCESS  read-only
    STATUS      current
    DESCRIPTION 
        "Average number of rows processed in DB queries"
    ::= { timesTen 9 }

  bwXSUpdateCount OBJECT-TYPE
    SYNTAX      Counter32
    MAX-ACCESS  read-write
    STATUS      current
    DESCRIPTION 
        "Number of DB updates performed since the application started"
    ::= { timesTen 10 }

  bwXSQueryCount OBJECT-TYPE
    SYNTAX      Counter32
    MAX-ACCESS  read-write
    STATUS      current
    DESCRIPTION 
        "Number of DB queries performed since the application started"
    ::= { timesTen 11 }

  bwXSTTHWMTable OBJECT-TYPE
    SYNTAX      SEQUENCE OF BwXSTTHWMEntry
    MAX-ACCESS  not-accessible
    STATUS      current
    DESCRIPTION 
        "This table contains counters for the XS TimesTen high water marks."
    ::= { timesTen 12 }

  bwXSTTHWMEntry OBJECT-TYPE
    SYNTAX      BwXSTTHWMEntry
    MAX-ACCESS  not-accessible
    STATUS      current
    DESCRIPTION 
        "Definition of the entries for bwXSTTHWMTable."
    INDEX       { bwXSTTHWMIndex }
    ::= { bwXSTTHWMTable 1 }

  BwXSTTHWMEntry ::= SEQUENCE {
    bwXSTTHWMIndex          Unsigned32,
    bwXSTTHWMName           DisplayString,
    bwXSTTHWMValue          Gauge32,
    bwXSTTHWMTimestamp      DisplayString,
    bwXSTTHWMStackTrace     DisplayString
  }

  bwXSTTHWMIndex OBJECT-TYPE
    SYNTAX      Unsigned32
    MAX-ACCESS  read-only
    STATUS      current
    DESCRIPTION 
        "This integer represents an index in table bwXSTTHWMTable. This is the index to a specific high water mark."
    ::= { bwXSTTHWMEntry 1 }

  bwXSTTHWMName OBJECT-TYPE
    SYNTAX      DisplayString
    MAX-ACCESS  read-only
    STATUS      current
    DESCRIPTION 
        "The name of an XS TimesTen high water mark."
    ::= { bwXSTTHWMEntry 2 }

  bwXSTTHWMValue OBJECT-TYPE
    SYNTAX      Gauge32
    MAX-ACCESS  read-write
    STATUS      current
    DESCRIPTION 
        "The value of an XS TimesTen high water mark."
    ::= { bwXSTTHWMEntry 3 }

  bwXSTTHWMTimestamp OBJECT-TYPE
    SYNTAX      DisplayString
    MAX-ACCESS  read-write
    STATUS      current
    DESCRIPTION 
        "The timestamp of an XS TimesTen high water mark."
    ::= { bwXSTTHWMEntry 4 }

  bwXSTTHWMStackTrace OBJECT-TYPE
    SYNTAX      DisplayString
    MAX-ACCESS  read-write
    STATUS      current
    DESCRIPTION 
        "The stack trace of an XS TimesTen high water mark."
    ::= { bwXSTTHWMEntry 5 }

  bwXSTimesTenNbOpenedTransactions OBJECT-TYPE
    SYNTAX      Gauge32
    MAX-ACCESS  read-only
    STATUS      current
    DESCRIPTION 
        "The number of opened transaction with the timesten database"
    ::= { timesTen 13 }

  bwXSTimesTenNbCommittedTransactions OBJECT-TYPE
    SYNTAX      Counter32
    MAX-ACCESS  read-write
    STATUS      current
    DESCRIPTION 
        "The total number of committed transactions to the timesten database since the last restart"
    ::= { timesTen 14 }

  bwXSTimesTenNbFailedTransactions OBJECT-TYPE
    SYNTAX      Counter32
    MAX-ACCESS  read-write
    STATUS      current
    DESCRIPTION 
        "The number of failed transactions with the timesten database"
    ::= { timesTen 15 }

  bwXSTimesTenNbCriticalErrors OBJECT-TYPE
    SYNTAX      Counter32
    MAX-ACCESS  read-write
    STATUS      current
    DESCRIPTION 
        "The total number of critical errors encountered during processing with the timesten database"
    ::= { timesTen 16 }

  perNbOpenedTransactions OBJECT-TYPE
    SYNTAX      Gauge32
    MAX-ACCESS  read-only
    STATUS      current
    DESCRIPTION 
        "Number of opened transaction with the database"
    ::= { databaseStats 2 }

  perNbCommittedTransactions OBJECT-TYPE
    SYNTAX      Counter32
    MAX-ACCESS  read-write
    STATUS      current
    DESCRIPTION 
        "Total number of committed transactions to the database since the last restart"
    ::= { databaseStats 3 }

  perNbFailedTransactions OBJECT-TYPE
    SYNTAX      Counter32
    MAX-ACCESS  read-write
    STATUS      current
    DESCRIPTION 
        "Number of failed transactions with the database"
    ::= { databaseStats 4 }

  perNbCriticalErrors OBJECT-TYPE
    SYNTAX      Counter32
    MAX-ACCESS  read-write
    STATUS      current
    DESCRIPTION 
        "Total number of critical errors encountered during processing with the database"
    ::= { databaseStats 5 }

-- oracle ...........................................

  oracle OBJECT IDENTIFIER
    ::= { databaseStats 6 }

  bwXSOracleNbOpenedTransactions OBJECT-TYPE
    SYNTAX      Gauge32
    MAX-ACCESS  read-only
    STATUS      current
    DESCRIPTION 
        "The number of opened transaction with the oracle database"
    ::= { oracle 1 }

  bwXSOracleNbCommittedTransactions OBJECT-TYPE
    SYNTAX      Counter32
    MAX-ACCESS  read-write
    STATUS      current
    DESCRIPTION 
        "The total number of committed transactions to the oracle database since the last restart"
    ::= { oracle 2 }

  bwXSOracleNbFailedTransactions OBJECT-TYPE
    SYNTAX      Counter32
    MAX-ACCESS  read-write
    STATUS      current
    DESCRIPTION 
        "The number of failed transactions with the oracle database"
    ::= { oracle 3 }

  bwXSOracleNbCriticalErrors OBJECT-TYPE
    SYNTAX      Counter32
    MAX-ACCESS  read-write
    STATUS      current
    DESCRIPTION 
        "The total number of critical errors encountered during processing with the oracle database"
    ::= { oracle 4 }
    
  bwXSOracleDbCount  OBJECT-TYPE
    SYNTAX      Integer32
    MAX-ACCESS  read-only
    STATUS      current
    DESCRIPTION
        "The number of oracle database defined for this application."
-- @feature:162466              
    ::= { oracle 5 }
  
  bwXSOracleDbStatsTable OBJECT-TYPE
    SYNTAX      SEQUENCE OF BwXSOracleDbStatsEntry
    MAX-ACCESS  not-accessible
    STATUS      current
    DESCRIPTION
        "A list of oracle database entries.  The number of entries is given by the value of bwXSOracleDbCount."
-- @feature:162466              
    ::= { oracle 6 }
  
  bwXSOracleDbStatsEntry OBJECT-TYPE
      SYNTAX      BwXSOracleDbStatsEntry
      MAX-ACCESS  not-accessible
      STATUS      current
      DESCRIPTION
          "An entry containing statistics information applicable to a particular oracle database."
      INDEX   { bwXSOracleDbStatsIndex }
-- @feature:162466            
    ::= { bwXSOracleDbStatsTable 1 }
    
  BwXSOracleDbStatsEntry ::= SEQUENCE {
    bwXSOracleDbStatsIndex           Unsigned32,
    bwXSOracleDbName                 DisplayString,
    bwXSOracleDbNbConnectionsCreated Counter32,
    bwXSOracleDbConnectionPoolSize   Gauge32,
    bwXSOracleDbAvgUpdateTime        Gauge32,
    bwXSOracleDbAvgRowsUpdated       Gauge32,
    bwXSOracleDbAvgQueryTime         Gauge32,
    bwXSOracleDbAvgRowsQueried       Gauge32,
    bwXSOracleDbUpdateCount          Counter32,
    bwXSOracleDbQueryCount           Counter32
  }
  
   bwXSOracleDbStatsIndex OBJECT-TYPE
     SYNTAX      Unsigned32
     MAX-ACCESS  read-only
     STATUS      current
     DESCRIPTION 
         "This integer represents an OracleDb database index in the table."
-- @feature:162466               
   ::= { bwXSOracleDbStatsEntry 1 }
   
   bwXSOracleDbName OBJECT-TYPE
     SYNTAX      DisplayString
     MAX-ACCESS  read-only
     STATUS      current
     DESCRIPTION 
         "This string represents the oracle database name."
-- @feature:162466               
   ::= { bwXSOracleDbStatsEntry 2 }
   
   bwXSOracleDbNbConnectionsCreated OBJECT-TYPE
      SYNTAX      Counter32
      MAX-ACCESS  read-only
      STATUS      current
      DESCRIPTION 
          "Number of total connection created to the oracle database."
-- @feature:162466                
   ::= { bwXSOracleDbStatsEntry 3 }
   
   bwXSOracleDbConnectionPoolSize OBJECT-TYPE
      SYNTAX      Gauge32
      MAX-ACCESS  read-only
      STATUS      current
      DESCRIPTION 
          "Number of connections residing in the oracle database connection pool."
-- @feature:162466                
   ::= { bwXSOracleDbStatsEntry 4 }
   
   bwXSOracleDbAvgUpdateTime OBJECT-TYPE
      SYNTAX      Gauge32
      MAX-ACCESS  read-only
      STATUS      current
      DESCRIPTION 
          "Average oracle DB update time in milliseconds."
-- @feature:162466                
   ::= { bwXSOracleDbStatsEntry 5 }
   
   bwXSOracleDbAvgRowsUpdated OBJECT-TYPE
      SYNTAX      Gauge32
      MAX-ACCESS  read-only
      STATUS      current
      DESCRIPTION 
          "Average number of rows affected in oracle DB updates."
-- @feature:162466                
   ::= { bwXSOracleDbStatsEntry 6 }
   
   bwXSOracleDbAvgQueryTime OBJECT-TYPE
      SYNTAX      Gauge32
      MAX-ACCESS  read-only
      STATUS      current
      DESCRIPTION 
          "Average oracle DB query time in milliseconds."
-- @feature:162466                
   ::= { bwXSOracleDbStatsEntry 7 }
   
   bwXSOracleDbAvgRowsQueried OBJECT-TYPE
      SYNTAX      Gauge32
      MAX-ACCESS  read-only
      STATUS      current
      DESCRIPTION 
          "Average number of rows processed in oracle DB queries."
-- @feature:162466                
   ::= { bwXSOracleDbStatsEntry 8 }
   
   bwXSOracleDbUpdateCount OBJECT-TYPE
      SYNTAX      Counter32
      MAX-ACCESS  read-only
      STATUS      current
      DESCRIPTION 
          "Number of oracle DB updates performed since the application started."
-- @feature:162466                
   ::= { bwXSOracleDbStatsEntry 9 }
   
   bwXSOracleDbQueryCount OBJECT-TYPE
      SYNTAX      Counter32
      MAX-ACCESS  read-only
      STATUS      current
      DESCRIPTION 
          "Number of oracle DB queries performed since the application started."
-- @feature:162466                
   ::= { bwXSOracleDbStatsEntry 10 }
      
   bwXSOracleDbHWMTable OBJECT-TYPE
       SYNTAX      SEQUENCE OF BwXSOracleDbHWMEntry
       MAX-ACCESS  not-accessible
       STATUS      current
       DESCRIPTION
           "A list of oracle database High Water Mark entries.  The number of entries is given by the value of bwXSOracleDbCount."
-- @feature:162466                 
       ::= { oracle 7 }
     
     bwXSOracleDbHWMEntry OBJECT-TYPE
         SYNTAX      BwXSOracleDbHWMEntry
         MAX-ACCESS  not-accessible
         STATUS      current
         DESCRIPTION
             "An entry containing high water mark information applicable to a particular oracle database."
         INDEX   { bwXSOracleDbHWMIndex }
-- @feature:162466               
    ::= { bwXSOracleDbHWMTable 1 }
    
    BwXSOracleDbHWMEntry ::= SEQUENCE {
        bwXSOracleDbHWMIndex           Unsigned32,
        bwXSOracleDbHWMDbName          DisplayString,
        bwXSOracleDbHWMStatName        DisplayString,
        bwXSOracleDbHWMStatValue       Gauge32,
        bwXSOracleDbHWMTimestamp       DisplayString,
        bwXSOracleDbHWMStackTrace      DisplayString
    }
    
    bwXSOracleDbHWMIndex OBJECT-TYPE
         SYNTAX      Unsigned32
         MAX-ACCESS  read-only
         STATUS      current
         DESCRIPTION 
             "This integer represents an OracleDb database index in the table."
-- @feature:162466                   
    ::= { bwXSOracleDbHWMEntry 1 }
       
    bwXSOracleDbHWMDbName OBJECT-TYPE
         SYNTAX      DisplayString
         MAX-ACCESS  read-only
         STATUS      current
         DESCRIPTION 
             "This string represents the oracle database name."
-- @feature:162466                   
    ::= { bwXSOracleDbHWMEntry 2 }
    
    bwXSOracleDbHWMStatName OBJECT-TYPE
         SYNTAX      DisplayString
         MAX-ACCESS  read-only
         STATUS      current
         DESCRIPTION 
             "This string represents the statistic name."
-- @feature:162466                   
   ::= { bwXSOracleDbHWMEntry 3 }
   
    bwXSOracleDbHWMStatValue OBJECT-TYPE
         SYNTAX      Gauge32
         MAX-ACCESS  read-only
         STATUS      current
         DESCRIPTION 
             "This is the statistic value."
-- @feature:162466                   
   ::= { bwXSOracleDbHWMEntry 4 }
   
    bwXSOracleDbHWMTimestamp OBJECT-TYPE
         SYNTAX      DisplayString
         MAX-ACCESS  read-only
         STATUS      current
         DESCRIPTION 
             "This string represents the timestamp of the high water mark."
-- @feature:162466                   
   ::= { bwXSOracleDbHWMEntry 5 }
   
    bwXSOracleDbHWMStackTrace OBJECT-TYPE
         SYNTAX      DisplayString
         MAX-ACCESS  read-only
         STATUS      current
         DESCRIPTION 
             "This string represents the stack trace when the high water mark occured."
-- @feature:162466                   
   ::= { bwXSOracleDbHWMEntry 6 }
  

-- CallP ...........................................

  bwCallpNetworkOriginationAttempts OBJECT-TYPE
    SYNTAX      Counter32
    MAX-ACCESS  read-write
    STATUS      current
    DESCRIPTION 
        "This count indicates the total number of originations
         from the network."
    ::= { callpStats 1 }

  bwCallpNetworkTerminationAttempts OBJECT-TYPE
    SYNTAX      Counter32
    MAX-ACCESS  read-write
    STATUS      current
    DESCRIPTION 
        "This count indicates the total number of termination
         attempts to the network."
    ::= { callpStats 2 }

  bwCallpNetworkTerminationsAnswered OBJECT-TYPE
    SYNTAX      Counter32
    MAX-ACCESS  read-write
    STATUS      current
    DESCRIPTION 
        "This count indicates the total number of termination
         attempts to the network answered."
    ::= { callpStats 3 }

  bwCallpUserOriginationAttempts OBJECT-TYPE
    SYNTAX      Counter32
    MAX-ACCESS  read-write
    STATUS      current
    DESCRIPTION 
        "This counts indicates the total number of origination
         attempts from the access network(BroadWorks user/virtual user)."
    ::= { callpStats 4 }

  bwCallpUserTerminationAttempts OBJECT-TYPE
    SYNTAX      Counter32
    MAX-ACCESS  read-write
    STATUS      current
    DESCRIPTION 
        "This counts indicates the total number of termination
         attempts to the access network(BroadWorks user/virtual user)."
    ::= { callpStats 5 }

  bwCallpUserTerminationsAnswered OBJECT-TYPE
    SYNTAX      Counter32
    MAX-ACCESS  read-write
    STATUS      current
    DESCRIPTION 
        "This counts indicates the total number of termination
         attempts to the access network answered."
    ::= { callpStats 6 }

  bwCallpEmergencyCallAttempts OBJECT-TYPE
    SYNTAX      Counter32
    MAX-ACCESS  read-write
    STATUS      current
    DESCRIPTION 
        "This counter represents the number of Emergency call originations made by user's of the system"
    ::= { callpStats 7 }

  bwCallpEmergencyCallAlarms OBJECT-TYPE
    SYNTAX      Counter32
    MAX-ACCESS  read-write
    STATUS      current
    DESCRIPTION 
        "The counter represents the number of times an alarm is generated for an emergency call routing failure"
    ::= { callpStats 8 }

  bwCallpSPTable OBJECT-TYPE
    SYNTAX      SEQUENCE OF BwCallpSPEntry
    MAX-ACCESS  not-accessible
    STATUS      current
    DESCRIPTION 
        "This table contains the counters for CallP measurements for service providers"
    ::= { callpStats 9 }

  bwCallpSPEntry OBJECT-TYPE
    SYNTAX      BwCallpSPEntry
    MAX-ACCESS  not-accessible
    STATUS      current
    DESCRIPTION 
        "This row contains the counters for CallP measurements for a service provider"
    INDEX       { bwCallpSPIndex }
    ::= { bwCallpSPTable 1 }

  BwCallpSPEntry ::= SEQUENCE {
    bwCallpSPIndex                                      Unsigned32,
    bwCallpSPID                                         DisplayString,
    bwCallpSPUserOriginationAttempts                    Counter32,
    bwCallpSPUserTerminationAttempts                    Counter32,
    bwCallpSPUserTerminationsAnswered                   Counter32,
    bwCallpSPEmergencyCallAttempts                      Counter32,
    bwCallpSPMaximumNumberofSimCallsExceeded            Counter32,
    bwCallpSPMaximumCallTimeforAnsweredCallsExceeded    Counter32,
    bwCallpSPMaximumCallTimeforUnansweredCallsExceeded  Counter32,
    bwCallpSPMaximumNumberofSimVideoCallsExceeded       Counter32,
    bwCallpSPMediaTypeNotSupported                      Counter32
  }

  bwCallpSPIndex OBJECT-TYPE
    SYNTAX      Unsigned32
    MAX-ACCESS  read-only
    STATUS      current
    DESCRIPTION 
        "This integer represents the a service provider index in the system"
    ::= { bwCallpSPEntry 1 }

  bwCallpSPID OBJECT-TYPE
    SYNTAX      DisplayString
    MAX-ACCESS  read-only
    STATUS      current
    DESCRIPTION 
        "This string represents a service provider ID"
    ::= { bwCallpSPEntry 2 }

  bwCallpSPUserOriginationAttempts OBJECT-TYPE
    SYNTAX      Counter32
    MAX-ACCESS  read-write
    STATUS      current
    DESCRIPTION 
        "This counts indicates the total number of origination attempts from the access network(BroadWorks user/virtual user) for a service provider"
    ::= { bwCallpSPEntry 3 }

  bwCallpSPUserTerminationAttempts OBJECT-TYPE
    SYNTAX      Counter32
    MAX-ACCESS  read-write
    STATUS      current
    DESCRIPTION 
        "This counts indicates the total number of termination attempts to the access network(BroadWorks user/virtual user) for a service provider"
    ::= { bwCallpSPEntry 4 }

  bwCallpSPUserTerminationsAnswered OBJECT-TYPE
    SYNTAX      Counter32
    MAX-ACCESS  read-write
    STATUS      current
    DESCRIPTION 
        "This counts indicates the total number of termination attempts to the access network answered for a service provider"
    ::= { bwCallpSPEntry 5 }

  bwCallpSPEmergencyCallAttempts OBJECT-TYPE
    SYNTAX      Counter32
    MAX-ACCESS  read-write
    STATUS      current
    DESCRIPTION 
        "This counter represents the number of Emergency call originations made by Broadworks users for a service provider"
    ::= { bwCallpSPEntry 6 }

  bwCallpSPMaximumNumberofSimCallsExceeded OBJECT-TYPE
    SYNTAX      Counter32
    MAX-ACCESS  read-write
    STATUS      current
    DESCRIPTION 
        "This counter reflects the number of times that the maximum number of simultaneous calls for a user is exceeded for a service provider."
    ::= { bwCallpSPEntry 7 }

  bwCallpSPMaximumCallTimeforAnsweredCallsExceeded OBJECT-TYPE
    SYNTAX      Counter32
    MAX-ACCESS  read-write
    STATUS      current
    DESCRIPTION 
        "This counter reflects the number of times that the maximum call time for answered calls is exceeded for a service provider."
    ::= { bwCallpSPEntry 8 }

  bwCallpSPMaximumCallTimeforUnansweredCallsExceeded OBJECT-TYPE
    SYNTAX      Counter32
    MAX-ACCESS  read-write
    STATUS      current
    DESCRIPTION 
        "This counter reflects the number of times that the maximum call time for unanswered calls is exceeded for a service provider."
    ::= { bwCallpSPEntry 9 }

  bwCallpSPMaximumNumberofSimVideoCallsExceeded OBJECT-TYPE
    SYNTAX      Counter32
    MAX-ACCESS  read-write
    STATUS      current
    DESCRIPTION 
        "The counter reflects the number of times that the maximum number of simultaneous video calls for a user is exceeded."
    ::= { bwCallpSPEntry 10 }

  bwCallpSPMediaTypeNotSupported OBJECT-TYPE
    SYNTAX      Counter32
    MAX-ACCESS  read-write
    STATUS      current
    DESCRIPTION 
        "The counter reflects the number of times that the media type (codec) within a service provider has not been supported for a user."
    ::= { bwCallpSPEntry 11 }

  bwCallpActiveCalls OBJECT-TYPE
    SYNTAX      Gauge32
    MAX-ACCESS  read-only
    STATUS      current
    DESCRIPTION 
        "This counts indicates the total number of active session.
         An active session is define as an active originating session.
         Any call that needs to perform a lookup in a NetworkServer/LocationServer
         will be counted as 2 calls, once for each call leg."
    ::= { callpStats 10 }

  bwCallpGroupTable OBJECT-TYPE
    SYNTAX      SEQUENCE OF BwCallpGroupEntry
    MAX-ACCESS  not-accessible
    STATUS      current
    DESCRIPTION 
        "This table contains the counters for CallP measurements for groups"
    ::= { callpStats 11 }

  bwCallpGroupEntry OBJECT-TYPE
    SYNTAX      BwCallpGroupEntry
    MAX-ACCESS  not-accessible
    STATUS      current
    DESCRIPTION 
        "This row contains the counters for CallP measurements for a group"
    INDEX       { bwCallpGroupIndex }
    ::= { bwCallpGroupTable 1 }

  BwCallpGroupEntry ::= SEQUENCE {
    bwCallpGroupIndex                                       Unsigned32,
    bwCallpGroupID                                          DisplayString,
    bwCallpGroupUserOriginationAttempts                     Counter32,
    bwCallpGroupUserTerminationAttempts                     Counter32,
    bwCallpGroupUserTerminationsAnswered                    Counter32,
    bwCallpGroupEmergencyCallAttempts                       Counter32,
    bwCallpGroupMaximumNumberofSimCallsExceeded             Counter32,
    bwCallpGroupMaximumCallTimeforAnsweredCallsExceeded     Counter32,
    bwCallpGroupMaximumCallTimeforUnansweredCallsExceeded   Counter32,
    bwCallpGroupMaximumNumberofSimVideoCallsExceeded        Counter32,
    bwCallpGroupMediaTypeNotSupported                       Counter32
  }

  bwCallpGroupIndex OBJECT-TYPE
    SYNTAX      Unsigned32
    MAX-ACCESS  read-only
    STATUS      current
    DESCRIPTION 
        "This integer represents the a group index in the system"
    ::= { bwCallpGroupEntry 1 }

  bwCallpGroupID OBJECT-TYPE
    SYNTAX      DisplayString
    MAX-ACCESS  read-only
    STATUS      current
    DESCRIPTION 
        "This string represents a group ID"
    ::= { bwCallpGroupEntry 2 }

  bwCallpGroupUserOriginationAttempts OBJECT-TYPE
    SYNTAX      Counter32
    MAX-ACCESS  read-write
    STATUS      current
    DESCRIPTION 
        "This counts indicates the total number of origination attempts from the access network(BroadWorks user/virtual user) for a group"
    ::= { bwCallpGroupEntry 3 }

  bwCallpGroupUserTerminationAttempts OBJECT-TYPE
    SYNTAX      Counter32
    MAX-ACCESS  read-write
    STATUS      current
    DESCRIPTION 
        "This counts indicates the total number of termination attempts to the access network(BroadWorks user/virtual user) for a group"
    ::= { bwCallpGroupEntry 4 }

  bwCallpGroupUserTerminationsAnswered OBJECT-TYPE
    SYNTAX      Counter32
    MAX-ACCESS  read-write
    STATUS      current
    DESCRIPTION 
        "This counts indicates the total number of termination attempts to the access network answered for a group"
    ::= { bwCallpGroupEntry 5 }

  bwCallpGroupEmergencyCallAttempts OBJECT-TYPE
    SYNTAX      Counter32
    MAX-ACCESS  read-write
    STATUS      current
    DESCRIPTION 
        "This counter represents the number of Emergency call originations made by Broadworks users for a group"
    ::= { bwCallpGroupEntry 6 }

  bwCallpGroupMaximumNumberofSimCallsExceeded OBJECT-TYPE
    SYNTAX      Counter32
    MAX-ACCESS  read-write
    STATUS      current
    DESCRIPTION 
        "This counter reflects the number of times that the maximum number of simultaneous calls for a user is exceeded for a group."
    ::= { bwCallpGroupEntry 7 }

  bwCallpGroupMaximumCallTimeforAnsweredCallsExceeded OBJECT-TYPE
    SYNTAX      Counter32
    MAX-ACCESS  read-write
    STATUS      current
    DESCRIPTION 
        "This counter reflects the number of times that the maximum call time for answered calls is exceeded for a group."
    ::= { bwCallpGroupEntry 8 }

  bwCallpGroupMaximumCallTimeforUnansweredCallsExceeded OBJECT-TYPE
    SYNTAX      Counter32
    MAX-ACCESS  read-write
    STATUS      current
    DESCRIPTION 
        "This counter reflects the number of times that the maximum call time for unanswered calls is exceeded for a group."
    ::= { bwCallpGroupEntry 9 }

  bwCallpGroupMaximumNumberofSimVideoCallsExceeded OBJECT-TYPE
    SYNTAX      Counter32
    MAX-ACCESS  read-write
    STATUS      current
    DESCRIPTION 
        "This counter reflects the number of times that the maximum number of simultaneous video calls for a user is exceeded."
    ::= { bwCallpGroupEntry 10 }

  bwCallpGroupMediaTypeNotSupported OBJECT-TYPE
    SYNTAX      Counter32
    MAX-ACCESS  read-write
    STATUS      current
    DESCRIPTION 
        "This counter reflects the number of times that a call is rejected because the media type was not valid for a user."
    ::= { bwCallpGroupEntry 11 }

  bwCallpCallsPerSecond OBJECT-TYPE
    SYNTAX      Gauge32
    MAX-ACCESS  read-only
    STATUS      current
    DESCRIPTION 
        "This gauge measures the rate at which network origination attempts and user origination attempts occur.  It uses the timestamps of up to the last 100 network origination attempts and user origination attempts in calculating the rate.  The criteria for capturing such attempts is the same as that for pegging the bwCallPNetworkOriginationAttempts and bwCallPUserOriginationAttempts PM's."
    ::= { callpStats 12 }

  bwCallpMaximumNumberofSimCallsExceeded OBJECT-TYPE
    SYNTAX      Counter32
    MAX-ACCESS  read-write
    STATUS      current
    DESCRIPTION 
        "This counter reflects the number of times that the maximum number of simultaneous calls for a user is exceeded."
    ::= { callpStats 13 }

  bwCallpMaximumCallTimeforAnsweredCallsExceeded OBJECT-TYPE
    SYNTAX      Counter32
    MAX-ACCESS  read-write
    STATUS      current
    DESCRIPTION 
        "This counter reflects the number of times that the maximum call time for answered calls is exceeded."
    ::= { callpStats 14 }

  bwCallpMaximumCallTimeforUnansweredCallsExceeded OBJECT-TYPE
    SYNTAX      Counter32
    MAX-ACCESS  read-write
    STATUS      current
    DESCRIPTION 
        "This counter reflects the number of times that the maximum call time for unanswered calls is exceeded."
    ::= { callpStats 15 }

  bwCallpActiveCallsAsPercentOfLicense OBJECT-TYPE
    SYNTAX      Gauge32
    MAX-ACCESS  read-only
    STATUS      current
    DESCRIPTION 
        "This gauge reports the number of active calls as a percentage of the maximum concurrent calls licensed value. If the concurrent calls licensed value is unlimited, the gauge is zero."
    ::= { callpStats 16 }

  bwCallpMaximumNumberofSimVideoCallsExceeded OBJECT-TYPE
    SYNTAX      Counter32
    MAX-ACCESS  read-write
    STATUS      current
    DESCRIPTION 
        "This counter reflects the number of times that the maximum number of simultaneous video calls for a user is exceeded."
    ::= { callpStats 17 }

  bwCallpMediaTypeNotSupported OBJECT-TYPE
    SYNTAX      Counter32
    MAX-ACCESS  read-write
    STATUS      current
    DESCRIPTION 
        "This counter reflects the number of times that the media type (codec) has not been supported for a user."
    ::= { callpStats 18 }

  bwCallpRemoteOfficeEmergencyCallsBlocked OBJECT-TYPE
    SYNTAX      Counter32
    MAX-ACCESS  read-write
    STATUS      current
    DESCRIPTION 
        "This is the number of times an emergency call origination attempt from a network location (i.e. remote office or BroadWorks anywhere) has been blocked."
    ::= { callpStats 19 }

  bwStateReplicationMessageSent OBJECT-TYPE
    SYNTAX      Counter32
    MAX-ACCESS  read-write
    STATUS      current
    DESCRIPTION 
        "This is the number of state replication messages sent to the peer server."
    ::= { callpStats 20 }

  bwStateReplicationMessageReceived OBJECT-TYPE
    SYNTAX      Counter32
    MAX-ACCESS  read-write
    STATUS      current
    DESCRIPTION 
        "This is the number of state replication messages received from the peer server."
    ::= { callpStats 21 }

  bwStateReplicationOwnershipTaken OBJECT-TYPE
    SYNTAX      Counter32
    MAX-ACCESS  read-write
    STATUS      current
    DESCRIPTION 
        "This is the number of call processing migration units that this server has taken over ownership."
    ::= { callpStats 22 }

  bwStateReplicationOwnershipGranted OBJECT-TYPE
    SYNTAX      Counter32
    MAX-ACCESS  read-write
    STATUS      current
    DESCRIPTION 
        "This is the number of call processing migration units that this server has relinquished ownership."
    ::= { callpStats 23 }

  bwStateReplicationRemoteLockTaken OBJECT-TYPE
    SYNTAX      Counter32
    MAX-ACCESS  read-write
    STATUS      current
    DESCRIPTION 
        "This is the number of shared data locks that this server has taken over ownership."
    ::= { callpStats 24 }

  bwStateReplicationRemoteLockGranted OBJECT-TYPE
    SYNTAX      Counter32
    MAX-ACCESS  read-write
    STATUS      current
    DESCRIPTION 
        "This is the number of shared data locks that this server relinquished ownership."
    ::= { callpStats 25 }

  bwCallpSystemServiceSimultaneousCallsExceeded OBJECT-TYPE
    SYNTAX      Counter32
    MAX-ACCESS  read-write
    STATUS      current
    DESCRIPTION 
        "This is the number of times that the maximum number of simultaneous calls for a system service is exceeded."
-- @feature:142137
    ::= { callpStats 26 }

  bwCallpSystemServiceSimultaneousVideoCallsExceeded OBJECT-TYPE
    SYNTAX      Counter32
    MAX-ACCESS  read-write
    STATUS      current
    DESCRIPTION 
        "This is the number of times that the maximum number of simultaneous video calls for a system service is exceeded."
-- @feature:142137
    ::= { callpStats 27 }

  bwCallpSystemServiceMaximumCallTimeforAnsweredCallsExceeded OBJECT-TYPE
    SYNTAX      Counter32
    MAX-ACCESS  read-write
    STATUS      current
    DESCRIPTION 
        "This is the number of times that the maximum call time for answered calls by a system service  is exceeded."
-- @feature:142137
    ::= { callpStats 28 }

  bwCallpSystemServiceRedirectCallsExceeded OBJECT-TYPE
    SYNTAX      Counter32
    MAX-ACCESS  read-write
    STATUS      current
    DESCRIPTION 
        "This is the number of times that the maximum number of redirection by a system service is exceeded."
-- @feature:142137
    ::= { callpStats 29 }

  bwRedundancyMessageSent OBJECT-TYPE
    SYNTAX      Counter32
    MAX-ACCESS  read-write
    STATUS      current
    DESCRIPTION 
        "This is the number of redundancy messages sent to the peer server."
-- @feature:176431
    ::= { callpStats 30 }

  bwRedundancyMessageReceived OBJECT-TYPE
    SYNTAX      Counter32
    MAX-ACCESS  read-write
    STATUS      current
    DESCRIPTION 
        "This is the number of redundancy messages received from the peer server."
-- @feature:176431
    ::= { callpStats 31 }

  bwRedundancyLinkFailureCount OBJECT-TYPE
    SYNTAX      Counter32
    MAX-ACCESS  read-write
    STATUS      current
    DESCRIPTION 
        "This is the number of redundancy link failures detected"
-- @feature:176431
    ::= { callpStats 32 }

  bwRedundancyLinkFailureCountTimeMSB OBJECT-TYPE
    SYNTAX      Gauge32
    MAX-ACCESS  read-only
    STATUS      current
    DESCRIPTION 
        "The most significant part of the timestamp (4 most significant bytes) of when the last redundancy link failure was detected."
-- @feature:176431
    ::= { callpStats 33 }

  bwRedundancyLinkFailureCountTimeLSB OBJECT-TYPE
    SYNTAX      Gauge32
    MAX-ACCESS  read-only
    STATUS      current
    DESCRIPTION 
        "The least significant part of the timestamp (4 least significant bytes) of when the last redundancy link failure was detected."
-- @feature:176431
    ::= { callpStats 34 }

-- Protocol :: SMTP ...........................................

  bwSMTPTotalPrimaryEmailSendAttempts OBJECT-TYPE
    SYNTAX      Counter32
    MAX-ACCESS  read-write
    STATUS      current
    DESCRIPTION 
        "This counter reflects the total number of message send attempted on the primary SMTP server."
    ::= { smtpStats 1 }

  bwSMTPTotalSecondaryEmailSendAttempts OBJECT-TYPE
    SYNTAX      Counter32
    MAX-ACCESS  read-write
    STATUS      current
    DESCRIPTION 
        "This counter reflects the total number of message send attempted on the secondary SMTP server."
    ::= { smtpStats 2 }

  bwSMTPPrimaryUnSuccessfulEmailSendAttempts OBJECT-TYPE
    SYNTAX      Counter32
    MAX-ACCESS  read-write
    STATUS      current
    DESCRIPTION 
        "This counter reflects the total number of message deliveries that failed on the primary SMTP server. This counter does not reflect SMTP failures on the Media Server."
    ::= { smtpStats 3 }

  bwSMTPSecondaryUnSuccessfulEmailSendAttempts OBJECT-TYPE
    SYNTAX      Counter32
    MAX-ACCESS  read-write
    STATUS      current
    DESCRIPTION 
        "This counter reflects the total number of message deliveries that failed on the secondary SMTP server. This counter does not reflect SMTP failures on the Media Server."
    ::= { smtpStats 4 }

-- Protocol :: SIP ...........................................

  bwSipSummaryTotalTransactions OBJECT-TYPE
    SYNTAX      Counter32
    MAX-ACCESS  read-write
    STATUS      current
    DESCRIPTION 
        "This counter contains a count of the number of transactions completed or in progress."
    ::= { sipStats 1 }

  bwSipStatsInviteIns OBJECT-TYPE
    SYNTAX      Counter32
    MAX-ACCESS  read-write
    STATUS      current
    DESCRIPTION 
        "This counter reflects the total number of INVITE requests received by BroadWorks."
    ::= { sipStats 2 }

  bwSipStatsInviteOuts OBJECT-TYPE
    SYNTAX      Counter32
    MAX-ACCESS  read-write
    STATUS      current
    DESCRIPTION 
        "This counter reflects the total number of INVITE requests sent by BroadWorks."
    ::= { sipStats 3 }

  bwSipStatsAckIns OBJECT-TYPE
    SYNTAX      Counter32
    MAX-ACCESS  read-write
    STATUS      current
    DESCRIPTION 
        "This counter reflects the total number of ACK requests received by BroadWorks."
    ::= { sipStats 4 }

  bwSipStatsAckOuts OBJECT-TYPE
    SYNTAX      Counter32
    MAX-ACCESS  read-write
    STATUS      current
    DESCRIPTION 
        "This counter reflects the total number of ACK requests sent by BroadWorks."
    ::= { sipStats 5 }

  bwSipStatsByeIns OBJECT-TYPE
    SYNTAX      Counter32
    MAX-ACCESS  read-write
    STATUS      current
    DESCRIPTION 
        "This counter reflects the total number of BYE requests received by BroadWorks."
    ::= { sipStats 6 }

  bwSipStatsByeOuts OBJECT-TYPE
    SYNTAX      Counter32
    MAX-ACCESS  read-write
    STATUS      current
    DESCRIPTION 
        "This counter reflects the total number of BYE requests sent by BroadWorks."
    ::= { sipStats 7 }

  bwSipStatsCancelIns OBJECT-TYPE
    SYNTAX      Counter32
    MAX-ACCESS  read-write
    STATUS      current
    DESCRIPTION 
        "This counter reflects the total number of CANCEL requests received by BroadWorks."
    ::= { sipStats 8 }

  bwSipStatsCancelOuts OBJECT-TYPE
    SYNTAX      Counter32
    MAX-ACCESS  read-write
    STATUS      current
    DESCRIPTION 
        "This counter reflects the total number of CANCEL requests sent by BroadWorks."
    ::= { sipStats 9 }

  bwSipStatsOptionsIns OBJECT-TYPE
    SYNTAX      Counter32
    MAX-ACCESS  read-write
    STATUS      current
    DESCRIPTION 
        "This counter reflects the total number of OPTIONS requests received by BroadWorks."
    ::= { sipStats 10 }

  bwSipStatsOptionsOuts OBJECT-TYPE
    SYNTAX      Counter32
    MAX-ACCESS  read-write
    STATUS      current
    DESCRIPTION 
        "This counter reflects the total number of OPTIONS requests sent by BroadWorks."
    ::= { sipStats 11 }

  bwSipStatsRegisterIns OBJECT-TYPE
    SYNTAX      Counter32
    MAX-ACCESS  read-write
    STATUS      current
    DESCRIPTION 
        "This counter reflects the total number of REGISTER requests received by BroadWorks."
    ::= { sipStats 12 }

  bwSipStatsRegisterOuts OBJECT-TYPE
    SYNTAX      Counter32
    MAX-ACCESS  read-write
    STATUS      current
    DESCRIPTION 
        "This counter reflects the total number of REGISTER requests sent by BroadWorks."
    ::= { sipStats 13 }

  bwSipStatsInfoIns OBJECT-TYPE
    SYNTAX      Counter32
    MAX-ACCESS  read-write
    STATUS      current
    DESCRIPTION 
        "This counter reflects the total number of INFO requests received by BroadWorks"
    ::= { sipStats 14 }

  bwSipStatsInfoOuts OBJECT-TYPE
    SYNTAX      Counter32
    MAX-ACCESS  read-write
    STATUS      current
    DESCRIPTION 
        "This counter reflects the total number of INFO requests sent by BroadWorks"
    ::= { sipStats 15 }

  bwSipStatsNotifyIns OBJECT-TYPE
    SYNTAX      Counter32
    MAX-ACCESS  read-write
    STATUS      current
    DESCRIPTION 
        "This counter reflects the total number of NOTIFY requests received by BroadWorks"
    ::= { sipStats 16 }

  bwSipStatsNotifyOuts OBJECT-TYPE
    SYNTAX      Counter32
    MAX-ACCESS  read-write
    STATUS      current
    DESCRIPTION 
        "This counter reflects the total number of NOTIFY requests sent by BroadWorks"
    ::= { sipStats 17 }

  bwSipStatsPrackIns OBJECT-TYPE
    SYNTAX      Counter32
    MAX-ACCESS  read-write
    STATUS      current
    DESCRIPTION 
        "This counter reflects the total number of PRACK requests received by BroadWorks"
    ::= { sipStats 18 }

  bwSipStatsPrackOuts OBJECT-TYPE
    SYNTAX      Counter32
    MAX-ACCESS  read-write
    STATUS      current
    DESCRIPTION 
        "This counter reflects the total number of PRACK requests sent by BroadWorks"
    ::= { sipStats 19 }

  bwSipStatsOtherIns OBJECT-TYPE
    SYNTAX      Counter32
    MAX-ACCESS  read-write
    STATUS      current
    DESCRIPTION 
        "This counter reflects the total number of unsupported requests (other than INFO and NOTIFY) received by BroadWorks"
    ::= { sipStats 20 }

  bwSipStatsOtherOuts OBJECT-TYPE
    SYNTAX      Counter32
    MAX-ACCESS  read-write
    STATUS      current
    DESCRIPTION 
        "This counter reflects the total number of UNKNOWN requests sent by BroadWorks"
    ::= { sipStats 21 }

  bwSipStatsInviteResponsesTable OBJECT-TYPE
    SYNTAX      SEQUENCE OF BwSipStatsInviteResponsesEntry
    MAX-ACCESS  not-accessible
    STATUS      current
    DESCRIPTION 
        "This table contains the counters for all SIP responses to the Invite requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 22 }

  bwSipStatsInviteResponsesEntry OBJECT-TYPE
    SYNTAX      BwSipStatsInviteResponsesEntry
    MAX-ACCESS  not-accessible
    STATUS      current
    DESCRIPTION 
        "This row contains information on a particular SIP status code received or sent in response to an Invite"
    INDEX       { bwSipStatsInviteResponseCodeValue }
    ::= { bwSipStatsInviteResponsesTable 1 }

  BwSipStatsInviteResponsesEntry ::= SEQUENCE {
    bwSipStatsInviteResponseCodeValue   Integer32,
    bwSipStatsInviteResponseIns         Counter32,
    bwSipStatsInviteResponseOuts        Counter32
  }

  bwSipStatsInviteResponseCodeValue OBJECT-TYPE
    SYNTAX      Integer32 (100..999)
    MAX-ACCESS  not-accessible
    STATUS      current
    DESCRIPTION 
        "This integer represents a SIP status code.  The rest of the information in this row is related to this value."
    ::= { bwSipStatsInviteResponsesEntry 1 }

  bwSipStatsInviteResponseIns OBJECT-TYPE
    SYNTAX      Counter32
    MAX-ACCESS  read-write
    STATUS      current
    DESCRIPTION 
        "This counter represents the number of SIP responses received in response to an Invite"
    ::= { bwSipStatsInviteResponsesEntry 2 }

  bwSipStatsInviteResponseOuts OBJECT-TYPE
    SYNTAX      Counter32
    MAX-ACCESS  read-write
    STATUS      current
    DESCRIPTION 
        "This counter represents the number of SIP responses sent in response to an Invite"
    ::= { bwSipStatsInviteResponsesEntry 3 }

  bwSipStatsByeResponsesTable OBJECT-TYPE
    SYNTAX      SEQUENCE OF BwSipStatsByeResponsesEntry
    MAX-ACCESS  not-accessible
    STATUS      current
    DESCRIPTION 
        "This table contains the counters for all SIP responses to the BYE requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 23 }

  bwSipStatsByeResponsesEntry OBJECT-TYPE
    SYNTAX      BwSipStatsByeResponsesEntry
    MAX-ACCESS  not-accessible
    STATUS      current
    DESCRIPTION 
        "This row contains information on a particular SIP status code received or sent in response to a Bye"
    INDEX       { bwSipStatsByeResponseCodeValue }
    ::= { bwSipStatsByeResponsesTable 1 }

  BwSipStatsByeResponsesEntry ::= SEQUENCE {
    bwSipStatsByeResponseCodeValue  Integer32,
    bwSipStatsByeResponseIns        Counter32,
    bwSipStatsByeResponseOuts       Counter32
  }

  bwSipStatsByeResponseCodeValue OBJECT-TYPE
    SYNTAX      Integer32 (100..999)
    MAX-ACCESS  not-accessible
    STATUS      current
    DESCRIPTION 
        "This integer represents a SIP status code.  The rest of the information in this row is related to this value."
    ::= { bwSipStatsByeResponsesEntry 1 }

  bwSipStatsByeResponseIns OBJECT-TYPE
    SYNTAX      Counter32
    MAX-ACCESS  read-write
    STATUS      current
    DESCRIPTION 
        "This counter represents the number of SIP responses received in response to a Bye"
    ::= { bwSipStatsByeResponsesEntry 2 }

  bwSipStatsByeResponseOuts OBJECT-TYPE
    SYNTAX      Counter32
    MAX-ACCESS  read-write
    STATUS      current
    DESCRIPTION 
        "This counter represents the number of SIP responses sent in response to a Bye"
    ::= { bwSipStatsByeResponsesEntry 3 }

  bwSipStatsCancelResponsesTable OBJECT-TYPE
    SYNTAX      SEQUENCE OF BwSipStatsCancelResponsesEntry
    MAX-ACCESS  not-accessible
    STATUS      current
    DESCRIPTION 
        "This table contains the counters for all SIP responses to the Cancel requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 24 }

  bwSipStatsCancelResponsesEntry OBJECT-TYPE
    SYNTAX      BwSipStatsCancelResponsesEntry
    MAX-ACCESS  not-accessible
    STATUS      current
    DESCRIPTION 
        "This row contains information on a particular SIP status code received or sent in response to a Cancel"
    INDEX       { bwSipStatsCancelResponseCodeValue }
    ::= { bwSipStatsCancelResponsesTable 1 }

  BwSipStatsCancelResponsesEntry ::= SEQUENCE {
    bwSipStatsCancelResponseCodeValue   Integer32,
    bwSipStatsCancelResponseIns         Counter32,
    bwSipStatsCancelResponseOuts        Counter32
  }

  bwSipStatsCancelResponseCodeValue OBJECT-TYPE
    SYNTAX      Integer32 (100..999)
    MAX-ACCESS  not-accessible
    STATUS      current
    DESCRIPTION 
        "This integer represents a SIP status code.  The rest of the information in this row is related to this value."
    ::= { bwSipStatsCancelResponsesEntry 1 }

  bwSipStatsCancelResponseIns OBJECT-TYPE
    SYNTAX      Counter32
    MAX-ACCESS  read-write
    STATUS      current
    DESCRIPTION 
        "This counter represents the number of SIP responses received in response to a Cancel"
    ::= { bwSipStatsCancelResponsesEntry 2 }

  bwSipStatsCancelResponseOuts OBJECT-TYPE
    SYNTAX      Counter32
    MAX-ACCESS  read-write
    STATUS      current
    DESCRIPTION 
        "This counter represents the number of SIP responses sent in response to a Cancel"
    ::= { bwSipStatsCancelResponsesEntry 3 }

  bwSipStatsOptionsResponsesTable OBJECT-TYPE
    SYNTAX      SEQUENCE OF BwSipStatsOptionsResponsesEntry
    MAX-ACCESS  not-accessible
    STATUS      current
    DESCRIPTION 
        "This table contains the counters for all SIP responses to the Options requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 25 }

  bwSipStatsOptionsResponsesEntry OBJECT-TYPE
    SYNTAX      BwSipStatsOptionsResponsesEntry
    MAX-ACCESS  not-accessible
    STATUS      current
    DESCRIPTION 
        "This row contains information on a particular SIP status code received or sent in response to a Options"
    INDEX       { bwSipStatsOptionsResponseCodeValue }
    ::= { bwSipStatsOptionsResponsesTable 1 }

  BwSipStatsOptionsResponsesEntry ::= SEQUENCE {
    bwSipStatsOptionsResponseCodeValue  Integer32,
    bwSipStatsOptionsResponseIns        Counter32,
    bwSipStatsOptionsResponseOuts       Counter32
  }

  bwSipStatsOptionsResponseCodeValue OBJECT-TYPE
    SYNTAX      Integer32 (100..999)
    MAX-ACCESS  not-accessible
    STATUS      current
    DESCRIPTION 
        "This integer represents a SIP status code.  The rest of the information in this row is related to this value."
    ::= { bwSipStatsOptionsResponsesEntry 1 }

  bwSipStatsOptionsResponseIns OBJECT-TYPE
    SYNTAX      Counter32
    MAX-ACCESS  read-write
    STATUS      current
    DESCRIPTION 
        "This counter represents the number of SIP responses received in response to an Options"
    ::= { bwSipStatsOptionsResponsesEntry 2 }

  bwSipStatsOptionsResponseOuts OBJECT-TYPE
    SYNTAX      Counter32
    MAX-ACCESS  read-write
    STATUS      current
    DESCRIPTION 
        "This counter represents the number of SIP responses sent in response to an Options"
    ::= { bwSipStatsOptionsResponsesEntry 3 }

  bwSipStatsRegisterResponsesTable OBJECT-TYPE
    SYNTAX      SEQUENCE OF BwSipStatsRegisterResponsesEntry
    MAX-ACCESS  not-accessible
    STATUS      current
    DESCRIPTION 
        "This table contains the counters for all SIP responses to the Register requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 26 }

  bwSipStatsRegisterResponsesEntry OBJECT-TYPE
    SYNTAX      BwSipStatsRegisterResponsesEntry
    MAX-ACCESS  not-accessible
    STATUS      current
    DESCRIPTION 
        "This row contains information on a particular SIP status code received or sent in response to a Register"
    INDEX       { bwSipStatsRegisterResponseCodeValue }
    ::= { bwSipStatsRegisterResponsesTable 1 }

  BwSipStatsRegisterResponsesEntry ::= SEQUENCE {
    bwSipStatsRegisterResponseCodeValue     Integer32,
    bwSipStatsRegisterResponseIns           Counter32,
    bwSipStatsRegisterResponseOuts          Counter32
  }

  bwSipStatsRegisterResponseCodeValue OBJECT-TYPE
    SYNTAX      Integer32 (100..999)
    MAX-ACCESS  not-accessible
    STATUS      current
    DESCRIPTION 
        "This integer represents a SIP status code.  The rest of the information in this row is related to this value."
    ::= { bwSipStatsRegisterResponsesEntry 1 }

  bwSipStatsRegisterResponseIns OBJECT-TYPE
    SYNTAX      Counter32
    MAX-ACCESS  read-write
    STATUS      current
    DESCRIPTION 
        "This counter represents the number of SIP responses received in response to a Register"
    ::= { bwSipStatsRegisterResponsesEntry 2 }

  bwSipStatsRegisterResponseOuts OBJECT-TYPE
    SYNTAX      Counter32
    MAX-ACCESS  read-write
    STATUS      current
    DESCRIPTION 
        "This counter represents the number of SIP responses sent in response to a Register"
    ::= { bwSipStatsRegisterResponsesEntry 3 }

  bwSipStatsPrackResponsesTable OBJECT-TYPE
    SYNTAX      SEQUENCE OF BwSipStatsPrackResponsesEntry
    MAX-ACCESS  not-accessible
    STATUS      current
    DESCRIPTION 
        "This table contains the counters for all SIP responses to the Prack requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 27 }

  bwSipStatsPrackResponsesEntry OBJECT-TYPE
    SYNTAX      BwSipStatsPrackResponsesEntry
    MAX-ACCESS  not-accessible
    STATUS      current
    DESCRIPTION 
        "This row contains information on a particular SIP status code received or sent in response to a Prack"
    INDEX       { bwSipStatsPrackResponseCodeValue }
    ::= { bwSipStatsPrackResponsesTable 1 }

  BwSipStatsPrackResponsesEntry ::= SEQUENCE {
    bwSipStatsPrackResponseCodeValue    Integer32,
    bwSipStatsPrackResponseIns          Counter32,
    bwSipStatsPrackResponseOuts         Counter32
  }

  bwSipStatsPrackResponseCodeValue OBJECT-TYPE
    SYNTAX      Integer32 (100..999)
    MAX-ACCESS  not-accessible
    STATUS      current
    DESCRIPTION 
        "This integer represents a SIP status code.  The rest of the information in this row is related to this value."
    ::= { bwSipStatsPrackResponsesEntry 1 }

  bwSipStatsPrackResponseIns OBJECT-TYPE
    SYNTAX      Counter32
    MAX-ACCESS  read-write
    STATUS      current
    DESCRIPTION 
        "This counter represents the number of SIP responses received in response to a Prack"
    ::= { bwSipStatsPrackResponsesEntry 2 }

  bwSipStatsPrackResponseOuts OBJECT-TYPE
    SYNTAX      Counter32
    MAX-ACCESS  read-write
    STATUS      current
    DESCRIPTION 
        "This counter represents the number of SIP responses sent in response to a Prack"
    ::= { bwSipStatsPrackResponsesEntry 3 }

  bwSipStatsInfoResponsesTable OBJECT-TYPE
    SYNTAX      SEQUENCE OF BwSipStatsInfoResponsesEntry
    MAX-ACCESS  not-accessible
    STATUS      current
    DESCRIPTION 
        "This table contains the counters for all SIP responses to the Info requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 28 }

  bwSipStatsInfoResponsesEntry OBJECT-TYPE
    SYNTAX      BwSipStatsInfoResponsesEntry
    MAX-ACCESS  not-accessible
    STATUS      current
    DESCRIPTION 
        "This row contains information on a particular SIP status code received or sent in response to an Info"
    INDEX       { bwSipStatsInfoResponseCodeValue }
    ::= { bwSipStatsInfoResponsesTable 1 }

  BwSipStatsInfoResponsesEntry ::= SEQUENCE {
    bwSipStatsInfoResponseCodeValue     Integer32,
    bwSipStatsInfoResponseIns           Counter32,
    bwSipStatsInfoResponseOuts          Counter32
  }

  bwSipStatsInfoResponseCodeValue OBJECT-TYPE
    SYNTAX      Integer32 (100..999)
    MAX-ACCESS  not-accessible
    STATUS      current
    DESCRIPTION 
        "This integer represents a SIP status code.  The rest of the information in this row is related to this value."
    ::= { bwSipStatsInfoResponsesEntry 1 }

  bwSipStatsInfoResponseIns OBJECT-TYPE
    SYNTAX      Counter32
    MAX-ACCESS  read-write
    STATUS      current
    DESCRIPTION 
        "This counter represents the number of SIP responses received in response to an Info"
    ::= { bwSipStatsInfoResponsesEntry 2 }

  bwSipStatsInfoResponseOuts OBJECT-TYPE
    SYNTAX      Counter32
    MAX-ACCESS  read-write
    STATUS      current
    DESCRIPTION 
        "This counter represents the number of SIP responses sent in response to an Info"
    ::= { bwSipStatsInfoResponsesEntry 3 }

  bwSipStatsNotifyResponsesTable OBJECT-TYPE
    SYNTAX      SEQUENCE OF BwSipStatsNotifyResponsesEntry
    MAX-ACCESS  not-accessible
    STATUS      current
    DESCRIPTION 
        "This table contains the counters for all SIP responses to the Notify requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 29 }

  bwSipStatsNotifyResponsesEntry OBJECT-TYPE
    SYNTAX      BwSipStatsNotifyResponsesEntry
    MAX-ACCESS  not-accessible
    STATUS      current
    DESCRIPTION 
        "This row contains information on a particular SIP status code received or sent in response to an Notify"
    INDEX       { bwSipStatsNotifyResponseCodeValue }
    ::= { bwSipStatsNotifyResponsesTable 1 }

  BwSipStatsNotifyResponsesEntry ::= SEQUENCE {
    bwSipStatsNotifyResponseCodeValue   Integer32,
    bwSipStatsNotifyResponseIns         Counter32,
    bwSipStatsNotifyResponseOuts        Counter32
  }

  bwSipStatsNotifyResponseCodeValue OBJECT-TYPE
    SYNTAX      Integer32 (100..999)
    MAX-ACCESS  not-accessible
    STATUS      current
    DESCRIPTION 
        "This integer represents a SIP status code.  The rest of the information in this row is related to this value."
    ::= { bwSipStatsNotifyResponsesEntry 1 }

  bwSipStatsNotifyResponseIns OBJECT-TYPE
    SYNTAX      Counter32
    MAX-ACCESS  read-write
    STATUS      current
    DESCRIPTION 
        "This counter represents the number of SIP responses received in response to a Notify"
    ::= { bwSipStatsNotifyResponsesEntry 2 }

  bwSipStatsNotifyResponseOuts OBJECT-TYPE
    SYNTAX      Counter32
    MAX-ACCESS  read-write
    STATUS      current
    DESCRIPTION 
        "This counter represents the number of SIP responses sent in response to a Notify"
    ::= { bwSipStatsNotifyResponsesEntry 3 }

  bwSipStatsOtherResponsesTable OBJECT-TYPE
    SYNTAX      SEQUENCE OF BwSipStatsOtherResponsesEntry
    MAX-ACCESS  not-accessible
    STATUS      current
    DESCRIPTION 
        "This table contains the counters for all SIP responses to the Other requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 30 }

  bwSipStatsOtherResponsesEntry OBJECT-TYPE
    SYNTAX      BwSipStatsOtherResponsesEntry
    MAX-ACCESS  not-accessible
    STATUS      current
    DESCRIPTION 
        "This row contains information on a particular SIP status code received or sent in response to an Other"
    INDEX       { bwSipStatsOtherResponseCodeValue }
    ::= { bwSipStatsOtherResponsesTable 1 }

  BwSipStatsOtherResponsesEntry ::= SEQUENCE {
    bwSipStatsOtherResponseCodeValue    Integer32,
    bwSipStatsOtherResponseIns          Counter32,
    bwSipStatsOtherResponseOuts         Counter32
  }

  bwSipStatsOtherResponseCodeValue OBJECT-TYPE
    SYNTAX      Integer32 (100..999)
    MAX-ACCESS  not-accessible
    STATUS      current
    DESCRIPTION 
        "This integer represents a SIP status code.  The rest of the information in this row is related to this value."
    ::= { bwSipStatsOtherResponsesEntry 1 }

  bwSipStatsOtherResponseIns OBJECT-TYPE
    SYNTAX      Counter32
    MAX-ACCESS  read-write
    STATUS      current
    DESCRIPTION 
        "This counter represents the number of SIP responses received in response to an Other"
    ::= { bwSipStatsOtherResponsesEntry 2 }

  bwSipStatsOtherResponseOuts OBJECT-TYPE
    SYNTAX      Counter32
    MAX-ACCESS  read-write
    STATUS      current
    DESCRIPTION 
        "This counter represents the number of SIP responses sent in response to an Other"
    ::= { bwSipStatsOtherResponsesEntry 3 }

  bwSipStatsRetryInvites OBJECT-TYPE
    SYNTAX      Counter32
    MAX-ACCESS  read-write
    STATUS      current
    DESCRIPTION 
        "This counter reflects the total number of INVITE retries that have been sent by the user agent."
    ::= { sipStats 31 }

  bwSipStatsRetryByes OBJECT-TYPE
    SYNTAX      Counter32
    MAX-ACCESS  read-write
    STATUS      current
    DESCRIPTION 
        "This counter reflects the total number of BYE retries that have been sent by the user agent."
    ::= { sipStats 32 }

  bwSipStatsRetryCancels OBJECT-TYPE
    SYNTAX      Counter32
    MAX-ACCESS  read-write
    STATUS      current
    DESCRIPTION 
        "This counter reflects the total number of CANCEL retries that have been sent by the user agent."
    ::= { sipStats 33 }

  bwSipStatsRetryResponses OBJECT-TYPE
    SYNTAX      Counter32
    MAX-ACCESS  read-write
    STATUS      current
    DESCRIPTION 
        "This counter reflects the total number of RESPONSES retries that have been sent by the user agent."
    ::= { sipStats 34 }

  bwSipStatsSubscribeIns OBJECT-TYPE
    SYNTAX      Counter32
    MAX-ACCESS  read-write
    STATUS      current
    DESCRIPTION 
        "This counter reflects the total number of SUBSCRIBE message that have been received at the AS."
    ::= { sipStats 35 }

  bwSipStatsSubscribeOuts OBJECT-TYPE
    SYNTAX      Counter32
    MAX-ACCESS  read-write
    STATUS      current
    DESCRIPTION 
        "This counter reflects the total number of SUBSCRIBE message that have been sent by the AS."
    ::= { sipStats 36 }

  bwSipStatsMessageIns OBJECT-TYPE
    SYNTAX      Counter32
    MAX-ACCESS  read-write
    STATUS      current
    DESCRIPTION 
        "This counter reflects the total number of MESSAGE message that have been received at the AS."
    ::= { sipStats 37 }

  bwSipStatsMessageOuts OBJECT-TYPE
    SYNTAX      Counter32
    MAX-ACCESS  read-write
    STATUS      current
    DESCRIPTION 
        "This counter reflects the total number of MESSAGE message that have been sent by the AS."
    ::= { sipStats 38 }

  bwSipStatsSubscribeResponsesTable OBJECT-TYPE
    SYNTAX      SEQUENCE OF BwSipStatsSubscribeResponsesEntry
    MAX-ACCESS  not-accessible
    STATUS      current
    DESCRIPTION 
        "This table contains the counters for all SIP responses to the Subscribe requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 39 }

  bwSipStatsSubscribeResponsesEntry OBJECT-TYPE
    SYNTAX      BwSipStatsSubscribeResponsesEntry
    MAX-ACCESS  not-accessible
    STATUS      current
    DESCRIPTION 
        "This row contains information on a particular SIP status code received or sent in response to a Subscribe"
    INDEX       { bwSipStatsSubscribeResponseCodeValue }
    ::= { bwSipStatsSubscribeResponsesTable 1 }

  BwSipStatsSubscribeResponsesEntry ::= SEQUENCE {
    bwSipStatsSubscribeResponseCodeValue    Integer32,
    bwSipStatsSubscribeResponseIns          Counter32,
    bwSipStatsSubscribeResponseOuts         Counter32
  }

  bwSipStatsSubscribeResponseCodeValue OBJECT-TYPE
    SYNTAX      Integer32 (100..999)
    MAX-ACCESS  not-accessible
    STATUS      current
    DESCRIPTION 
        "This integer represents a SIP status code.  The rest of the information in this row is related to this value."
    ::= { bwSipStatsSubscribeResponsesEntry 1 }

  bwSipStatsSubscribeResponseIns OBJECT-TYPE
    SYNTAX      Counter32
    MAX-ACCESS  read-write
    STATUS      current
    DESCRIPTION 
        "This counter represents the number of SIP responses received in response to a Subscribe"
    ::= { bwSipStatsSubscribeResponsesEntry 2 }

  bwSipStatsSubscribeResponseOuts OBJECT-TYPE
    SYNTAX      Counter32
    MAX-ACCESS  read-write
    STATUS      current
    DESCRIPTION 
        "This counter represents the number of SIP responses sent in response to a Subscribe"
    ::= { bwSipStatsSubscribeResponsesEntry 3 }

  bwSipStatsMessageResponsesTable OBJECT-TYPE
    SYNTAX      SEQUENCE OF BwSipStatsMessageResponsesEntry
    MAX-ACCESS  not-accessible
    STATUS      current
    DESCRIPTION 
        "This table contains the counters for all SIP responses to the Message requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 40 }

  bwSipStatsMessageResponsesEntry OBJECT-TYPE
    SYNTAX      BwSipStatsMessageResponsesEntry
    MAX-ACCESS  not-accessible
    STATUS      current
    DESCRIPTION 
        "This row contains information on a particular SIP status code received or sent in response to a Message"
    INDEX       { bwSipStatsMessageResponseCodeValue }
    ::= { bwSipStatsMessageResponsesTable 1 }

  BwSipStatsMessageResponsesEntry ::= SEQUENCE {
    bwSipStatsMessageResponseCodeValue  Integer32,
    bwSipStatsMessageResponseIns        Counter32,
    bwSipStatsMessageResponseOuts       Counter32
  }

  bwSipStatsMessageResponseCodeValue OBJECT-TYPE
    SYNTAX      Integer32 (100..999)
    MAX-ACCESS  not-accessible
    STATUS      current
    DESCRIPTION 
        "This integer represents a SIP status code.  The rest of the information in this row is related to this value."
    ::= { bwSipStatsMessageResponsesEntry 1 }

  bwSipStatsMessageResponseIns OBJECT-TYPE
    SYNTAX      Counter32
    MAX-ACCESS  read-write
    STATUS      current
    DESCRIPTION 
        "This counter represents the number of SIP responses received in response to a Message"
    ::= { bwSipStatsMessageResponsesEntry 2 }

  bwSipStatsMessageResponseOuts OBJECT-TYPE
    SYNTAX      Counter32
    MAX-ACCESS  read-write
    STATUS      current
    DESCRIPTION 
        "This counter represents the number of SIP responses sent in response to a Message"
    ::= { bwSipStatsMessageResponsesEntry 3 }

  bwSipStatsUpdateIns OBJECT-TYPE
    SYNTAX      Counter32
    MAX-ACCESS  read-write
    STATUS      current
    DESCRIPTION 
        "This counter reflects the total number of UPDATE requests received by BroadWorks."
    ::= { sipStats 41 }

  bwSipStatsUpdateOuts OBJECT-TYPE
    SYNTAX      Counter32
    MAX-ACCESS  read-write
    STATUS      current
    DESCRIPTION 
        "This counter reflects the total number of UPDATE requests sent by BroadWorks."
    ::= { sipStats 42 }

  bwSipStatsUpdateResponseTable OBJECT-TYPE
    SYNTAX      SEQUENCE OF BwSipStatsUpdateResponseEntry
    MAX-ACCESS  not-accessible
    STATUS      current
    DESCRIPTION 
        "This table contains the counters for all SIP responses to the Message requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 513, 600, 603, 604, 606"
    ::= { sipStats 43 }

  bwSipStatsUpdateResponseEntry OBJECT-TYPE
    SYNTAX      BwSipStatsUpdateResponseEntry
    MAX-ACCESS  not-accessible
    STATUS      current
    DESCRIPTION 
        "This row contains information on a particular SIP status code received or sent in response to an Update message"
    INDEX       { bwSipStatsUpdateResponseCodeValue }
    ::= { bwSipStatsUpdateResponseTable 1 }

  BwSipStatsUpdateResponseEntry ::= SEQUENCE {
    bwSipStatsUpdateResponseCodeValue   Integer32,
    bwSipStatsUpdateResponseIns         Counter32,
    bwSipStatsUpdateResponseOuts        Counter32
  }

  bwSipStatsUpdateResponseCodeValue OBJECT-TYPE
    SYNTAX      Integer32 (100..999)
    MAX-ACCESS  not-accessible
    STATUS      current
    DESCRIPTION 
        "This integer represents a SIP status code.  The rest of the information in this row is related to this value."
    ::= { bwSipStatsUpdateResponseEntry 1 }

  bwSipStatsUpdateResponseIns OBJECT-TYPE
    SYNTAX      Counter32
    MAX-ACCESS  read-write
    STATUS      current
    DESCRIPTION 
        "This counter represents the number of SIP responses received in response to an Update message"
    ::= { bwSipStatsUpdateResponseEntry 2 }

  bwSipStatsUpdateResponseOuts OBJECT-TYPE
    SYNTAX      Counter32
    MAX-ACCESS  read-write
    STATUS      current
    DESCRIPTION 
        "This counter represents the number of SIP responses sent in response to an Update message"
    ::= { bwSipStatsUpdateResponseEntry 3 }

  bwSipStatsSetupSignalDelay OBJECT-TYPE
    SYNTAX      Gauge32
    MAX-ACCESS  read-write
    STATUS      current
    DESCRIPTION 
        "This gauge is applicable to SIP originated calls.  It measures the average time (in milliseconds) it takes between the receipt of an INVITE message for the origination of a new call and the transmission of an INVITE (Sip terminator), RQNT (MGCP terminator with in-band ringback), or CRCX (MGCP terminator without in-band ringback) to the primary device of the original called party (in the case of intra-group call) or to the network element of the original called party (in the case of a call to the PSTN).  Delays incurred by a query to an external element (e.g. - dip to the Network Server, CNAME query, any external database interaction incurred by CPL scripting) are part of the measurement.  This measurement is intended to reflect the elapsed delay between receipt of the call setup signal from the caller and transmission of the call setup signal to the called party"
    ::= { sipStats 44 }

  bwSipStatsMinSetupSignalDelay OBJECT-TYPE
    SYNTAX      Gauge32
    MAX-ACCESS  read-write
    STATUS      current
    DESCRIPTION 
        "This measures the shortest SIP setup-signal delay sampled since the system was started or since this measurement was cleared"
    ::= { sipStats 45 }

  bwSipStatsMaxSetupSignalDelay OBJECT-TYPE
    SYNTAX      Gauge32
    MAX-ACCESS  read-write
    STATUS      current
    DESCRIPTION 
        "This measures the longest SIP setup-signal delay sampled since the system was started or since this measurement was cleared"
    ::= { sipStats 46 }

  bwSipStatsAnswerSignalDelay OBJECT-TYPE
    SYNTAX      Gauge32
    MAX-ACCESS  read-write
    STATUS      current
    DESCRIPTION 
        "This gauge measures the average time (in milliseconds) between the receipt of a 200 OK message indicating answer or a NTFY off-hook indicating answer and the transmission of a 200 OK indicating answer to the originator.   This measurement is intended to reflect internal queuing, scheduling, and processing delays.
         This gauge is applicable to only the SIP originated calls for which the setup-signal delay is measured.  Answer signal delay is not measured when the call has been forwarded, redirected, or when the call has encountered route advancing"
    ::= { sipStats 47 }

  bwSipStatsMinAnswerSignalDelay OBJECT-TYPE
    SYNTAX      Gauge32
    MAX-ACCESS  read-write
    STATUS      current
    DESCRIPTION 
        "This measures the shortest SIP answer-signal delay sampled since the system was started or since this measurement was cleared"
    ::= { sipStats 49 }

  bwSipStatsMaxAnswerSignalDelay OBJECT-TYPE
    SYNTAX      Gauge32
    MAX-ACCESS  read-write
    STATUS      current
    DESCRIPTION 
        "This measures the longest SIP answer-signal delay sampled since the system was started or since this measurement was cleared"
    ::= { sipStats 50 }

  bwSipStatsRegistrationsPerMinute OBJECT-TYPE
    SYNTAX      Gauge32
    MAX-ACCESS  read-only
    STATUS      current
    DESCRIPTION 
        "This gauge measures the rate at which the Application Server receives SIP REGISTER messages.  It uses the timestamps of up to the last 100 registrations received in calculating the rate"
    ::= { sipStats 51 }

  bwSipStatsMsgRetryPercentageToOther OBJECT-TYPE
    SYNTAX      Gauge32
    MAX-ACCESS  read-only
    STATUS      current
    DESCRIPTION 
        "This gauge measures the percentage of SIP requests and reliable responses sent (to nodes other than those covered by bwSipStatsMsgRetryToNeTable) due to retry.  Of up to the last 100 requests and reliable responses sent, this gauge calculates the percentage sent due to retransmission (i.e. - gauge = (SIP request retransmissions + SIP reliable response retransmissions) / (SIP request initial transmissions + SIP request retransmissions + SIP reliable response initial transmissions + SIP reliable response retransmissions)"
    ::= { sipStats 52 }

  bwSipStatsMsgRetryToNeTable OBJECT-TYPE
    SYNTAX      SEQUENCE OF BwSipStatsMsgRetryToNeEntry
    MAX-ACCESS  not-accessible
    STATUS      current
    DESCRIPTION 
        "This gauge table consists of a bwSipStatsMsgRetryToNEEntry per Network Element address.  A Network Element can be a Network Server, Media Server, a Network Gateway, etc - anything but an access device."
    ::= { sipStats 53 }

  bwSipStatsMsgRetryToNeEntry OBJECT-TYPE
    SYNTAX      BwSipStatsMsgRetryToNeEntry
    MAX-ACCESS  not-accessible
    STATUS      current
    DESCRIPTION 
        "This row contains information on a particular Network Element"
    INDEX       { bwSipStatsMsgRetryToNeID }
    ::= { bwSipStatsMsgRetryToNeTable 1 }

  BwSipStatsMsgRetryToNeEntry ::= SEQUENCE {
    bwSipStatsMsgRetryToNeID            Unsigned32,
    bwSipStatsMsgRetryToNeAddr          DisplayString,
    bwSipStatsMsgRetryToNePercentage    Gauge32
  }

  bwSipStatsMsgRetryToNeID OBJECT-TYPE
    SYNTAX      Unsigned32
    MAX-ACCESS  read-only
    STATUS      current
    DESCRIPTION 
        "This integer represents the unique index of a Network Element"
    ::= { bwSipStatsMsgRetryToNeEntry 1 }

  bwSipStatsMsgRetryToNeAddr OBJECT-TYPE
    SYNTAX      DisplayString
    MAX-ACCESS  read-only
    STATUS      current
    DESCRIPTION 
        "This string represents a Network Element address"
    ::= { bwSipStatsMsgRetryToNeEntry 2 }

  bwSipStatsMsgRetryToNePercentage OBJECT-TYPE
    SYNTAX      Gauge32
    MAX-ACCESS  read-only
    STATUS      current
    DESCRIPTION 
        "The gauge measures for that particular Network Element the percentage of SIP requests and reliable responses sent due to retry.  Of up to the last 100 requests and reliable responses sent to a particular NetworkElement address, this gauge calculates the percentage sent due to retransmission (i.e. - gauge = (SIP request retransmissions + SIP reliable response retransmissions) / (SIP request initial transmissions + SIP request retransmissions + SIP reliable response initial transmissions + SIP reliable response retransmissions)."
    ::= { bwSipStatsMsgRetryToNeEntry 3 }

  bwSipStatsActiveTcpConnections OBJECT-TYPE
    SYNTAX      Gauge32
    MAX-ACCESS  read-only
    STATUS      current
    DESCRIPTION 
        "This gauge is incremented whenever a SIP TCP connection is established.   It decremented whenever a connection is closed."
    ::= { sipStats 54 }

  bwSipStatsTcpIns OBJECT-TYPE
    SYNTAX      Counter32
    MAX-ACCESS  read-write
    STATUS      current
    DESCRIPTION 
        "This counter is incremented whenever a SIP message is received via TCP."
    ::= { sipStats 55 }

  bwSipStatsTcpOuts OBJECT-TYPE
    SYNTAX      Counter32
    MAX-ACCESS  read-write
    STATUS      current
    DESCRIPTION 
        "This counter is incremented whenever a SIP message is sent via TCP."
    ::= { sipStats 56 }

  bwSipStatsTcpFailures OBJECT-TYPE
    SYNTAX      Counter32
    MAX-ACCESS  read-write
    STATUS      current
    DESCRIPTION 
        "This counter is incremented whenever a SIP message was attempted to be sent via TCP but failed."
    ::= { sipStats 57 }

  bwSipStatsUdpIns OBJECT-TYPE
    SYNTAX      Counter32
    MAX-ACCESS  read-write
    STATUS      current
    DESCRIPTION 
        "This counter is incremented whenever a SIP message is received via UDP."
    ::= { sipStats 58 }

  bwSipStatsUdpOuts OBJECT-TYPE
    SYNTAX      Counter32
    MAX-ACCESS  read-write
    STATUS      current
    DESCRIPTION 
        "This counter is incremented whenever a SIP message is sent via UDP."
    ::= { sipStats 59 }

  bwSIPReclaimedStaleTcpConnections OBJECT-TYPE
    SYNTAX      Counter32
    MAX-ACCESS  read-write
    STATUS      current
    DESCRIPTION 
        "This counter is incremented every time a SIP TCP connection is reclaimed because it is stale."
    ::= { sipStats 60 }

  bwSipPeerConnectionFailureCount OBJECT-TYPE
    SYNTAX      Counter32
    MAX-ACCESS  read-write
    STATUS      current
    DESCRIPTION 
        "This counter tracks the number of SIP peer connection failure detected."
-- @feature:175540
    ::= { sipStats 61 }

  bwSipPeerConnectionMessageReceived OBJECT-TYPE
    SYNTAX      Counter32
    MAX-ACCESS  read-write
    STATUS      current
    DESCRIPTION 
        "This counter tracks the number of monitoring messages received from the peer server over the SIP network interface."
-- @feature:175540
    ::= { sipStats 62 }

  bwSipPeerConnectionMessageSent OBJECT-TYPE
    SYNTAX      Counter32
    MAX-ACCESS  read-write
    STATUS      current
    DESCRIPTION 
        "This counter tracks the number of monitoring messages sent to the peer server over the SIP network interface."
-- @feature:175540
    ::= { sipStats 63 }

  bwSipPeerConnectionFailureCountTimeMSB OBJECT-TYPE
    SYNTAX      Gauge32
    MAX-ACCESS  read-only
    STATUS      current
    DESCRIPTION 
        "The most significant part of the timestamp (4 most significant bytes) when the SIP peer connection failure was detected."
-- @feature:175540
    ::= { sipStats 64 }

  bwSipPeerConnectionFailureCountTimeLSB OBJECT-TYPE
    SYNTAX      Gauge32
    MAX-ACCESS  read-only
    STATUS      current
    DESCRIPTION 
        "The least significant part of the timestamp (4 least significant bytes) when the SIP peer connection failure was detected."
-- @feature:175540
    ::= { sipStats 65 }

-- Congestion Management

  bwCongestionManagementNeighborTable OBJECT-TYPE
    SYNTAX      SEQUENCE OF BwCongestionManagementNeighborEntry
    MAX-ACCESS  not-accessible
    STATUS      current
    DESCRIPTION 
        "This table consists of bwCongestionManagementNeighborEntry. "
    ::= { congestionManagement 1 }

  bwCongestionManagementNeighborEntry OBJECT-TYPE
    SYNTAX      BwCongestionManagementNeighborEntry
    MAX-ACCESS  not-accessible
    STATUS      current
    DESCRIPTION 
        "This row contains information on a particular neighbor."
    INDEX       { bwCongestionManagementNeighborIndex }
    ::= { bwCongestionManagementNeighborTable 1 }

  BwCongestionManagementNeighborEntry ::= SEQUENCE {
    bwCongestionManagementNeighborIndex                     Unsigned32,
    bwCongestionManagementNeighborIpAddress                 DisplayString,
    bwCongestionManagementNeighborInviteIn                  Counter32,
    bwCongestionManagementNeighborInviteOut                 Counter32,
    bwCongestionManagementNeighborRegisterIn                Counter32,
    bwCongestionManagementNeighborOptionsIn                 Counter32,
    bwCongestionManagementNeighborOptionsOut                Counter32,
    bwCongestionManagementNeighborSubscribeNotifyIn         Counter32,
    bwCongestionManagementNeighborSubscribeNotifyOut        Counter32,
    bwCongestionManagementNeighbor5xxIn                     Counter32,
    bwCongestionManagementNeighborCallpMessageInRate        Gauge32,
    bwCongestionManagementNeighborCallpMessageOutRate       Gauge32,
    bwCongestionManagementNeighborCallpRequestInRate        Gauge32,
    bwCongestionManagementNeighborNonCallpMessageInRate     Gauge32,
    bwCongestionManagementNeighborNonCallpMessageOutRate    Gauge32,
    bwCongestionManagementNeighborNonCallpRequestInRate     Gauge32,
    bwCongestionManagementNeighborState                     DisplayString,
    bwCongestionManagementNeighborCapability                DisplayString
  }

  bwCongestionManagementNeighborIndex OBJECT-TYPE
    SYNTAX      Unsigned32
    MAX-ACCESS  read-only
    STATUS      current
    DESCRIPTION 
        "This integer represents the neighbor index in the system"
    ::= { bwCongestionManagementNeighborEntry 1 }

  bwCongestionManagementNeighborIpAddress OBJECT-TYPE
    SYNTAX      DisplayString
    MAX-ACCESS  read-only
    STATUS      current
    DESCRIPTION 
        "The IP address of the neighbor."
    ::= { bwCongestionManagementNeighborEntry 2 }

  bwCongestionManagementNeighborInviteIn OBJECT-TYPE
    SYNTAX      Counter32
    MAX-ACCESS  read-write
    STATUS      current
    DESCRIPTION 
        "This is the number of Invite requests that the neighbor sends to the AS."
    ::= { bwCongestionManagementNeighborEntry 3 }

  bwCongestionManagementNeighborInviteOut OBJECT-TYPE
    SYNTAX      Counter32
    MAX-ACCESS  read-write
    STATUS      current
    DESCRIPTION 
        "This is the number of Invite requests that the AS sends to the neighbor."
    ::= { bwCongestionManagementNeighborEntry 4 }

  bwCongestionManagementNeighborRegisterIn OBJECT-TYPE
    SYNTAX      Counter32
    MAX-ACCESS  read-write
    STATUS      current
    DESCRIPTION 
        "This is the number of Register requests that the neighbor sends to the AS."
    ::= { bwCongestionManagementNeighborEntry 5 }

  bwCongestionManagementNeighborOptionsIn OBJECT-TYPE
    SYNTAX      Counter32
    MAX-ACCESS  read-write
    STATUS      current
    DESCRIPTION 
        "This is the number of Options requests that the neighbor sends to the AS."
    ::= { bwCongestionManagementNeighborEntry 6 }

  bwCongestionManagementNeighborOptionsOut OBJECT-TYPE
    SYNTAX      Counter32
    MAX-ACCESS  read-write
    STATUS      current
    DESCRIPTION 
        "This is the number of Options requests that the AS sends to the neighbor."
    ::= { bwCongestionManagementNeighborEntry 7 }

  bwCongestionManagementNeighborSubscribeNotifyIn OBJECT-TYPE
    SYNTAX      Counter32
    MAX-ACCESS  read-write
    STATUS      current
    DESCRIPTION 
        "This is the number of Subscribe and Notify requests that the neighbor sends to the AS."
    ::= { bwCongestionManagementNeighborEntry 8 }

  bwCongestionManagementNeighborSubscribeNotifyOut OBJECT-TYPE
    SYNTAX      Counter32
    MAX-ACCESS  read-write
    STATUS      current
    DESCRIPTION 
        "This is the number of Subscribe and Notify requests that the AS sends to the neighbor."
    ::= { bwCongestionManagementNeighborEntry 9 }

  bwCongestionManagementNeighbor5xxIn OBJECT-TYPE
    SYNTAX      Counter32
    MAX-ACCESS  read-write
    STATUS      current
    DESCRIPTION 
        "This is the number of 5xx responses that the neighbor sends to the AS."
    ::= { bwCongestionManagementNeighborEntry 10 }

  bwCongestionManagementNeighborCallpMessageInRate OBJECT-TYPE
    SYNTAX      Gauge32
    MAX-ACCESS  read-only
    STATUS      current
    DESCRIPTION 
        "This is the incoming callp messages (requests and responses) rate."
    ::= { bwCongestionManagementNeighborEntry 11 }

  bwCongestionManagementNeighborCallpMessageOutRate OBJECT-TYPE
    SYNTAX      Gauge32
    MAX-ACCESS  read-only
    STATUS      current
    DESCRIPTION 
        "This is the outgoing callp messages (requests and responses) rate."
    ::= { bwCongestionManagementNeighborEntry 12 }

  bwCongestionManagementNeighborCallpRequestInRate OBJECT-TYPE
    SYNTAX      Gauge32
    MAX-ACCESS  read-only
    STATUS      current
    DESCRIPTION 
        "This is the incoming callp requests rate."
    ::= { bwCongestionManagementNeighborEntry 13 }

  bwCongestionManagementNeighborNonCallpMessageInRate OBJECT-TYPE
    SYNTAX      Gauge32
    MAX-ACCESS  read-only
    STATUS      current
    DESCRIPTION 
        "This is the incoming non-callp messages (requests and responses) rate."
    ::= { bwCongestionManagementNeighborEntry 14 }

  bwCongestionManagementNeighborNonCallpMessageOutRate OBJECT-TYPE
    SYNTAX      Gauge32
    MAX-ACCESS  read-only
    STATUS      current
    DESCRIPTION 
        "This is the outgoing non-callp messages (requests and responses) rate."
    ::= { bwCongestionManagementNeighborEntry 15 }

  bwCongestionManagementNeighborNonCallpRequestInRate OBJECT-TYPE
    SYNTAX      Gauge32
    MAX-ACCESS  read-only
    STATUS      current
    DESCRIPTION 
        "This is the incoming non-callp requests rate."
    ::= { bwCongestionManagementNeighborEntry 16 }

  bwCongestionManagementNeighborState OBJECT-TYPE
    SYNTAX      DisplayString
    MAX-ACCESS  read-only
    STATUS      current
    DESCRIPTION 
        "The current congestion management state of the neighbor."
    ::= { bwCongestionManagementNeighborEntry 17 }

  bwCongestionManagementNeighborCapability OBJECT-TYPE
    SYNTAX      DisplayString
    MAX-ACCESS  read-only
    STATUS      current
    DESCRIPTION 
        "The congestion management capability of the neighbor."
    ::= { bwCongestionManagementNeighborEntry 18 }

-- SERVICES

  bwAuthCodeNumAttempts OBJECT-TYPE
    SYNTAX      Counter32
    MAX-ACCESS  read-write
    STATUS      current
    DESCRIPTION 
        "This counter reflects the number of authorization attempts"
    ::= { accountCodes 1 }

  bwAuthCodeNumValidations OBJECT-TYPE
    SYNTAX      Counter32
    MAX-ACCESS  read-write
    STATUS      current
    DESCRIPTION 
        "This counter reflects the number of successful validations"
    ::= { accountCodes 2 }

  bwAccountCodeNumAttempts OBJECT-TYPE
    SYNTAX      Counter32
    MAX-ACCESS  read-write
    STATUS      current
    DESCRIPTION 
        "This counter is incremented whenever the user is prompted for an account code in Automatic mode"
    ::= { accountCodes 3 }

  bwAccountCodesSPTable OBJECT-TYPE
    SYNTAX      SEQUENCE OF BwAccountCodesSPEntry
    MAX-ACCESS  not-accessible
    STATUS      current
    DESCRIPTION 
        "This table contains the counters for Account/Authorization Codes service measurements for service providers"
    ::= { accountCodes 4 }

  bwAccountCodesSPEntry OBJECT-TYPE
    SYNTAX      BwAccountCodesSPEntry
    MAX-ACCESS  not-accessible
    STATUS      current
    DESCRIPTION 
        "This row contains the counters for Account/Authorization Codes service measurements for a service provider"
    INDEX       { bwAccountCodesSPIndex }
    ::= { bwAccountCodesSPTable 1 }

  BwAccountCodesSPEntry ::= SEQUENCE {
    bwAccountCodesSPIndex               Unsigned32,
    bwAccountCodesSPID                  DisplayString,
    bwAuthCodeSPNumAttempts             Counter32,
    bwAuthCodeSPNumValidations          Counter32,
    bwAccountCodeSPNumAttempts          Counter32,
    bwAccountCodeSPNumPerCallAttempts   Counter32
  }

  bwAccountCodesSPIndex OBJECT-TYPE
    SYNTAX      Unsigned32
    MAX-ACCESS  read-only
    STATUS      current
    DESCRIPTION 
        "This integer represents the a service provider index in the system"
    ::= { bwAccountCodesSPEntry 1 }

  bwAccountCodesSPID OBJECT-TYPE
    SYNTAX      DisplayString
    MAX-ACCESS  read-only
    STATUS      current
    DESCRIPTION 
        "This string represents a service provider ID"
    ::= { bwAccountCodesSPEntry 2 }

  bwAuthCodeSPNumAttempts OBJECT-TYPE
    SYNTAX      Counter32
    MAX-ACCESS  read-write
    STATUS      current
    DESCRIPTION 
        "This counter reflects the number of authorization attempts for a service provider"
    ::= { bwAccountCodesSPEntry 3 }

  bwAuthCodeSPNumValidations OBJECT-TYPE
    SYNTAX      Counter32
    MAX-ACCESS  read-write
    STATUS      current
    DESCRIPTION 
        "This counter reflects the number of successful validations for a service provider"
    ::= { bwAccountCodesSPEntry 4 }

  bwAccountCodeSPNumAttempts OBJECT-TYPE
    SYNTAX      Counter32
    MAX-ACCESS  read-write
    STATUS      current
    DESCRIPTION 
        "Number of attempts to validate an Account Code (for a given service provider)."
    ::= { bwAccountCodesSPEntry 5 }

  bwAccountCodeSPNumPerCallAttempts OBJECT-TYPE
    SYNTAX      Counter32
    MAX-ACCESS  read-write
    STATUS      current
    DESCRIPTION 
        "Number of attempts to validate an Account Code (for a given service provider)."
    ::= { bwAccountCodesSPEntry 6 }

  bwAccountCodesGroupTable OBJECT-TYPE
    SYNTAX      SEQUENCE OF BwAccountCodesGroupEntry
    MAX-ACCESS  not-accessible
    STATUS      current
    DESCRIPTION 
        "This table contains the counters for Account/Authorization Codes service measurements for groups"
    ::= { accountCodes 5 }

  bwAccountCodesGroupEntry OBJECT-TYPE
    SYNTAX      BwAccountCodesGroupEntry
    MAX-ACCESS  not-accessible
    STATUS      current
    DESCRIPTION 
        "This row contains the counters for Account/Authorization Codes service measurements for a group"
    INDEX       { bwAccountCodesGroupIndex }
    ::= { bwAccountCodesGroupTable 1 }

  BwAccountCodesGroupEntry ::= SEQUENCE {
    bwAccountCodesGroupIndex                Unsigned32,
    bwAccountCodesGroupID                   DisplayString,
    bwAuthCodeGroupNumAttempts              Counter32,
    bwAuthCodeGroupNumValidations           Counter32,
    bwAccountCodeGroupNumAttempts           Counter32,
    bwAccountCodeGroupNumPerCallAttempts    Counter32
  }

  bwAccountCodesGroupIndex OBJECT-TYPE
    SYNTAX      Unsigned32
    MAX-ACCESS  read-only
    STATUS      current
    DESCRIPTION 
        "This integer represents the a group index in the system"
    ::= { bwAccountCodesGroupEntry 1 }

  bwAccountCodesGroupID OBJECT-TYPE
    SYNTAX      DisplayString
    MAX-ACCESS  read-only
    STATUS      current
    DESCRIPTION 
        "This string represents a Group ID"
    ::= { bwAccountCodesGroupEntry 2 }

  bwAuthCodeGroupNumAttempts OBJECT-TYPE
    SYNTAX      Counter32
    MAX-ACCESS  read-write
    STATUS      current
    DESCRIPTION 
        "This counter reflects the number of authorization attempts for a group"
    ::= { bwAccountCodesGroupEntry 3 }

  bwAuthCodeGroupNumValidations OBJECT-TYPE
    SYNTAX      Counter32
    MAX-ACCESS  read-write
    STATUS      current
    DESCRIPTION 
        "This counter reflects the number of successful validations for a group"
    ::= { bwAccountCodesGroupEntry 4 }

  bwAccountCodeGroupNumAttempts OBJECT-TYPE
    SYNTAX      Counter32
    MAX-ACCESS  read-write
    STATUS      current
    DESCRIPTION 
        "This counter reflects the number of Account code attempts for a group"
    ::= { bwAccountCodesGroupEntry 5 }

  bwAccountCodeGroupNumPerCallAttempts OBJECT-TYPE
    SYNTAX      Counter32
    MAX-ACCESS  read-write
    STATUS      current
    DESCRIPTION 
        "Number of attempts to validate an Account Code (for a given group)."
    ::= { bwAccountCodesGroupEntry 6 }

  bwAccountCodeNumPerCallAttempts OBJECT-TYPE
    SYNTAX      Counter32
    MAX-ACCESS  read-write
    STATUS      current
    DESCRIPTION 
        "This counter is incremented whenever the user is prompted for an account code in FAC-based mode"
    ::= { accountCodes 6 }

  bwAnonymousCallsNumRejected OBJECT-TYPE
    SYNTAX      Counter32
    MAX-ACCESS  read-write
    STATUS      current
    DESCRIPTION 
        "This counter reflects the number of incoming anonymous calls rejected"
    ::= { anonymousCallRejection 1 }

  bwAnonymousCallRejectionSPTable OBJECT-TYPE
    SYNTAX      SEQUENCE OF BwAnonymousCallRejectionSPEntry
    MAX-ACCESS  not-accessible
    STATUS      current
    DESCRIPTION 
        "This table contains the counters for Anonymous Call Rejection service measurements for service providers"
    ::= { anonymousCallRejection 2 }

  bwAnonymousCallRejectionSPEntry OBJECT-TYPE
    SYNTAX      BwAnonymousCallRejectionSPEntry
    MAX-ACCESS  not-accessible
    STATUS      current
    DESCRIPTION 
        "This row contains the counters for Anonymous Call Rejection service measurements for a service provider"
    INDEX       { bwAnonymousCallRejectionSPIndex }
    ::= { bwAnonymousCallRejectionSPTable 1 }

  BwAnonymousCallRejectionSPEntry ::= SEQUENCE {
    bwAnonymousCallRejectionSPIndex     Unsigned32,
    bwAnonymousCallRejectionSPID        DisplayString,
    bwAnonymousCallsSPNumRejected       Counter32
  }

  bwAnonymousCallRejectionSPIndex OBJECT-TYPE
    SYNTAX      Unsigned32
    MAX-ACCESS  read-only
    STATUS      current
    DESCRIPTION 
        "This integer represents the a service provider index in the system"
    ::= { bwAnonymousCallRejectionSPEntry 1 }

  bwAnonymousCallRejectionSPID OBJECT-TYPE
    SYNTAX      DisplayString
    MAX-ACCESS  read-only
    STATUS      current
    DESCRIPTION 
        "This string represents a service provider ID"
    ::= { bwAnonymousCallRejectionSPEntry 2 }

  bwAnonymousCallsSPNumRejected OBJECT-TYPE
    SYNTAX      Counter32
    MAX-ACCESS  read-write
    STATUS      current
    DESCRIPTION 
        "This counter reflects the number of incoming anonymous calls rejected by a service provider"
    ::= { bwAnonymousCallRejectionSPEntry 3 }

  bwAnonymousCallRejectionGroupTable OBJECT-TYPE
    SYNTAX      SEQUENCE OF BwAnonymousCallRejectionGroupEntry
    MAX-ACCESS  not-accessible
    STATUS      current
    DESCRIPTION 
        "This table contains the counters for Anonymous Call Rejection service measurements for group"
    ::= { anonymousCallRejection 3 }

  bwAnonymousCallRejectionGroupEntry OBJECT-TYPE
    SYNTAX      BwAnonymousCallRejectionGroupEntry
    MAX-ACCESS  not-accessible
    STATUS      current
    DESCRIPTION 
        "This row contains the counters for Anonymous Call Rejection service measurements for a group"
    INDEX       { bwAnonymousCallRejectionGroupIndex }
    ::= { bwAnonymousCallRejectionGroupTable 1 }

  BwAnonymousCallRejectionGroupEntry ::= SEQUENCE {
    bwAnonymousCallRejectionGroupIndex  Unsigned32,
    bwAnonymousCallRejectionGroupID     DisplayString,
    bwAnonymousCallsGroupNumRejected    Counter32
  }

  bwAnonymousCallRejectionGroupIndex OBJECT-TYPE
    SYNTAX      Unsigned32
    MAX-ACCESS  read-only
    STATUS      current
    DESCRIPTION 
        "This integer represents the a group index in the system"
    ::= { bwAnonymousCallRejectionGroupEntry 1 }

  bwAnonymousCallRejectionGroupID OBJECT-TYPE
    SYNTAX      DisplayString
    MAX-ACCESS  read-only
    STATUS      current
    DESCRIPTION 
        "This string represents a group ID"
    ::= { bwAnonymousCallRejectionGroupEntry 2 }

  bwAnonymousCallsGroupNumRejected OBJECT-TYPE
    SYNTAX      Counter32
    MAX-ACCESS  read-write
    STATUS      current
    DESCRIPTION 
        "This counter reflects the number of incoming anonymous calls rejected by a group"
    ::= { bwAnonymousCallRejectionGroupEntry 3 }

  bwAuthenticationNumChallenges OBJECT-TYPE
    SYNTAX      Counter32
    MAX-ACCESS  read-write
    STATUS      current
    DESCRIPTION 
        "This counter reflects the number of authentication challenges"
    ::= { authentication 1 }

  bwAuthenticationNumValidResponses OBJECT-TYPE
    SYNTAX      Counter32
    MAX-ACCESS  read-write
    STATUS      current
    DESCRIPTION 
        "This counter reflects the number of valid client authentication responses"
    ::= { authentication 2 }

  bwAuthenticationSPTable OBJECT-TYPE
    SYNTAX      SEQUENCE OF BwAuthenticationSPEntry
    MAX-ACCESS  not-accessible
    STATUS      current
    DESCRIPTION 
        "This table contains the counters for Authentication service measurements for service providers"
    ::= { authentication 3 }

  bwAuthenticationSPEntry OBJECT-TYPE
    SYNTAX      BwAuthenticationSPEntry
    MAX-ACCESS  not-accessible
    STATUS      current
    DESCRIPTION 
        "This row contains the counters for Authentication service measurements for a service provider"
    INDEX       { bwAuthenticationSPIndex }
    ::= { bwAuthenticationSPTable 1 }

  BwAuthenticationSPEntry ::= SEQUENCE {
    bwAuthenticationSPIndex                 Unsigned32,
    bwAuthenticationSPID                    DisplayString,
    bwAuthenticationSPNumChallenges         Counter32,
    bwAuthenticationSPNumValidResponses     Counter32
  }

  bwAuthenticationSPIndex OBJECT-TYPE
    SYNTAX      Unsigned32
    MAX-ACCESS  read-only
    STATUS      current
    DESCRIPTION 
        "This integer represents the a service provider index in the system"
    ::= { bwAuthenticationSPEntry 1 }

  bwAuthenticationSPID OBJECT-TYPE
    SYNTAX      DisplayString
    MAX-ACCESS  read-only
    STATUS      current
    DESCRIPTION 
        "This string represents a service provider ID"
    ::= { bwAuthenticationSPEntry 2 }

  bwAuthenticationSPNumChallenges OBJECT-TYPE
    SYNTAX      Counter32
    MAX-ACCESS  read-write
    STATUS      current
    DESCRIPTION 
        "This counter reflects the number of authentication challenges by a service provider"
    ::= { bwAuthenticationSPEntry 3 }

  bwAuthenticationSPNumValidResponses OBJECT-TYPE
    SYNTAX      Counter32
    MAX-ACCESS  read-write
    STATUS      current
    DESCRIPTION 
        "This counter reflects the number of valid client authentication responses by a service provider"
    ::= { bwAuthenticationSPEntry 4 }

  bwAuthenticationGroupTable OBJECT-TYPE
    SYNTAX      SEQUENCE OF BwAuthenticationGroupEntry
    MAX-ACCESS  not-accessible
    STATUS      current
    DESCRIPTION 
        "This table contains the counters for Authentication service measurements for groups"
    ::= { authentication 4 }

  bwAuthenticationGroupEntry OBJECT-TYPE
    SYNTAX      BwAuthenticationGroupEntry
    MAX-ACCESS  not-accessible
    STATUS      current
    DESCRIPTION 
        "This row contains the counters for Authentication service measurements for a group"
    INDEX       { bwAuthenticationGroupIndex }
    ::= { bwAuthenticationGroupTable 1 }

  BwAuthenticationGroupEntry ::= SEQUENCE {
    bwAuthenticationGroupIndex              Unsigned32,
    bwAuthenticationGroupID                 DisplayString,
    bwAuthenticationGroupNumChallenges      Counter32,
    bwAuthenticationGroupNumValidResponses  Counter32
  }

  bwAuthenticationGroupIndex OBJECT-TYPE
    SYNTAX      Unsigned32
    MAX-ACCESS  read-only
    STATUS      current
    DESCRIPTION 
        "This integer represents the a group index in the system"
    ::= { bwAuthenticationGroupEntry 1 }

  bwAuthenticationGroupID OBJECT-TYPE
    SYNTAX      DisplayString
    MAX-ACCESS  read-only
    STATUS      current
    DESCRIPTION 
        "This string represents a group ID"
    ::= { bwAuthenticationGroupEntry 2 }

  bwAuthenticationGroupNumChallenges OBJECT-TYPE
    SYNTAX      Counter32
    MAX-ACCESS  read-write
    STATUS      current
    DESCRIPTION 
        "This counter reflects the number of authentication challenges by a group"
    ::= { bwAuthenticationGroupEntry 3 }

  bwAuthenticationGroupNumValidResponses OBJECT-TYPE
    SYNTAX      Counter32
    MAX-ACCESS  read-write
    STATUS      current
    DESCRIPTION 
        "This counter reflects the number of valid client authentication responses by a group"
    ::= { bwAuthenticationGroupEntry 4 }

  bwAutoAttendantNumAnswers OBJECT-TYPE
    SYNTAX      Counter32
    MAX-ACCESS  read-write
    STATUS      current
    DESCRIPTION 
        "This counter reflects the number of times the Auto Attendant answers an incoming call"
    ::= { autoAttendant 1 }

  bwAutoAttendantNumTransfers OBJECT-TYPE
    SYNTAX      Counter32
    MAX-ACCESS  read-write
    STATUS      current
    DESCRIPTION 
        "This counter reflects the number times a call is transferred to another party
         (name dialing, ext. dialing, etc.) by the Auto Attendant"
    ::= { autoAttendant 2 }

  bwAutoAttendantSPTable OBJECT-TYPE
    SYNTAX      SEQUENCE OF BwAutoAttendantSPEntry
    MAX-ACCESS  not-accessible
    STATUS      current
    DESCRIPTION 
        "This table contains the counters for Auto Attendant service measurements for service providers"
    ::= { autoAttendant 3 }

  bwAutoAttendantSPEntry OBJECT-TYPE
    SYNTAX      BwAutoAttendantSPEntry
    MAX-ACCESS  not-accessible
    STATUS      current
    DESCRIPTION 
        "This row contains the counters for Auto Attendant Rejection service measurements for a service provider"
    INDEX       { bwAutoAttendantSPIndex }
    ::= { bwAutoAttendantSPTable 1 }

  BwAutoAttendantSPEntry ::= SEQUENCE {
    bwAutoAttendantSPIndex          Unsigned32,
    bwAutoAttendantSPID             DisplayString,
    bwAutoAttendantSPNumAnswers     Counter32,
    bwAutoAttendantSPNumTransfers   Counter32
  }

  bwAutoAttendantSPIndex OBJECT-TYPE
    SYNTAX      Unsigned32
    MAX-ACCESS  read-only
    STATUS      current
    DESCRIPTION 
        "This integer represents the a service provider index in the system"
    ::= { bwAutoAttendantSPEntry 1 }

  bwAutoAttendantSPID OBJECT-TYPE
    SYNTAX      DisplayString
    MAX-ACCESS  read-only
    STATUS      current
    DESCRIPTION 
        "This string represents a service provider ID"
    ::= { bwAutoAttendantSPEntry 2 }

  bwAutoAttendantSPNumAnswers OBJECT-TYPE
    SYNTAX      Counter32
    MAX-ACCESS  read-write
    STATUS      current
    DESCRIPTION 
        "This counter reflects the number of times the Auto Attendant answers an incoming call by a service provider"
    ::= { bwAutoAttendantSPEntry 3 }

  bwAutoAttendantSPNumTransfers OBJECT-TYPE
    SYNTAX      Counter32
    MAX-ACCESS  read-write
    STATUS      current
    DESCRIPTION 
        "This counter reflects the number times a call is transferred to another party (name dialing, ext. dialing, etc.) by the Auto Attendant by a service provider"
    ::= { bwAutoAttendantSPEntry 4 }

  bwAutoAttendantGroupTable OBJECT-TYPE
    SYNTAX      SEQUENCE OF BwAutoAttendantGroupEntry
    MAX-ACCESS  not-accessible
    STATUS      current
    DESCRIPTION 
        "This table contains the counters for Auto Attendant service measurements for Groups"
    ::= { autoAttendant 4 }

  bwAutoAttendantGroupEntry OBJECT-TYPE
    SYNTAX      BwAutoAttendantGroupEntry
    MAX-ACCESS  not-accessible
    STATUS      current
    DESCRIPTION 
        "This row contains the counters for Auto Attendant Rejection service measurements for a group"
    INDEX       { bwAutoAttendantGroupIndex }
    ::= { bwAutoAttendantGroupTable 1 }

  BwAutoAttendantGroupEntry ::= SEQUENCE {
    bwAutoAttendantGroupIndex           Unsigned32,
    bwAutoAttendantGroupID              DisplayString,
    bwAutoAttendantGroupNumAnswers      Counter32,
    bwAutoAttendantGroupNumTransfers    Counter32
  }

  bwAutoAttendantGroupIndex OBJECT-TYPE
    SYNTAX      Unsigned32
    MAX-ACCESS  read-only
    STATUS      current
    DESCRIPTION 
        "This integer represents the a group index in the system"
    ::= { bwAutoAttendantGroupEntry 1 }

  bwAutoAttendantGroupID OBJECT-TYPE
    SYNTAX      DisplayString
    MAX-ACCESS  read-only
    STATUS      current
    DESCRIPTION 
        "This string represents a group ID"
    ::= { bwAutoAttendantGroupEntry 2 }

  bwAutoAttendantGroupNumAnswers OBJECT-TYPE
    SYNTAX      Counter32
    MAX-ACCESS  read-write
    STATUS      current
    DESCRIPTION 
        "This counter reflects the number of times the Auto Attendant answers an incoming call by a group"
    ::= { bwAutoAttendantGroupEntry 3 }

  bwAutoAttendantGroupNumTransfers OBJECT-TYPE
    SYNTAX      Counter32
    MAX-ACCESS  read-write
    STATUS      current
    DESCRIPTION 
        "This counter reflects the number times a call is transferred to another party (name dialing, ext. dialing, etc.) by the Auto Attendant by a group"
    ::= { bwAutoAttendantGroupEntry 4 }

  bwCallCapacityNumCallsAttempted OBJECT-TYPE
    SYNTAX      Counter32
    MAX-ACCESS  read-write
    STATUS      current
    DESCRIPTION 
        "This counter reflects the number of calls attempted"
    ::= { callCapacity 1 }

  bwCallCapacityNumCallsBlocked OBJECT-TYPE
    SYNTAX      Counter32
    MAX-ACCESS  read-write
    STATUS      current
    DESCRIPTION 
        "This counter reflects the number of calls blocked by this service"
    ::= { callCapacity 2 }

  bwCallCapacitySPTable OBJECT-TYPE
    SYNTAX      SEQUENCE OF BwCallCapacitySPEntry
    MAX-ACCESS  not-accessible
    STATUS      current
    DESCRIPTION 
        "This table contains the counters for Call Capacity Management service measurements for service providers"
    ::= { callCapacity 3 }

  bwCallCapacitySPEntry OBJECT-TYPE
    SYNTAX      BwCallCapacitySPEntry
    MAX-ACCESS  not-accessible
    STATUS      current
    DESCRIPTION 
        "This row contains the counters for Call Capacity Management service measurements for a service provider"
    INDEX       { bwCallCapacitySPIndex }
    ::= { bwCallCapacitySPTable 1 }

  BwCallCapacitySPEntry ::= SEQUENCE {
    bwCallCapacitySPIndex               Unsigned32,
    bwCallCapacitySPID                  DisplayString,
    bwCallCapacitySPNumCallsAttempted   Counter32,
    bwCallCapacitySPNumCallsBlocked     Counter32
  }

  bwCallCapacitySPIndex OBJECT-TYPE
    SYNTAX      Unsigned32
    MAX-ACCESS  read-only
    STATUS      current
    DESCRIPTION 
        "This integer represents the a service provider index in the system"
    ::= { bwCallCapacitySPEntry 1 }

  bwCallCapacitySPID OBJECT-TYPE
    SYNTAX      DisplayString
    MAX-ACCESS  read-only
    STATUS      current
    DESCRIPTION 
        "This string represents a service provider ID"
    ::= { bwCallCapacitySPEntry 2 }

  bwCallCapacitySPNumCallsAttempted OBJECT-TYPE
    SYNTAX      Counter32
    MAX-ACCESS  read-write
    STATUS      current
    DESCRIPTION 
        "This counter reflects the number of calls attempted by a service provider"
    ::= { bwCallCapacitySPEntry 3 }

  bwCallCapacitySPNumCallsBlocked OBJECT-TYPE
    SYNTAX      Counter32
    MAX-ACCESS  read-write
    STATUS      current
    DESCRIPTION 
        "This counter reflects the number of calls blocked by this service by a service provider"
    ::= { bwCallCapacitySPEntry 4 }

  bwCallCapacityGroupTable OBJECT-TYPE
    SYNTAX      SEQUENCE OF BwCallCapacityGroupEntry
    MAX-ACCESS  not-accessible
    STATUS      current
    DESCRIPTION 
        "This table contains the counters for Call Capacity Management service measurements for groups"
    ::= { callCapacity 4 }

  bwCallCapacityGroupEntry OBJECT-TYPE
    SYNTAX      BwCallCapacityGroupEntry
    MAX-ACCESS  not-accessible
    STATUS      current
    DESCRIPTION 
        "This row contains the counters for Call Capacity Management service measurements for a group"
    INDEX       { bwCallCapacityGroupIndex }
    ::= { bwCallCapacityGroupTable 1 }

  BwCallCapacityGroupEntry ::= SEQUENCE {
    bwCallCapacityGroupIndex                Unsigned32,
    bwCallCapacityGroupID                   DisplayString,
    bwCallCapacityGroupNumCallsAttempted    Counter32,
    bwCallCapacityGroupNumCallsBlocked      Counter32
  }

  bwCallCapacityGroupIndex OBJECT-TYPE
    SYNTAX      Unsigned32
    MAX-ACCESS  read-only
    STATUS      current
    DESCRIPTION 
        "This integer represents the a group index in the system"
    ::= { bwCallCapacityGroupEntry 1 }

  bwCallCapacityGroupID OBJECT-TYPE
    SYNTAX      DisplayString
    MAX-ACCESS  read-only
    STATUS      current
    DESCRIPTION 
        "This string represents a group ID"
    ::= { bwCallCapacityGroupEntry 2 }

  bwCallCapacityGroupNumCallsAttempted OBJECT-TYPE
    SYNTAX      Counter32
    MAX-ACCESS  read-write
    STATUS      current
    DESCRIPTION 
        "This counter reflects the number of calls attempted by a group"
    ::= { bwCallCapacityGroupEntry 3 }

  bwCallCapacityGroupNumCallsBlocked OBJECT-TYPE
    SYNTAX      Counter32
    MAX-ACCESS  read-write
    STATUS      current
    DESCRIPTION 
        "This counter reflects the number of calls blocked by this service by a group"
    ::= { bwCallCapacityGroupEntry 4 }

  bwCFANumForwarded OBJECT-TYPE
    SYNTAX      Counter32
    MAX-ACCESS  read-write
    STATUS      current
    DESCRIPTION 
        "This counter reflects the number of calls forwarded"
    ::= { callForwardingAlways 1 }

  bwCFANumPhoneActivations OBJECT-TYPE
    SYNTAX      Counter32
    MAX-ACCESS  read-write
    STATUS      current
    DESCRIPTION 
        "Incremented whenever a user activates CFA via FAC"
    ::= { callForwardingAlways 2 }

  bwCFANumPhoneDeactivations OBJECT-TYPE
    SYNTAX      Counter32
    MAX-ACCESS  read-write
    STATUS      current
    DESCRIPTION 
        "Incremented whenever a user deactivates CFN via FAC"
    ::= { callForwardingAlways 3 }

  bwCallForwardingAlwaysSPTable OBJECT-TYPE
    SYNTAX      SEQUENCE OF BwCallForwardingAlwaysSPEntry
    MAX-ACCESS  not-accessible
    STATUS      current
    DESCRIPTION 
        "This table contains the counters for Call Forwarding Always service measurements for service providers"
    ::= { callForwardingAlways 4 }

  bwCallForwardingAlwaysSPEntry OBJECT-TYPE
    SYNTAX      BwCallForwardingAlwaysSPEntry
    MAX-ACCESS  not-accessible
    STATUS      current
    DESCRIPTION 
        "This row contains the counters for Call Forwarding Always service measurements for a service provider"
    INDEX       { bwCallForwardingAlwaysSPIndex }
    ::= { bwCallForwardingAlwaysSPTable 1 }

  BwCallForwardingAlwaysSPEntry ::= SEQUENCE {
    bwCallForwardingAlwaysSPIndex   Unsigned32,
    bwCallForwardingAlwaysSPID      DisplayString,
    bwCFASPNumForwarded             Counter32,
    bwCFASPNumPhoneActivations      Counter32,
    bwCFASPNumPhoneDeactivations    Counter32,
    bwCFASPDestinationChanged       Counter32,
    bwCFASPNumPhoneInterrogation    Counter32
  }

  bwCallForwardingAlwaysSPIndex OBJECT-TYPE
    SYNTAX      Unsigned32
    MAX-ACCESS  read-only
    STATUS      current
    DESCRIPTION 
        "This integer represents the a service provider index in the system"
    ::= { bwCallForwardingAlwaysSPEntry 1 }

  bwCallForwardingAlwaysSPID OBJECT-TYPE
    SYNTAX      DisplayString
    MAX-ACCESS  read-only
    STATUS      current
    DESCRIPTION 
        "This string represents a service provider ID"
    ::= { bwCallForwardingAlwaysSPEntry 2 }

  bwCFASPNumForwarded OBJECT-TYPE
    SYNTAX      Counter32
    MAX-ACCESS  read-write
    STATUS      current
    DESCRIPTION 
        "This counter reflects the number of calls forwarded for a given service provider"
    ::= { bwCallForwardingAlwaysSPEntry 3 }

  bwCFASPNumPhoneActivations OBJECT-TYPE
    SYNTAX      Counter32
    MAX-ACCESS  read-write
    STATUS      current
    DESCRIPTION 
        "Number of times CFA has been activated via FAC for users in a given service provider"
    ::= { bwCallForwardingAlwaysSPEntry 4 }

  bwCFASPNumPhoneDeactivations OBJECT-TYPE
    SYNTAX      Counter32
    MAX-ACCESS  read-write
    STATUS      current
    DESCRIPTION 
        "Number of times CFA has been deactivated via FAC for users in a given service provider"
    ::= { bwCallForwardingAlwaysSPEntry 5 }

  bwCFASPDestinationChanged OBJECT-TYPE
    SYNTAX      Counter32
    MAX-ACCESS  read-write
    STATUS      current
    DESCRIPTION 
        "Number of times CFA destination has been changed, by FAC only for a given service provider"
    ::= { bwCallForwardingAlwaysSPEntry 6 }

  bwCFASPNumPhoneInterrogation OBJECT-TYPE
    SYNTAX      Counter32
    MAX-ACCESS  read-write
    STATUS      current
    DESCRIPTION 
        "This is the number of times CFA has been interrogated via FAC for users in a given service provider."
    ::= { bwCallForwardingAlwaysSPEntry 7 }

  bwCFADestinationChanged OBJECT-TYPE
    SYNTAX      Counter32
    MAX-ACCESS  read-write
    STATUS      current
    DESCRIPTION 
        "Incremented whenever a user changes the CFA destination via FAC"
    ::= { callForwardingAlways 5 }

  bwCallForwardingAlwaysGroupTable OBJECT-TYPE
    SYNTAX      SEQUENCE OF BwCallForwardingAlwaysGroupEntry
    MAX-ACCESS  not-accessible
    STATUS      current
    DESCRIPTION 
        "This table contains the counters for Call Forwarding Always service measurements for groups"
    ::= { callForwardingAlways 6 }

  bwCallForwardingAlwaysGroupEntry OBJECT-TYPE
    SYNTAX      BwCallForwardingAlwaysGroupEntry
    MAX-ACCESS  not-accessible
    STATUS      current
    DESCRIPTION 
        "This row contains the counters for Call Forwarding Always service measurements for a group"
    INDEX       { bwCallForwardingAlwaysGroupIndex }
    ::= { bwCallForwardingAlwaysGroupTable 1 }

  BwCallForwardingAlwaysGroupEntry ::= SEQUENCE {
    bwCallForwardingAlwaysGroupIndex    Unsigned32,
    bwCallForwardingAlwaysGroupID       DisplayString,
    bwCFAGroupNumForwarded              Counter32,
    bwCFAGroupNumPhoneActivations       Counter32,
    bwCFAGroupNumPhoneDeactivations     Counter32,
    bwCFAGroupDestinationChanged        Counter32,
    bwCFAGroupNumPhoneInterrogation     Counter32
  }

  bwCallForwardingAlwaysGroupIndex OBJECT-TYPE
    SYNTAX      Unsigned32
    MAX-ACCESS  read-only
    STATUS      current
    DESCRIPTION 
        "This integer represents the a group index in the system"
    ::= { bwCallForwardingAlwaysGroupEntry 1 }

  bwCallForwardingAlwaysGroupID OBJECT-TYPE
    SYNTAX      DisplayString
    MAX-ACCESS  read-only
    STATUS      current
    DESCRIPTION 
        "This string represents a group ID"
    ::= { bwCallForwardingAlwaysGroupEntry 2 }

  bwCFAGroupNumForwarded OBJECT-TYPE
    SYNTAX      Counter32
    MAX-ACCESS  read-write
    STATUS      current
    DESCRIPTION 
        "This counter reflects the number of calls forwarded for a given group"
    ::= { bwCallForwardingAlwaysGroupEntry 3 }

  bwCFAGroupNumPhoneActivations OBJECT-TYPE
    SYNTAX      Counter32
    MAX-ACCESS  read-write
    STATUS      current
    DESCRIPTION 
        "Number of times CFA has been activated via FAC for users in a given group"
    ::= { bwCallForwardingAlwaysGroupEntry 4 }

  bwCFAGroupNumPhoneDeactivations OBJECT-TYPE
    SYNTAX      Counter32
    MAX-ACCESS  read-write
    STATUS      current
    DESCRIPTION 
        "Number of times CFA has been deactivated via FAC for users in a given group"
    ::= { bwCallForwardingAlwaysGroupEntry 5 }

  bwCFAGroupDestinationChanged OBJECT-TYPE
    SYNTAX      Counter32
    MAX-ACCESS  read-write
    STATUS      current
    DESCRIPTION 
        "Number of times CFA destination has been changed, by FAC only for a given group"
    ::= { bwCallForwardingAlwaysGroupEntry 6 }

  bwCFAGroupNumPhoneInterrogation OBJECT-TYPE
    SYNTAX      Counter32
    MAX-ACCESS  read-write
    STATUS      current
    DESCRIPTION 
        "This is the number of times CFA has been interrogated via FAC for users in a given group."
    ::= { bwCallForwardingAlwaysGroupEntry 7 }

  bwCFANumPhoneInterrogation OBJECT-TYPE
    SYNTAX      Counter32
    MAX-ACCESS  read-write
    STATUS      current
    DESCRIPTION 
        "This is the number of times CFA has been interrogated via FAC."
    ::= { callForwardingAlways 7 }

  bwCFBNumForwarded OBJECT-TYPE
    SYNTAX      Counter32
    MAX-ACCESS  read-write
    STATUS      current
    DESCRIPTION 
        "This counter reflects the number of times a call is forwarded by this service"
    ::= { callForwardingBusy 1 }

  bwCallForwardingBusySPTable OBJECT-TYPE
    SYNTAX      SEQUENCE OF BwCallForwardingBusySPEntry
    MAX-ACCESS  not-accessible
    STATUS      current
    DESCRIPTION 
        "This table contains the counters for Call Forwarding Busy service measurements for service providers"
    ::= { callForwardingBusy 2 }

  bwCallForwardingBusySPEntry OBJECT-TYPE
    SYNTAX      BwCallForwardingBusySPEntry
    MAX-ACCESS  not-accessible
    STATUS      current
    DESCRIPTION 
        "This row contains the counters for Call Forwarding Busy service measurements for a service provider"
    INDEX       { bwCallForwardingBusySPIndex }
    ::= { bwCallForwardingBusySPTable 1 }

  BwCallForwardingBusySPEntry ::= SEQUENCE {
    bwCallForwardingBusySPIndex     Unsigned32,
    bwCallForwardingBusySPID        DisplayString,
    bwCFBSPNumForwarded             Counter32,
    bwCFBSPNumPhoneActivations      Counter32,
    bwCFBSPNumPhoneDeactivations    Counter32,
    bwCFBSPDestinationChanged       Counter32,
    bwCFBSPNumPhoneInterrogation    Counter32
  }

  bwCallForwardingBusySPIndex OBJECT-TYPE
    SYNTAX      Unsigned32
    MAX-ACCESS  read-only
    STATUS      current
    DESCRIPTION 
        "This integer represents the a service provider index in the system"
    ::= { bwCallForwardingBusySPEntry 1 }

  bwCallForwardingBusySPID OBJECT-TYPE
    SYNTAX      DisplayString
    MAX-ACCESS  read-only
    STATUS      current
    DESCRIPTION 
        "This string represents a service provider ID"
    ::= { bwCallForwardingBusySPEntry 2 }

  bwCFBSPNumForwarded OBJECT-TYPE
    SYNTAX      Counter32
    MAX-ACCESS  read-write
    STATUS      current
    DESCRIPTION 
        "This counter reflects the number of times a call is forwarded by this service by a service provider"
    ::= { bwCallForwardingBusySPEntry 3 }

  bwCFBSPNumPhoneActivations OBJECT-TYPE
    SYNTAX      Counter32
    MAX-ACCESS  read-write
    STATUS      current
    DESCRIPTION 
        "Number of times CFB has been activated via FAC for users in a given service provider"
    ::= { bwCallForwardingBusySPEntry 4 }

  bwCFBSPNumPhoneDeactivations OBJECT-TYPE
    SYNTAX      Counter32
    MAX-ACCESS  read-write
    STATUS      current
    DESCRIPTION 
        "Number of times CFB has been deactivated via FAC for users in a given service provider"
    ::= { bwCallForwardingBusySPEntry 5 }

  bwCFBSPDestinationChanged OBJECT-TYPE
    SYNTAX      Counter32
    MAX-ACCESS  read-write
    STATUS      current
    DESCRIPTION 
        "Number of times CFB destination has been changed, by FAC only for a given service provider"
    ::= { bwCallForwardingBusySPEntry 6 }

  bwCFBSPNumPhoneInterrogation OBJECT-TYPE
    SYNTAX      Counter32
    MAX-ACCESS  read-write
    STATUS      current
    DESCRIPTION 
        "This is the number of times CFB has been interrogated via FAC for users in a given service provider."
    ::= { bwCallForwardingBusySPEntry 7 }

  bwCFBNumPhoneActivations OBJECT-TYPE
    SYNTAX      Counter32
    MAX-ACCESS  read-write
    STATUS      current
    DESCRIPTION 
        "Total number of times CFB has been activated via FAC"
    ::= { callForwardingBusy 3 }

  bwCFBNumPhoneDeactivations OBJECT-TYPE
    SYNTAX      Counter32
    MAX-ACCESS  read-write
    STATUS      current
    DESCRIPTION 
        "Total number of times CFB has been deactivated via FAC"
    ::= { callForwardingBusy 4 }

  bwCFBDestinationChanged OBJECT-TYPE
    SYNTAX      Counter32
    MAX-ACCESS  read-write
    STATUS      current
    DESCRIPTION 
        "Incremented whenever a user changes the CFB destination via FAC"
    ::= { callForwardingBusy 5 }

  bwCallForwardingBusyGroupTable OBJECT-TYPE
    SYNTAX      SEQUENCE OF BwCallForwardingBusyGroupEntry
    MAX-ACCESS  not-accessible
    STATUS      current
    DESCRIPTION 
        "This table contains the counters for Call Forwarding Busy service measurements for groups"
    ::= { callForwardingBusy 6 }

  bwCallForwardingBusyGroupEntry OBJECT-TYPE
    SYNTAX      BwCallForwardingBusyGroupEntry
    MAX-ACCESS  not-accessible
    STATUS      current
    DESCRIPTION 
        "This row contains the counters for Call Forwarding Busy service measurements for a group"
    INDEX       { bwCallForwardingBusyGroupIndex }
    ::= { bwCallForwardingBusyGroupTable 1 }

  BwCallForwardingBusyGroupEntry ::= SEQUENCE {
    bwCallForwardingBusyGroupIndex      Unsigned32,
    bwCallForwardingBusyGroupID         DisplayString,
    bwCFBGroupNumForwarded              Counter32,
    bwCFBGroupNumPhoneActivations       Counter32,
    bwCFBGroupNumPhoneDeactivations     Counter32,
    bwCFBGroupDestinationChanged        Counter32,
    bwCFBGroupNumPhoneInterrogation     Counter32
  }

  bwCallForwardingBusyGroupIndex OBJECT-TYPE
    SYNTAX      Unsigned32
    MAX-ACCESS  read-only
    STATUS      current
    DESCRIPTION 
        "This integer represents the a group index in the system"
    ::= { bwCallForwardingBusyGroupEntry 1 }

  bwCallForwardingBusyGroupID OBJECT-TYPE
    SYNTAX      DisplayString
    MAX-ACCESS  read-only
    STATUS      current
    DESCRIPTION 
        "This string represents a group ID"
    ::= { bwCallForwardingBusyGroupEntry 2 }

  bwCFBGroupNumForwarded OBJECT-TYPE
    SYNTAX      Counter32
    MAX-ACCESS  read-write
    STATUS      current
    DESCRIPTION 
        "This counter reflects the number of times a call is forwarded by this service by a group"
    ::= { bwCallForwardingBusyGroupEntry 3 }

  bwCFBGroupNumPhoneActivations OBJECT-TYPE
    SYNTAX      Counter32
    MAX-ACCESS  read-write
    STATUS      current
    DESCRIPTION 
        "Number of times CFB has been activated via FAC for users in a given group"
    ::= { bwCallForwardingBusyGroupEntry 4 }

  bwCFBGroupNumPhoneDeactivations OBJECT-TYPE
    SYNTAX      Counter32
    MAX-ACCESS  read-write
    STATUS      current
    DESCRIPTION 
        "Number of times CFB has been deactivated via FAC for users in a given group"
    ::= { bwCallForwardingBusyGroupEntry 5 }

  bwCFBGroupDestinationChanged OBJECT-TYPE
    SYNTAX      Counter32
    MAX-ACCESS  read-write
    STATUS      current
    DESCRIPTION 
        "Number of times CFB destination has been changed, by FAC only for a given group"
    ::= { bwCallForwardingBusyGroupEntry 6 }

  bwCFBGroupNumPhoneInterrogation OBJECT-TYPE
    SYNTAX      Counter32
    MAX-ACCESS  read-write
    STATUS      current
    DESCRIPTION 
        "This is the number of times CFB has been interrogated via FAC for users in a given group."
    ::= { bwCallForwardingBusyGroupEntry 7 }

  bwCFBNumPhoneInterrogation OBJECT-TYPE
    SYNTAX      Counter32
    MAX-ACCESS  read-write
    STATUS      current
    DESCRIPTION 
        "This is the number of times CFB has been interrogated via FAC."
    ::= { callForwardingBusy 7 }

  bwCFNANumForwarded OBJECT-TYPE
    SYNTAX      Counter32
    MAX-ACCESS  read-write
    STATUS      current
    DESCRIPTION 
        "This counter reflects the number of times a call is forwarded by this service"
    ::= { callForwardingNoAnswer 1 }

  bwCallForwardingNoAnswerSPTable OBJECT-TYPE
    SYNTAX      SEQUENCE OF BwCallForwardingNoAnswerSPEntry
    MAX-ACCESS  not-accessible
    STATUS      current
    DESCRIPTION 
        "This table contains the counters for Call Forwarding No Answer service measurements for service providers"
    ::= { callForwardingNoAnswer 2 }

  bwCallForwardingNoAnswerSPEntry OBJECT-TYPE
    SYNTAX      BwCallForwardingNoAnswerSPEntry
    MAX-ACCESS  not-accessible
    STATUS      current
    DESCRIPTION 
        "This row contains the counters for Call Forwarding No Answer service measurements for a service provider"
    INDEX       { bwCallForwardingNoAnswerSPIndex }
    ::= { bwCallForwardingNoAnswerSPTable 1 }

  BwCallForwardingNoAnswerSPEntry ::= SEQUENCE {
    bwCallForwardingNoAnswerSPIndex     Integer32,
    bwCallForwardingNoAnswerSPID        DisplayString,
    bwCFNASPNumForwarded                Counter32,
    bwCFNASPDestinationChanged          Counter32,
    bwCFNASPNumPhoneActivations         Counter32,
    bwCFNASPNumPhoneDeactivations       Counter32,
    bwCFNASPNumPhoneInterrogation       Counter32
  }

  bwCallForwardingNoAnswerSPIndex OBJECT-TYPE
    SYNTAX      Integer32 (-2147483648..2147483647)
    MAX-ACCESS  read-only
    STATUS      current
    DESCRIPTION 
        "This integer represents the a service provider index in the system"
    ::= { bwCallForwardingNoAnswerSPEntry 1 }

  bwCallForwardingNoAnswerSPID OBJECT-TYPE
    SYNTAX      DisplayString
    MAX-ACCESS  read-only
    STATUS      current
    DESCRIPTION 
        "This string represents a service provider ID"
    ::= { bwCallForwardingNoAnswerSPEntry 2 }

  bwCFNASPNumForwarded OBJECT-TYPE
    SYNTAX      Counter32
    MAX-ACCESS  read-write
    STATUS      current
    DESCRIPTION 
        "This counter reflects the number of times a call is forwarded by this service by a service provider"
    ::= { bwCallForwardingNoAnswerSPEntry 3 }

  bwCFNASPDestinationChanged OBJECT-TYPE
    SYNTAX      Counter32
    MAX-ACCESS  read-write
    STATUS      current
    DESCRIPTION 
        "Number of times CFNA destination has been changed, by FAC only for a given service provider"
    ::= { bwCallForwardingNoAnswerSPEntry 4 }

  bwCFNASPNumPhoneActivations OBJECT-TYPE
    SYNTAX      Counter32
    MAX-ACCESS  read-write
    STATUS      current
    DESCRIPTION 
        "Number of times CFNA has been activated via FAC for users in a given service provider"
    ::= { bwCallForwardingNoAnswerSPEntry 5 }

  bwCFNASPNumPhoneDeactivations OBJECT-TYPE
    SYNTAX      Counter32
    MAX-ACCESS  read-write
    STATUS      current
    DESCRIPTION 
        "Number of times CFNA has been deactivated via FAC for users in a given service provider"
    ::= { bwCallForwardingNoAnswerSPEntry 6 }

  bwCFNASPNumPhoneInterrogation OBJECT-TYPE
    SYNTAX      Counter32
    MAX-ACCESS  read-write
    STATUS      current
    DESCRIPTION 
        "This is the number of times CFNA has been interrogated via FAC for users in a given service provider."
    ::= { bwCallForwardingNoAnswerSPEntry 7 }

  bwCFNADestinationChanged OBJECT-TYPE
    SYNTAX      Counter32
    MAX-ACCESS  read-write
    STATUS      current
    DESCRIPTION 
        "Incremented whenever a user changes the CFNA destination via FAC"
    ::= { callForwardingNoAnswer 3 }

  bwCFNANumPhoneActivations OBJECT-TYPE
    SYNTAX      Counter32
    MAX-ACCESS  read-write
    STATUS      current
    DESCRIPTION 
        "Total number of times CFNA has been activated via FAC"
    ::= { callForwardingNoAnswer 4 }

  bwCFNANumPhoneDeactivations OBJECT-TYPE
    SYNTAX      Counter32
    MAX-ACCESS  read-write
    STATUS      current
    DESCRIPTION 
        "Total number of times CFNA has been deactivated via FAC"
    ::= { callForwardingNoAnswer 5 }

  bwCallForwardingNoAnswerGroupTable OBJECT-TYPE
    SYNTAX      SEQUENCE OF BwCallForwardingNoAnswerGroupEntry
    MAX-ACCESS  not-accessible
    STATUS      current
    DESCRIPTION 
        "This table contains the counters for Call Forwarding No Answer service measurements for groups"
    ::= { callForwardingNoAnswer 6 }

  bwCallForwardingNoAnswerGroupEntry OBJECT-TYPE
    SYNTAX      BwCallForwardingNoAnswerGroupEntry
    MAX-ACCESS  not-accessible
    STATUS      current
    DESCRIPTION 
        "This row contains the counters for Call Forwarding No Answer service measurements for a group"
    INDEX       { bwCallForwardingNoAnswerGroupIndex }
    ::= { bwCallForwardingNoAnswerGroupTable 1 }

  BwCallForwardingNoAnswerGroupEntry ::= SEQUENCE {
    bwCallForwardingNoAnswerGroupIndex  Integer32,
    bwCallForwardingNoAnswerGroupID     DisplayString,
    bwCFNAGroupNumForwarded             Counter32,
    bwCFNAGroupDestinationChanged       Counter32,
    bwCFNAGroupNumPhoneActivations      Counter32,
    bwCFNAGroupNumPhoneDeactivations    Counter32,
    bwCFNAGroupNumPhoneInterrogation    Counter32
  }

  bwCallForwardingNoAnswerGroupIndex OBJECT-TYPE
    SYNTAX      Integer32 (-2147483648..2147483647)
    MAX-ACCESS  read-only
    STATUS      current
    DESCRIPTION 
        "This integer represents the a group index in the system"
    ::= { bwCallForwardingNoAnswerGroupEntry 1 }

  bwCallForwardingNoAnswerGroupID OBJECT-TYPE
    SYNTAX      DisplayString
    MAX-ACCESS  read-only
    STATUS      current
    DESCRIPTION 
        "This string represents a group ID"
    ::= { bwCallForwardingNoAnswerGroupEntry 2 }

  bwCFNAGroupNumForwarded OBJECT-TYPE
    SYNTAX      Counter32
    MAX-ACCESS  read-write
    STATUS      current
    DESCRIPTION 
        "This counter reflects the number of times a call is forwarded by this service by a group"
    ::= { bwCallForwardingNoAnswerGroupEntry 3 }

  bwCFNAGroupDestinationChanged OBJECT-TYPE
    SYNTAX      Counter32
    MAX-ACCESS  read-write
    STATUS      current
    DESCRIPTION 
        "Number of times CFNA destination has been changed, by FAC only for a given group"
    ::= { bwCallForwardingNoAnswerGroupEntry 4 }

  bwCFNAGroupNumPhoneActivations OBJECT-TYPE
    SYNTAX      Counter32
    MAX-ACCESS  read-write
    STATUS      current
    DESCRIPTION 
        "Number of times CFNA has been activated via FAC for users in a given group"
    ::= { bwCallForwardingNoAnswerGroupEntry 5 }

  bwCFNAGroupNumPhoneDeactivations OBJECT-TYPE
    SYNTAX      Counter32
    MAX-ACCESS  read-write
    STATUS      current
    DESCRIPTION 
        "Number of times CFNA has been deactivated via FAC for users in a given group"
    ::= { bwCallForwardingNoAnswerGroupEntry 6 }

  bwCFNAGroupNumPhoneInterrogation OBJECT-TYPE
    SYNTAX      Counter32
    MAX-ACCESS  read-write
    STATUS      current
    DESCRIPTION 
        "This is the number of times CFNA has been interrogated via FAC for users in a given group."
    ::= { bwCallForwardingNoAnswerGroupEntry 7 }

  bwCFNANumPhoneInterrogation OBJECT-TYPE
    SYNTAX      Counter32
    MAX-ACCESS  read-write
    STATUS      current
    DESCRIPTION 
        "This is the number of times CFNA has been interrogated via FAC."
    ::= { callForwardingNoAnswer 7 }

  bwCallNotifyNumNotifications OBJECT-TYPE
    SYNTAX      Counter32
    MAX-ACCESS  read-write
    STATUS      current
    DESCRIPTION 
        "This counter reflects the number of times a criteria evaluates successfully and the
         service executes"
    ::= { callNotify 1 }

  bwCallNotifySPTable OBJECT-TYPE
    SYNTAX      SEQUENCE OF BwCallNotifySPEntry
    MAX-ACCESS  not-accessible
    STATUS      current
    DESCRIPTION 
        "This table contains the counters for Call Notify service measurements for service providers"
    ::= { callNotify 2 }

  bwCallNotifySPEntry OBJECT-TYPE
    SYNTAX      BwCallNotifySPEntry
    MAX-ACCESS  not-accessible
    STATUS      current
    DESCRIPTION 
        "This row contains the counters for Call Notify service measurements for a service provider"
    INDEX       { bwCallNotifySPIndex }
    ::= { bwCallNotifySPTable 1 }

  BwCallNotifySPEntry ::= SEQUENCE {
    bwCallNotifySPIndex             Unsigned32,
    bwCallNotifySPID                DisplayString,
    bwCallNotifySPNumNotifications  Counter32
  }

  bwCallNotifySPIndex OBJECT-TYPE
    SYNTAX      Unsigned32
    MAX-ACCESS  read-only
    STATUS      current
    DESCRIPTION 
        "This integer represents the a service provider index in the system"
    ::= { bwCallNotifySPEntry 1 }

  bwCallNotifySPID OBJECT-TYPE
    SYNTAX      DisplayString
    MAX-ACCESS  read-only
    STATUS      current
    DESCRIPTION 
        "This string represents a service provider ID"
    ::= { bwCallNotifySPEntry 2 }

  bwCallNotifySPNumNotifications OBJECT-TYPE
    SYNTAX      Counter32
    MAX-ACCESS  read-write
    STATUS      current
    DESCRIPTION 
        "This counter reflects the number of times a criteria evaluates successfully and the service executes by a service provider"
    ::= { bwCallNotifySPEntry 3 }

  bwCallNotifyGroupTable OBJECT-TYPE
    SYNTAX      SEQUENCE OF BwCallNotifyGroupEntry
    MAX-ACCESS  not-accessible
    STATUS      current
    DESCRIPTION 
        "This table contains the counters for Call Notify service measurements for groups"
    ::= { callNotify 3 }

  bwCallNotifyGroupEntry OBJECT-TYPE
    SYNTAX      BwCallNotifyGroupEntry
    MAX-ACCESS  not-accessible
    STATUS      current
    DESCRIPTION 
        "This row contains the counters for Call Notify service measurements for a group"
    INDEX       { bwCallNotifyGroupIndex }
    ::= { bwCallNotifyGroupTable 1 }

  BwCallNotifyGroupEntry ::= SEQUENCE {
    bwCallNotifyGroupIndex              Unsigned32,
    bwCallNotifyGroupID                 DisplayString,
    bwCallNotifyGroupNumNotifications   Counter32
  }

  bwCallNotifyGroupIndex OBJECT-TYPE
    SYNTAX      Unsigned32
    MAX-ACCESS  read-only
    STATUS      current
    DESCRIPTION 
        "This integer represents the a group index in the system"
    ::= { bwCallNotifyGroupEntry 1 }

  bwCallNotifyGroupID OBJECT-TYPE
    SYNTAX      DisplayString
    MAX-ACCESS  read-only
    STATUS      current
    DESCRIPTION 
        "This string represents a group ID"
    ::= { bwCallNotifyGroupEntry 2 }

  bwCallNotifyGroupNumNotifications OBJECT-TYPE
    SYNTAX      Counter32
    MAX-ACCESS  read-write
    STATUS      current
    DESCRIPTION 
        "This counter reflects the number of times a criteria evaluates successfully and the service executes by a group"
    ::= { bwCallNotifyGroupEntry 3 }

  bwCallParkNumAttempts OBJECT-TYPE
    SYNTAX      Counter32
    MAX-ACCESS  read-write
    STATUS      current
    DESCRIPTION 
        "This counter reflects the number of times a user attempts to park a call"
    ::= { callPark 1 }

  bwCallParkNumFailures OBJECT-TYPE
    SYNTAX      Counter32
    MAX-ACCESS  read-write
    STATUS      current
    DESCRIPTION 
        "This counter reflects the number of failed attempts to park a call"
    ::= { callPark 2 }

  bwCallParkNumRetrieveAttempts OBJECT-TYPE
    SYNTAX      Counter32
    MAX-ACCESS  read-write
    STATUS      current
    DESCRIPTION 
        "This counter reflects the number of times a user attempts to retrieve a parked call"
    ::= { callPark 3 }

  bwCallParkNumRetrieveFailures OBJECT-TYPE
    SYNTAX      Counter32
    MAX-ACCESS  read-write
    STATUS      current
    DESCRIPTION 
        "This counter reflects the number of times an attempt to retrieve a parked call fails"
    ::= { callPark 4 }

  bwCallParkSPTable OBJECT-TYPE
    SYNTAX      SEQUENCE OF BwCallParkSPEntry
    MAX-ACCESS  not-accessible
    STATUS      current
    DESCRIPTION 
        "This table contains the counters for Call Park service measurements for service providers"
    ::= { callPark 5 }

  bwCallParkSPEntry OBJECT-TYPE
    SYNTAX      BwCallParkSPEntry
    MAX-ACCESS  not-accessible
    STATUS      current
    DESCRIPTION 
        "This row contains the counters for Call Park service measurements for a service provider"
    INDEX       { bwCallParkSPIndex }
    ::= { bwCallParkSPTable 1 }

  BwCallParkSPEntry ::= SEQUENCE {
    bwCallParkSPIndex                   Unsigned32,
    bwCallParkSPID                      DisplayString,
    bwCallParkSPNumAttempts             Counter32,
    bwCallParkSPNumFailures             Counter32,
    bwCallParkSPNumRetrieveAttempts     Counter32,
    bwCallParkSPNumRetrieveFailures     Counter32
  }

  bwCallParkSPIndex OBJECT-TYPE
    SYNTAX      Unsigned32
    MAX-ACCESS  read-only
    STATUS      current
    DESCRIPTION 
        "This integer represents the a service provider index in the system"
    ::= { bwCallParkSPEntry 1 }

  bwCallParkSPID OBJECT-TYPE
    SYNTAX      DisplayString
    MAX-ACCESS  read-only
    STATUS      current
    DESCRIPTION 
        "This string represents a service provider ID"
    ::= { bwCallParkSPEntry 2 }

  bwCallParkSPNumAttempts OBJECT-TYPE
    SYNTAX      Counter32
    MAX-ACCESS  read-write
    STATUS      current
    DESCRIPTION 
        "This counter reflects the number of times a user attempts to park a call by a service provider"
    ::= { bwCallParkSPEntry 3 }

  bwCallParkSPNumFailures OBJECT-TYPE
    SYNTAX      Counter32
    MAX-ACCESS  read-write
    STATUS      current
    DESCRIPTION 
        "This counter reflects the number of failed attempts to park a call by a service provider"
    ::= { bwCallParkSPEntry 4 }

  bwCallParkSPNumRetrieveAttempts OBJECT-TYPE
    SYNTAX      Counter32
    MAX-ACCESS  read-write
    STATUS      current
    DESCRIPTION 
        "This counter reflects the number of times a user attempts to retrieve a parked call by a service provider"
    ::= { bwCallParkSPEntry 5 }

  bwCallParkSPNumRetrieveFailures OBJECT-TYPE
    SYNTAX      Counter32
    MAX-ACCESS  read-write
    STATUS      current
    DESCRIPTION 
        "This counter reflects the number of times an attempt to retrieve a parked call fails by a service provider"
    ::= { bwCallParkSPEntry 6 }

  bwCallParkGroupTable OBJECT-TYPE
    SYNTAX      SEQUENCE OF BwCallParkGroupEntry
    MAX-ACCESS  not-accessible
    STATUS      current
    DESCRIPTION 
        "This table contains the counters for Call Park service measurements for groups"
    ::= { callPark 6 }

  bwCallParkGroupEntry OBJECT-TYPE
    SYNTAX      BwCallParkGroupEntry
    MAX-ACCESS  not-accessible
    STATUS      current
    DESCRIPTION 
        "This row contains the counters for Call Park service measurements for a group"
    INDEX       { bwCallParkGroupIndex }
    ::= { bwCallParkGroupTable 1 }

  BwCallParkGroupEntry ::= SEQUENCE {
    bwCallParkGroupIndex                Unsigned32,
    bwCallParkGroupID                   DisplayString,
    bwCallParkGroupNumAttempts          Counter32,
    bwCallParkGroupNumFailures          Counter32,
    bwCallParkGroupNumRetrieveAttempts  Counter32,
    bwCallParkGroupNumRetrieveFailures  Counter32
  }

  bwCallParkGroupIndex OBJECT-TYPE
    SYNTAX      Unsigned32
    MAX-ACCESS  read-only
    STATUS      current
    DESCRIPTION 
        "This integer represents the a group index in the system"
    ::= { bwCallParkGroupEntry 1 }

  bwCallParkGroupID OBJECT-TYPE
    SYNTAX      DisplayString
    MAX-ACCESS  read-only
    STATUS      current
    DESCRIPTION 
        "This string represents a group ID"
    ::= { bwCallParkGroupEntry 2 }

  bwCallParkGroupNumAttempts OBJECT-TYPE
    SYNTAX      Counter32
    MAX-ACCESS  read-write
    STATUS      current
    DESCRIPTION 
        "This counter reflects the number of times a user attempts to park a call by a group"
    ::= { bwCallParkGroupEntry 3 }

  bwCallParkGroupNumFailures OBJECT-TYPE
    SYNTAX      Counter32
    MAX-ACCESS  read-write
    STATUS      current
    DESCRIPTION 
        "This counter reflects the number of failed attempts to park a call by a group"
    ::= { bwCallParkGroupEntry 4 }

  bwCallParkGroupNumRetrieveAttempts OBJECT-TYPE
    SYNTAX      Counter32
    MAX-ACCESS  read-write
    STATUS      current
    DESCRIPTION 
        "This counter reflects the number of times a user attempts to retrieve a parked call by a group"
    ::= { bwCallParkGroupEntry 5 }

  bwCallParkGroupNumRetrieveFailures OBJECT-TYPE
    SYNTAX      Counter32
    MAX-ACCESS  read-write
    STATUS      current
    DESCRIPTION 
        "This counter reflects the number of times an attempt to retrieve a parked call fails by a group"
    ::= { bwCallParkGroupEntry 6 }

  bwCallPickupNumAttempts OBJECT-TYPE
    SYNTAX      Counter32
    MAX-ACCESS  read-write
    STATUS      current
    DESCRIPTION 
        "This counter reflects the number of user attempts to pick up an incoming call"
    ::= { callPickup 1 }

  bwCallPickupNumFailures OBJECT-TYPE
    SYNTAX      Counter32
    MAX-ACCESS  read-write
    STATUS      current
    DESCRIPTION 
        "This counter reflects the number of failed attempts to pick up an incoming call"
    ::= { callPickup 2 }

  bwCallPickupSPTable OBJECT-TYPE
    SYNTAX      SEQUENCE OF BwCallPickupSPEntry
    MAX-ACCESS  not-accessible
    STATUS      current
    DESCRIPTION 
        "This table contains the counters for Call Pickup service measurements for service providers"
    ::= { callPickup 3 }

  bwCallPickupSPEntry OBJECT-TYPE
    SYNTAX      BwCallPickupSPEntry
    MAX-ACCESS  not-accessible
    STATUS      current
    DESCRIPTION 
        "This row contains the counters for Call Pickup service measurements for a service provider"
    INDEX       { bwCallPickupSPIndex }
    ::= { bwCallPickupSPTable 1 }

  BwCallPickupSPEntry ::= SEQUENCE {
    bwCallPickupSPIndex         Unsigned32,
    bwCallPickupSPID            DisplayString,
    bwCallPickupSPNumAttempts   Counter32,
    bwCallPickupSPNumFailures   Counter32
  }

  bwCallPickupSPIndex OBJECT-TYPE
    SYNTAX      Unsigned32
    MAX-ACCESS  read-only
    STATUS      current
    DESCRIPTION 
        "This integer represents the a service provider index in the system"
    ::= { bwCallPickupSPEntry 1 }

  bwCallPickupSPID OBJECT-TYPE
    SYNTAX      DisplayString
    MAX-ACCESS  read-only
    STATUS      current
    DESCRIPTION 
        "This string represents a service provider ID"
    ::= { bwCallPickupSPEntry 2 }

  bwCallPickupSPNumAttempts OBJECT-TYPE
    SYNTAX      Counter32
    MAX-ACCESS  read-write
    STATUS      current
    DESCRIPTION 
        "This counter reflects the number of user attempts to pick up an incoming call by a service provider"
    ::= { bwCallPickupSPEntry 3 }

  bwCallPickupSPNumFailures OBJECT-TYPE
    SYNTAX      Counter32
    MAX-ACCESS  read-write
    STATUS      current
    DESCRIPTION 
        "This counter reflects the number of failed attempts to pick up an incoming call by a service provider"
    ::= { bwCallPickupSPEntry 4 }

  bwCallPickupGroupTable OBJECT-TYPE
    SYNTAX      SEQUENCE OF BwCallPickupGroupEntry
    MAX-ACCESS  not-accessible
    STATUS      current
    DESCRIPTION 
        "This table contains the counters for Call Pickup service measurements for groups"
    ::= { callPickup 4 }

  bwCallPickupGroupEntry OBJECT-TYPE
    SYNTAX      BwCallPickupGroupEntry
    MAX-ACCESS  not-accessible
    STATUS      current
    DESCRIPTION 
        "This row contains the counters for Call Pickup service measurements for a group"
    INDEX       { bwCallPickupGroupIndex }
    ::= { bwCallPickupGroupTable 1 }

  BwCallPickupGroupEntry ::= SEQUENCE {
    bwCallPickupGroupIndex          Unsigned32,
    bwCallPickupGroupID             DisplayString,
    bwCallPickupGroupNumAttempts    Counter32,
    bwCallPickupGroupNumFailures    Counter32
  }

  bwCallPickupGroupIndex OBJECT-TYPE
    SYNTAX      Unsigned32
    MAX-ACCESS  read-only
    STATUS      current
    DESCRIPTION 
        "This integer represents the a Group index in the system"
    ::= { bwCallPickupGroupEntry 1 }

  bwCallPickupGroupID OBJECT-TYPE
    SYNTAX      DisplayString
    MAX-ACCESS  read-only
    STATUS      current
    DESCRIPTION 
        "This string represents a Group ID"
    ::= { bwCallPickupGroupEntry 2 }

  bwCallPickupGroupNumAttempts OBJECT-TYPE
    SYNTAX      Counter32
    MAX-ACCESS  read-write
    STATUS      current
    DESCRIPTION 
        "This counter reflects the number of user attempts to pick up an incoming call by a Group"
    ::= { bwCallPickupGroupEntry 3 }

  bwCallPickupGroupNumFailures OBJECT-TYPE
    SYNTAX      Counter32
    MAX-ACCESS  read-write
    STATUS      current
    DESCRIPTION 
        "This counter reflects the number of failed attempts to pick up an incoming call by a Group"
    ::= { bwCallPickupGroupEntry 4 }

  bwCallReturnNumReturns OBJECT-TYPE
    SYNTAX      Counter32
    MAX-ACCESS  read-write
    STATUS      current
    DESCRIPTION 
        "This counter reflects the number of times this service is executed"
    ::= { callReturn 1 }

  bwCallReturnSPTable OBJECT-TYPE
    SYNTAX      SEQUENCE OF BwCallReturnSPEntry
    MAX-ACCESS  not-accessible
    STATUS      current
    DESCRIPTION 
        "This table contains the counters for Call Return service measurements for service providers"
    ::= { callReturn 2 }

  bwCallReturnSPEntry OBJECT-TYPE
    SYNTAX      BwCallReturnSPEntry
    MAX-ACCESS  not-accessible
    STATUS      current
    DESCRIPTION 
        "This row contains the counters for Call Return service measurements for a service provider"
    INDEX       { bwCallReturnSPIndex }
    ::= { bwCallReturnSPTable 1 }

  BwCallReturnSPEntry ::= SEQUENCE {
    bwCallReturnSPIndex         Unsigned32,
    bwCallReturnSPID            DisplayString,
    bwCallReturnSPNumReturns    Counter32
  }

  bwCallReturnSPIndex OBJECT-TYPE
    SYNTAX      Unsigned32
    MAX-ACCESS  read-only
    STATUS      current
    DESCRIPTION 
        "This integer represents the a service provider index in the system"
    ::= { bwCallReturnSPEntry 1 }

  bwCallReturnSPID OBJECT-TYPE
    SYNTAX      DisplayString
    MAX-ACCESS  read-only
    STATUS      current
    DESCRIPTION 
        "This string represents a service provider ID"
    ::= { bwCallReturnSPEntry 2 }

  bwCallReturnSPNumReturns OBJECT-TYPE
    SYNTAX      Counter32
    MAX-ACCESS  read-write
    STATUS      current
    DESCRIPTION 
        "This counter reflects the number of times this service is executed by a service provider"
    ::= { bwCallReturnSPEntry 3 }

  bwCallReturnGroupTable OBJECT-TYPE
    SYNTAX      SEQUENCE OF BwCallReturnGroupEntry
    MAX-ACCESS  not-accessible
    STATUS      current
    DESCRIPTION 
        "This table contains the counters for Call Return service measurements for groups"
    ::= { callReturn 3 }

  bwCallReturnGroupEntry OBJECT-TYPE
    SYNTAX      BwCallReturnGroupEntry
    MAX-ACCESS  not-accessible
    STATUS      current
    DESCRIPTION 
        "This row contains the counters for Call Return service measurements for a group"
    INDEX       { bwCallReturnGroupIndex }
    ::= { bwCallReturnGroupTable 1 }

  BwCallReturnGroupEntry ::= SEQUENCE {
    bwCallReturnGroupIndex          Unsigned32,
    bwCallReturnGroupID             DisplayString,
    bwCallReturnGroupNumReturns     Counter32
  }

  bwCallReturnGroupIndex OBJECT-TYPE
    SYNTAX      Unsigned32
    MAX-ACCESS  read-only
    STATUS      current
    DESCRIPTION 
        "This integer represents the a group index in the system"
    ::= { bwCallReturnGroupEntry 1 }

  bwCallReturnGroupID OBJECT-TYPE
    SYNTAX      DisplayString
    MAX-ACCESS  read-only
    STATUS      current
    DESCRIPTION 
        "This string represents a group ID"
    ::= { bwCallReturnGroupEntry 2 }

  bwCallReturnGroupNumReturns OBJECT-TYPE
    SYNTAX      Counter32
    MAX-ACCESS  read-write
    STATUS      current
    DESCRIPTION 
        "This counter reflects the number of times this service is executed by a group"
    ::= { bwCallReturnGroupEntry 3 }

  bwCommPilotCallMgrNumDial OBJECT-TYPE
    SYNTAX      Counter32
    MAX-ACCESS  read-write
    STATUS      current
    DESCRIPTION 
        "This counter reflects the number of dial requests from a CommPilot Call Mgr that
         results in an outgoing call"
    ::= { commPilotCallManager 1 }

  bwCommPilotCallMgrNumAnswer OBJECT-TYPE
    SYNTAX      Counter32
    MAX-ACCESS  read-write
    STATUS      current
    DESCRIPTION 
        "This counter reflects the number of times an incoming call being answered from the
         CommPilot Call Mgr results in that call being answered"
    ::= { commPilotCallManager 2 }

  bwCommPilotCallMgrNumRelease OBJECT-TYPE
    SYNTAX      Counter32
    MAX-ACCESS  read-write
    STATUS      current
    DESCRIPTION 
        "This counter reflects the number of times a Release request from the CommPilot Call
         Mgr results in the call being released"
    ::= { commPilotCallManager 3 }

  bwCommPilotCallMgrNumHold OBJECT-TYPE
    SYNTAX      Counter32
    MAX-ACCESS  read-write
    STATUS      current
    DESCRIPTION 
        "This counter reflects the number of times a Hold request from the CommPilot Call Mgr
         results in the call being held"
    ::= { commPilotCallManager 4 }

  bwCommPilotCallMgrNumTransfer OBJECT-TYPE
    SYNTAX      Counter32
    MAX-ACCESS  read-write
    STATUS      current
    DESCRIPTION 
        "This counter reflects the number of times a Transfer request from the CommPilot Call
         Mgr results in the call being transferred"
    ::= { commPilotCallManager 5 }

  bwCommPilotCallMgrNumConference OBJECT-TYPE
    SYNTAX      Counter32
    MAX-ACCESS  read-write
    STATUS      current
    DESCRIPTION 
        "This counter reflects the number of times a Conference request from the CommPilot
         Call Mgr results in two calls being conferenced"
    ::= { commPilotCallManager 6 }

  bwCommPilotCallMgrNumTransferVM OBJECT-TYPE
    SYNTAX      Counter32
    MAX-ACCESS  read-write
    STATUS      current
    DESCRIPTION 
        "This counter reflects the number of times a user attempts to send a call to voicemail"
    ::= { commPilotCallManager 7 }

  bwCommPilotCallManagerSPTable OBJECT-TYPE
    SYNTAX      SEQUENCE OF BwCommPilotCallManagerSPEntry
    MAX-ACCESS  not-accessible
    STATUS      current
    DESCRIPTION 
        "This table contains the counters for CommPilot Call Manager service measurements for service providers"
    ::= { commPilotCallManager 8 }

  bwCommPilotCallManagerSPEntry OBJECT-TYPE
    SYNTAX      BwCommPilotCallManagerSPEntry
    MAX-ACCESS  not-accessible
    STATUS      current
    DESCRIPTION 
        "This row contains the counters for CommPilot Call Manager service measurements for a service provider"
    INDEX       { bwCommPilotCallManagerSPIndex }
    ::= { bwCommPilotCallManagerSPTable 1 }

  BwCommPilotCallManagerSPEntry ::= SEQUENCE {
    bwCommPilotCallManagerSPIndex               Unsigned32,
    bwCommPilotCallManagerSPID                  DisplayString,
    bwCommPilotCallMgrSPNumDial                 Counter32,
    bwCommPilotCallMgrSPNumAnswer               Counter32,
    bwCommPilotCallMgrSPNumRelease              Counter32,
    bwCommPilotCallMgrSPNumHold                 Counter32,
    bwCommPilotCallMgrSPNumTransfer             Counter32,
    bwCommPilotCallMgrSPNumConference           Counter32,
    bwCommPilotCallMgrSPNumTransferVM           Counter32,
    bwCommPilotCallMgrSPNumConferenceAnswer     Counter32,
    bwCommPilotCallMgrSPNumConferenceHold       Counter32,
    bwCommPilotCallMgrSPNumConferenceRelease    Counter32,
    bwCommPilotCallMgrSPNumTransferCC           Counter32,
    bwCommPilotCallMgrSPNumConferenceAdd        Counter32,
    bwCommPilotCallMgrSPNumCallPark             Counter32,
    bwCommPilotCallMgrSPNumGroupCallPark        Counter32,
    bwCommPilotCallMgrSPNumCallParkRetrieve     Counter32
  }

  bwCommPilotCallManagerSPIndex OBJECT-TYPE
    SYNTAX      Unsigned32
    MAX-ACCESS  read-only
    STATUS      current
    DESCRIPTION 
        "This integer represents the a service provider index in the system"
    ::= { bwCommPilotCallManagerSPEntry 1 }

  bwCommPilotCallManagerSPID OBJECT-TYPE
    SYNTAX      DisplayString
    MAX-ACCESS  read-only
    STATUS      current
    DESCRIPTION 
        "This string represents a service provider ID"
    ::= { bwCommPilotCallManagerSPEntry 2 }

  bwCommPilotCallMgrSPNumDial OBJECT-TYPE
    SYNTAX      Counter32
    MAX-ACCESS  read-write
    STATUS      current
    DESCRIPTION 
        "This counter reflects the number of dial requests from a CommPilot Call Mgr that results in an outgoing call by a service provider"
    ::= { bwCommPilotCallManagerSPEntry 3 }

  bwCommPilotCallMgrSPNumAnswer OBJECT-TYPE
    SYNTAX      Counter32
    MAX-ACCESS  read-write
    STATUS      current
    DESCRIPTION 
        "This counter reflects the number of times an incoming call being answered from the CommPilot Call Mgr results in that call being answered by a service provider"
    ::= { bwCommPilotCallManagerSPEntry 4 }

  bwCommPilotCallMgrSPNumRelease OBJECT-TYPE
    SYNTAX      Counter32
    MAX-ACCESS  read-write
    STATUS      current
    DESCRIPTION 
        "This counter reflects the number of times a Release request from the CommPilot Call Mgr results in the call being released by a service provider"
    ::= { bwCommPilotCallManagerSPEntry 5 }

  bwCommPilotCallMgrSPNumHold OBJECT-TYPE
    SYNTAX      Counter32
    MAX-ACCESS  read-write
    STATUS      current
    DESCRIPTION 
        "This counter reflects the number of times a Hold request from the CommPilot Call Mgr results in the call being held by a service provider"
    ::= { bwCommPilotCallManagerSPEntry 6 }

  bwCommPilotCallMgrSPNumTransfer OBJECT-TYPE
    SYNTAX      Counter32
    MAX-ACCESS  read-write
    STATUS      current
    DESCRIPTION 
        "This counter reflects the number of times a Transfer request from the CommPilot Call Mgr results in the call being transferred by a service provider"
    ::= { bwCommPilotCallManagerSPEntry 7 }

  bwCommPilotCallMgrSPNumConference OBJECT-TYPE
    SYNTAX      Counter32
    MAX-ACCESS  read-write
    STATUS      current
    DESCRIPTION 
        "This counter reflects the number of times a Conference request from the CommPilot Call Mgr results in two calls being conferenced by a service provider"
    ::= { bwCommPilotCallManagerSPEntry 8 }

  bwCommPilotCallMgrSPNumTransferVM OBJECT-TYPE
    SYNTAX      Counter32
    MAX-ACCESS  read-write
    STATUS      current
    DESCRIPTION 
        "This counter reflects the number of times a user attempts to send a call to voicemail by a service provider"
    ::= { bwCommPilotCallManagerSPEntry 9 }

  bwCommPilotCallMgrSPNumConferenceAnswer OBJECT-TYPE
    SYNTAX      Counter32
    MAX-ACCESS  read-write
    STATUS      current
    DESCRIPTION 
        "This counter reflects the number of times a held conference has been answered/retrieved from the CommPilot Call Mgr by a service provider"
    ::= { bwCommPilotCallManagerSPEntry 10 }

  bwCommPilotCallMgrSPNumConferenceHold OBJECT-TYPE
    SYNTAX      Counter32
    MAX-ACCESS  read-write
    STATUS      current
    DESCRIPTION 
        "This counter reflects the number of times a Conference has been held from the CommPilot Call Mgr by a service provider by the service provider"
    ::= { bwCommPilotCallManagerSPEntry 11 }

  bwCommPilotCallMgrSPNumConferenceRelease OBJECT-TYPE
    SYNTAX      Counter32
    MAX-ACCESS  read-write
    STATUS      current
    DESCRIPTION 
        "This counter reflects the number of times a Conference has been released from the CommPilot Call Mgr by a service provider by the service provider"
    ::= { bwCommPilotCallManagerSPEntry 12 }

  bwCommPilotCallMgrSPNumTransferCC OBJECT-TYPE
    SYNTAX      Counter32
    MAX-ACCESS  read-write
    STATUS      current
    DESCRIPTION 
        "This counter reflects the number of CAP callActions with actionType of xferCC which are received by the system per service provider"
    ::= { bwCommPilotCallManagerSPEntry 13 }

  bwCommPilotCallMgrSPNumConferenceAdd OBJECT-TYPE
    SYNTAX      Counter32
    MAX-ACCESS  read-write
    STATUS      current
    DESCRIPTION 
        "This counter reflects the number of CAP callActions with actionType of ConfAdd which are received by the system per service provider"
    ::= { bwCommPilotCallManagerSPEntry 14 }

  bwCommPilotCallMgrSPNumCallPark OBJECT-TYPE
    SYNTAX      Counter32
    MAX-ACCESS  read-write
    STATUS      current
    DESCRIPTION 
        "Number of CallPark call actions that have been received for a user under the service provider."
    ::= { bwCommPilotCallManagerSPEntry 15 }

  bwCommPilotCallMgrSPNumGroupCallPark OBJECT-TYPE
    SYNTAX      Counter32
    MAX-ACCESS  read-write
    STATUS      current
    DESCRIPTION 
        "Number of GroupCallPark call actions that have been received for a user under the service provider."
    ::= { bwCommPilotCallManagerSPEntry 16 }

  bwCommPilotCallMgrSPNumCallParkRetrieve OBJECT-TYPE
    SYNTAX      Counter32
    MAX-ACCESS  read-write
    STATUS      current
    DESCRIPTION 
        "Number of CallParkRetrieve call actions that have been received for a user under the service provider."
    ::= { bwCommPilotCallManagerSPEntry 17 }

  bwCommPilotCallMgrNumConferenceAnswer OBJECT-TYPE
    SYNTAX      Counter32
    MAX-ACCESS  read-write
    STATUS      current
    DESCRIPTION 
        "This counter reflects the number of times a held Conference has been answered/retrieved from the CommPilot Call Mgr"
    ::= { commPilotCallManager 9 }

  bwCommPilotCallMgrNumConferenceHold OBJECT-TYPE
    SYNTAX      Counter32
    MAX-ACCESS  read-write
    STATUS      current
    DESCRIPTION 
        "This counter reflects the number of times a Conference has been held from the CommPilot Call Mgr"
    ::= { commPilotCallManager 10 }

  bwCommPilotCallMgrNumConferenceRelease OBJECT-TYPE
    SYNTAX      Counter32
    MAX-ACCESS  read-write
    STATUS      current
    DESCRIPTION 
        "This counter reflects the number of times a Conference has been released from the CommPilot Call Mgr"
    ::= { commPilotCallManager 11 }

  bwCommPilotCallManagerGroupTable OBJECT-TYPE
    SYNTAX      SEQUENCE OF BwCommPilotCallManagerGroupEntry
    MAX-ACCESS  not-accessible
    STATUS      current
    DESCRIPTION 
        "This table contains the counters for CommPilot Call Manager service measurements for service providers"
    ::= { commPilotCallManager 12 }

  bwCommPilotCallManagerGroupEntry OBJECT-TYPE
    SYNTAX      BwCommPilotCallManagerGroupEntry
    MAX-ACCESS  not-accessible
    STATUS      current
    DESCRIPTION 
        "This row contains the counters for CommPilot Call Manager service measurements for a group"
    INDEX       { bwCommPilotCallManagerGroupIndex }
    ::= { bwCommPilotCallManagerGroupTable 1 }

  BwCommPilotCallManagerGroupEntry ::= SEQUENCE {
    bwCommPilotCallManagerGroupIndex                Unsigned32,
    bwCommPilotCallManagerGroupID                   DisplayString,
    bwCommPilotCallMgrGroupNumDial                  Counter32,
    bwCommPilotCallMgrGroupNumAnswer                Counter32,
    bwCommPilotCallMgrGroupNumRelease               Counter32,
    bwCommPilotCallMgrGroupNumHold                  Counter32,
    bwCommPilotCallMgrGroupNumTransfer              Counter32,
    bwCommPilotCallMgrGroupNumConference            Counter32,
    bwCommPilotCallMgrGroupNumTransferVM            Counter32,
    bwCommPilotCallMgrGroupNumConferenceAnswer      Counter32,
    bwCommPilotCallMgrGroupNumConferenceHold        Counter32,
    bwCommPilotCallMgrGroupNumConferenceRelease     Counter32,
    bwCommPilotCallMgrGroupNumTransferCC            Counter32,
    bwCommPilotCallMgrGroupNumConferenceAdd         Counter32,
    bwCommPilotCallMgrGroupNumCallPark              Counter32,
    bwCommPilotCallMgrGroupNumGroupCallPark         Counter32,
    bwCommPilotCallMgrGroupNumCallParkRetrieve      Counter32
  }

  bwCommPilotCallManagerGroupIndex OBJECT-TYPE
    SYNTAX      Unsigned32
    MAX-ACCESS  read-only
    STATUS      current
    DESCRIPTION 
        "This integer represents the a group index in the system"
    ::= { bwCommPilotCallManagerGroupEntry 1 }

  bwCommPilotCallManagerGroupID OBJECT-TYPE
    SYNTAX      DisplayString
    MAX-ACCESS  read-only
    STATUS      current
    DESCRIPTION 
        "This string represents a group ID"
    ::= { bwCommPilotCallManagerGroupEntry 2 }

  bwCommPilotCallMgrGroupNumDial OBJECT-TYPE
    SYNTAX      Counter32
    MAX-ACCESS  read-write
    STATUS      current
    DESCRIPTION 
        "This counter reflects the number of dial requests from a CommPilot Call Mgr that results in an outgoing call by a group"
    ::= { bwCommPilotCallManagerGroupEntry 3 }

  bwCommPilotCallMgrGroupNumAnswer OBJECT-TYPE
    SYNTAX      Counter32
    MAX-ACCESS  read-write
    STATUS      current
    DESCRIPTION 
        "This counter reflects the number of times an incoming call being answered from the CommPilot Call Mgr results in that call being answered by a group"
    ::= { bwCommPilotCallManagerGroupEntry 4 }

  bwCommPilotCallMgrGroupNumRelease OBJECT-TYPE
    SYNTAX      Counter32
    MAX-ACCESS  read-write
    STATUS      current
    DESCRIPTION 
        "This counter reflects the number of times a Release request from the CommPilot Call Mgr results in the call being released by a group"
    ::= { bwCommPilotCallManagerGroupEntry 5 }

  bwCommPilotCallMgrGroupNumHold OBJECT-TYPE
    SYNTAX      Counter32
    MAX-ACCESS  read-write
    STATUS      current
    DESCRIPTION 
        "This counter reflects the number of times a Hold request from the CommPilot Call Mgr results in the call being held by a group"
    ::= { bwCommPilotCallManagerGroupEntry 6 }

  bwCommPilotCallMgrGroupNumTransfer OBJECT-TYPE
    SYNTAX      Counter32
    MAX-ACCESS  read-write
    STATUS      current
    DESCRIPTION 
        "This counter reflects the number of times a Transfer request from the CommPilot Call Mgr results in the call being transferred by a group"
    ::= { bwCommPilotCallManagerGroupEntry 7 }

  bwCommPilotCallMgrGroupNumConference OBJECT-TYPE
    SYNTAX      Counter32
    MAX-ACCESS  read-write
    STATUS      current
    DESCRIPTION 
        "This counter reflects the number of times a Conference request from the CommPilot Call Mgr results in two calls being conferenced by a group"
    ::= { bwCommPilotCallManagerGroupEntry 8 }

  bwCommPilotCallMgrGroupNumTransferVM OBJECT-TYPE
    SYNTAX      Counter32
    MAX-ACCESS  read-write
    STATUS      current
    DESCRIPTION 
        "This counter reflects the number of times a user attempts to send a call to voicemail by a group"
    ::= { bwCommPilotCallManagerGroupEntry 9 }

  bwCommPilotCallMgrGroupNumConferenceAnswer OBJECT-TYPE
    SYNTAX      Counter32
    MAX-ACCESS  read-write
    STATUS      current
    DESCRIPTION 
        "This counter reflects the number of times a held conference has been answered/retrieved from the CommPilot Call Mgr by a group"
    ::= { bwCommPilotCallManagerGroupEntry 10 }

  bwCommPilotCallMgrGroupNumConferenceHold OBJECT-TYPE
    SYNTAX      Counter32
    MAX-ACCESS  read-write
    STATUS      current
    DESCRIPTION 
        "This counter reflects the number of times a Conference has been held from the CommPilot Call Mgr by a group"
    ::= { bwCommPilotCallManagerGroupEntry 11 }

  bwCommPilotCallMgrGroupNumConferenceRelease OBJECT-TYPE
    SYNTAX      Counter32
    MAX-ACCESS  read-write
    STATUS      current
    DESCRIPTION 
        "This counter reflects the number of times a Conference has been released from the CommPilot Call Mgr by a group"
    ::= { bwCommPilotCallManagerGroupEntry 12 }

  bwCommPilotCallMgrGroupNumTransferCC OBJECT-TYPE
    SYNTAX      Counter32
    MAX-ACCESS  read-write
    STATUS      current
    DESCRIPTION 
        "This counter reflects the number of CAP callActions with actionType of xferCC which are received by the system per group"
    ::= { bwCommPilotCallManagerGroupEntry 13 }

  bwCommPilotCallMgrGroupNumConferenceAdd OBJECT-TYPE
    SYNTAX      Counter32
    MAX-ACCESS  read-write
    STATUS      current
    DESCRIPTION 
        "This counter reflects the number of CAP callActions with actionType of ConfAdd which are received by the system per group"
    ::= { bwCommPilotCallManagerGroupEntry 14 }

  bwCommPilotCallMgrGroupNumCallPark OBJECT-TYPE
    SYNTAX      Counter32
    MAX-ACCESS  read-write
    STATUS      current
    DESCRIPTION 
        "Number of CallPark call actions that have been received for a user in the group."
    ::= { bwCommPilotCallManagerGroupEntry 15 }

  bwCommPilotCallMgrGroupNumGroupCallPark OBJECT-TYPE
    SYNTAX      Counter32
    MAX-ACCESS  read-write
    STATUS      current
    DESCRIPTION 
        "Number of GroupCallPark call actions that have been received for a user in the group."
    ::= { bwCommPilotCallManagerGroupEntry 16 }

  bwCommPilotCallMgrGroupNumCallParkRetrieve OBJECT-TYPE
    SYNTAX      Counter32
    MAX-ACCESS  read-write
    STATUS      current
    DESCRIPTION 
        "Number of CallParkRetrieve call actions that have been received for a user in the group."
    ::= { bwCommPilotCallManagerGroupEntry 17 }

  bwCommPilotCallMgrNumTransferCC OBJECT-TYPE
    SYNTAX      Counter32
    MAX-ACCESS  read-write
    STATUS      current
    DESCRIPTION 
        "This counter reflects the number of CAP callActions with actionType of xferCC which are received by the system"
    ::= { commPilotCallManager 13 }

  bwCommPilotCallMgrNumConferenceAdd OBJECT-TYPE
    SYNTAX      Counter32
    MAX-ACCESS  read-write
    STATUS      current
    DESCRIPTION 
        "This counter reflects the number of CAP callActions with actionType of ConfAdd which are received by the system"
    ::= { commPilotCallManager 14 }

  bwCommPilotCallMgrNumCallPark OBJECT-TYPE
    SYNTAX      Counter32
    MAX-ACCESS  read-write
    STATUS      current
    DESCRIPTION 
        "Number of CallPark call actions that have been received."
    ::= { commPilotCallManager 15 }

  bwCommPilotCallMgrNumGroupCallPark OBJECT-TYPE
    SYNTAX      Counter32
    MAX-ACCESS  read-write
    STATUS      current
    DESCRIPTION 
        "Number of GroupCallPark call actions that have been received."
    ::= { commPilotCallManager 16 }

  bwCommPilotCallMgrNumCallParkRetrieve OBJECT-TYPE
    SYNTAX      Counter32
    MAX-ACCESS  read-write
    STATUS      current
    DESCRIPTION 
        "Number of CallParkRetrieve call actions that have been received."
    ::= { commPilotCallManager 17 }

  bwDoNotDisturbNumInvoked OBJECT-TYPE
    SYNTAX      Counter32
    MAX-ACCESS  read-write
    STATUS      current
    DESCRIPTION 
        "This counter reflects the number of times this service is triggered"
    ::= { doNotDisturb 1 }

  bwDoNotDisturbSPTable OBJECT-TYPE
    SYNTAX      SEQUENCE OF BwDoNotDisturbSPEntry
    MAX-ACCESS  not-accessible
    STATUS      current
    DESCRIPTION 
        "This table contains the counters for Do Not Disturb service measurements for service providers"
    ::= { doNotDisturb 2 }

  bwDoNotDisturbSPEntry OBJECT-TYPE
    SYNTAX      BwDoNotDisturbSPEntry
    MAX-ACCESS  not-accessible
    STATUS      current
    DESCRIPTION 
        "This row contains the counters for Do Not Disturb service measurements for a service provider"
    INDEX       { bwDoNotDisturbSPIndex }
    ::= { bwDoNotDisturbSPTable 1 }

  BwDoNotDisturbSPEntry ::= SEQUENCE {
    bwDoNotDisturbSPIndex           Unsigned32,
    bwDoNotDisturbSPID              DisplayString,
    bwDoNotDisturbSPNumInvoked      Counter32,
    bwDNDSPNumPhoneActivations      Counter32,
    bwDNDSPNumPhoneDeactivations    Counter32
  }

  bwDoNotDisturbSPIndex OBJECT-TYPE
    SYNTAX      Unsigned32
    MAX-ACCESS  read-only
    STATUS      current
    DESCRIPTION 
        "This integer represents the a service provider index in the system"
    ::= { bwDoNotDisturbSPEntry 1 }

  bwDoNotDisturbSPID OBJECT-TYPE
    SYNTAX      DisplayString
    MAX-ACCESS  read-only
    STATUS      current
    DESCRIPTION 
        "This string represents a service provider ID"
    ::= { bwDoNotDisturbSPEntry 2 }

  bwDoNotDisturbSPNumInvoked OBJECT-TYPE
    SYNTAX      Counter32
    MAX-ACCESS  read-write
    STATUS      current
    DESCRIPTION 
        "This counter reflects the number of times this service is triggered by a service provider"
    ::= { bwDoNotDisturbSPEntry 3 }

  bwDNDSPNumPhoneActivations OBJECT-TYPE
    SYNTAX      Counter32
    MAX-ACCESS  read-write
    STATUS      current
    DESCRIPTION 
        "Number of times DND has been activated via FAC for users in a given service provider"
    ::= { bwDoNotDisturbSPEntry 4 }

  bwDNDSPNumPhoneDeactivations OBJECT-TYPE
    SYNTAX      Counter32
    MAX-ACCESS  read-write
    STATUS      current
    DESCRIPTION 
        "Number of times DND has been deactivated via FAC for users in a given service provider"
    ::= { bwDoNotDisturbSPEntry 5 }

  bwDndPhoneActivations OBJECT-TYPE
    SYNTAX      Counter32
    MAX-ACCESS  read-write
    STATUS      current
    DESCRIPTION 
        "Total number of times DND has been activated via FAC"
    ::= { doNotDisturb 3 }

  bwDndPhoneDeactivations OBJECT-TYPE
    SYNTAX      Counter32
    MAX-ACCESS  read-write
    STATUS      current
    DESCRIPTION 
        "Total number of times DND has been deactivated via FAC"
    ::= { doNotDisturb 4 }

  bwDoNotDisturbGroupTable OBJECT-TYPE
    SYNTAX      SEQUENCE OF BwDoNotDisturbGroupEntry
    MAX-ACCESS  not-accessible
    STATUS      current
    DESCRIPTION 
        "This table contains the counters for Do Not Disturb service measurements for groups"
    ::= { doNotDisturb 5 }

  bwDoNotDisturbGroupEntry OBJECT-TYPE
    SYNTAX      BwDoNotDisturbGroupEntry
    MAX-ACCESS  not-accessible
    STATUS      current
    DESCRIPTION 
        "This row contains the counters for Do Not Disturb service measurements for a group"
    INDEX       { bwDoNotDisturbGroupIndex }
    ::= { bwDoNotDisturbGroupTable 1 }

  BwDoNotDisturbGroupEntry ::= SEQUENCE {
    bwDoNotDisturbGroupIndex            Unsigned32,
    bwDoNotDisturbGroupID               DisplayString,
    bwDoNotDisturbGroupNumInvoked       Counter32,
    bwDNDGroupNumPhoneActivations       Counter32,
    bwDNDGroupNumPhoneDeactivations     Counter32
  }

  bwDoNotDisturbGroupIndex OBJECT-TYPE
    SYNTAX      Unsigned32
    MAX-ACCESS  read-only
    STATUS      current
    DESCRIPTION 
        "This integer represents the a group index in the system"
    ::= { bwDoNotDisturbGroupEntry 1 }

  bwDoNotDisturbGroupID OBJECT-TYPE
    SYNTAX      DisplayString
    MAX-ACCESS  read-only
    STATUS      current
    DESCRIPTION 
        "This string represents a group ID"
    ::= { bwDoNotDisturbGroupEntry 2 }

  bwDoNotDisturbGroupNumInvoked OBJECT-TYPE
    SYNTAX      Counter32
    MAX-ACCESS  read-write
    STATUS      current
    DESCRIPTION 
        "This counter reflects the number of times this service is triggered by a group"
    ::= { bwDoNotDisturbGroupEntry 3 }

  bwDNDGroupNumPhoneActivations OBJECT-TYPE
    SYNTAX      Counter32
    MAX-ACCESS  read-write
    STATUS      current
    DESCRIPTION 
        "Number of times DND has been activated via FAC for users in a given group"
    ::= { bwDoNotDisturbGroupEntry 4 }

  bwDNDGroupNumPhoneDeactivations OBJECT-TYPE
    SYNTAX      Counter32
    MAX-ACCESS  read-write
    STATUS      current
    DESCRIPTION 
        "Number of times DND has been deactivated via FAC for users in a given group"
    ::= { bwDoNotDisturbGroupEntry 5 }

  bwFlashCallTransferNumTransfers OBJECT-TYPE
    SYNTAX      Counter32
    MAX-ACCESS  read-write
    STATUS      current
    DESCRIPTION 
        "This counter reflects the number of times the flash code and destination number
         are used to effect a transfer"
    ::= { flashCallTransfer 1 }

  bwFlashCallTransferSPTable OBJECT-TYPE
    SYNTAX      SEQUENCE OF BwFlashCallTransferSPEntry
    MAX-ACCESS  not-accessible
    STATUS      current
    DESCRIPTION 
        "This table contains the counters for Flash Call Transfer service measurements for service providers"
    ::= { flashCallTransfer 2 }

  bwFlashCallTransferSPEntry OBJECT-TYPE
    SYNTAX      BwFlashCallTransferSPEntry
    MAX-ACCESS  not-accessible
    STATUS      current
    DESCRIPTION 
        "This row contains the counters for Flash Call Transfer service measurements for a service provider"
    INDEX       { bwFlashCallTransferSPIndex }
    ::= { bwFlashCallTransferSPTable 1 }

  BwFlashCallTransferSPEntry ::= SEQUENCE {
    bwFlashCallTransferSPIndex          Unsigned32,
    bwFlashCallTransferSPID             DisplayString,
    bwFlashCallTransferSPNumTransfers   Counter32
  }

  bwFlashCallTransferSPIndex OBJECT-TYPE
    SYNTAX      Unsigned32
    MAX-ACCESS  read-only
    STATUS      current
    DESCRIPTION 
        "This integer represents the a service provider index in the system"
    ::= { bwFlashCallTransferSPEntry 1 }

  bwFlashCallTransferSPID OBJECT-TYPE
    SYNTAX      DisplayString
    MAX-ACCESS  read-only
    STATUS      current
    DESCRIPTION 
        "This string represents a service provider ID"
    ::= { bwFlashCallTransferSPEntry 2 }

  bwFlashCallTransferSPNumTransfers OBJECT-TYPE
    SYNTAX      Counter32
    MAX-ACCESS  read-write
    STATUS      current
    DESCRIPTION 
        "This counter reflects the number of times the flash code and destination number are used to effect a transfer by a service provider"
    ::= { bwFlashCallTransferSPEntry 3 }

  bwFlashCallTransferGroupTable OBJECT-TYPE
    SYNTAX      SEQUENCE OF BwFlashCallTransferGroupEntry
    MAX-ACCESS  not-accessible
    STATUS      current
    DESCRIPTION 
        "This table contains the counters for Flash Call Transfer service measurements for groups"
    ::= { flashCallTransfer 3 }

  bwFlashCallTransferGroupEntry OBJECT-TYPE
    SYNTAX      BwFlashCallTransferGroupEntry
    MAX-ACCESS  not-accessible
    STATUS      current
    DESCRIPTION 
        "This row contains the counters for Flash Call Transfer service measurements for a group"
    INDEX       { bwFlashCallTransferGroupIndex }
    ::= { bwFlashCallTransferGroupTable 1 }

  BwFlashCallTransferGroupEntry ::= SEQUENCE {
    bwFlashCallTransferGroupIndex           Unsigned32,
    bwFlashCallTransferGroupID              DisplayString,
    bwFlashCallTransferGroupNumTransfers    Counter32
  }

  bwFlashCallTransferGroupIndex OBJECT-TYPE
    SYNTAX      Unsigned32
    MAX-ACCESS  read-only
    STATUS      current
    DESCRIPTION 
        "This integer represents the a group index in the system"
    ::= { bwFlashCallTransferGroupEntry 1 }

  bwFlashCallTransferGroupID OBJECT-TYPE
    SYNTAX      DisplayString
    MAX-ACCESS  read-only
    STATUS      current
    DESCRIPTION 
        "This string represents a group ID"
    ::= { bwFlashCallTransferGroupEntry 2 }

  bwFlashCallTransferGroupNumTransfers OBJECT-TYPE
    SYNTAX      Counter32
    MAX-ACCESS  read-write
    STATUS      current
    DESCRIPTION 
        "This counter reflects the number of times the flash code and destination number are used to effect a transfer by a group"
    ::= { bwFlashCallTransferGroupEntry 3 }

  bwFlashCallWaitingNumAnswers OBJECT-TYPE
    SYNTAX      Counter32
    MAX-ACCESS  read-write
    STATUS      current
    DESCRIPTION 
        "This counter reflects the number of times the flash code results in the waiting call
         getting answered"
    ::= { flashCallWaiting 1 }

  bwFlashCallWaitingSPTable OBJECT-TYPE
    SYNTAX      SEQUENCE OF BwFlashCallWaitingSPEntry
    MAX-ACCESS  not-accessible
    STATUS      current
    DESCRIPTION 
        "This table contains the counters for Flash Call Waiting service measurements for service providers"
    ::= { flashCallWaiting 2 }

  bwFlashCallWaitingSPEntry OBJECT-TYPE
    SYNTAX      BwFlashCallWaitingSPEntry
    MAX-ACCESS  not-accessible
    STATUS      current
    DESCRIPTION 
        "This row contains the counters for Flash Call Waiting service measurements for a service provider"
    INDEX       { bwFlashCallWaitingSPIndex }
    ::= { bwFlashCallWaitingSPTable 1 }

  BwFlashCallWaitingSPEntry ::= SEQUENCE {
    bwFlashCallWaitingSPIndex       Unsigned32,
    bwFlashCallWaitingSPID          DisplayString,
    bwFlashCallWaitingSPNumAnswers  Counter32
  }

  bwFlashCallWaitingSPIndex OBJECT-TYPE
    SYNTAX      Unsigned32
    MAX-ACCESS  read-only
    STATUS      current
    DESCRIPTION 
        "This integer represents the a service provider index in the system"
    ::= { bwFlashCallWaitingSPEntry 1 }

  bwFlashCallWaitingSPID OBJECT-TYPE
    SYNTAX      DisplayString
    MAX-ACCESS  read-only
    STATUS      current
    DESCRIPTION 
        "This string represents a service provider ID"
    ::= { bwFlashCallWaitingSPEntry 2 }

  bwFlashCallWaitingSPNumAnswers OBJECT-TYPE
    SYNTAX      Counter32
    MAX-ACCESS  read-write
    STATUS      current
    DESCRIPTION 
        "This counter reflects the number of times the flash code results in the waiting call getting answered by a service provider"
    ::= { bwFlashCallWaitingSPEntry 3 }

  bwFlashCallWaitingGroupTable OBJECT-TYPE
    SYNTAX      SEQUENCE OF BwFlashCallWaitingGroupEntry
    MAX-ACCESS  not-accessible
    STATUS      current
    DESCRIPTION 
        "This table contains the counters for Flash Call Waiting service measurements for groups"
    ::= { flashCallWaiting 3 }

  bwFlashCallWaitingGroupEntry OBJECT-TYPE
    SYNTAX      BwFlashCallWaitingGroupEntry
    MAX-ACCESS  not-accessible
    STATUS      current
    DESCRIPTION 
        "This row contains the counters for Flash Call Waiting service measurements for a group"
    INDEX       { bwFlashCallWaitingGroupIndex }
    ::= { bwFlashCallWaitingGroupTable 1 }

  BwFlashCallWaitingGroupEntry ::= SEQUENCE {
    bwFlashCallWaitingGroupIndex        Unsigned32,
    bwFlashCallWaitingGroupID           DisplayString,
    bwFlashCallWaitingGroupNumAnswers   Counter32
  }

  bwFlashCallWaitingGroupIndex OBJECT-TYPE
    SYNTAX      Unsigned32
    MAX-ACCESS  read-only
    STATUS      current
    DESCRIPTION 
        "This integer represents the a group index in the system"
    ::= { bwFlashCallWaitingGroupEntry 1 }

  bwFlashCallWaitingGroupID OBJECT-TYPE
    SYNTAX      DisplayString
    MAX-ACCESS  read-only
    STATUS      current
    DESCRIPTION 
        "This string represents a group ID"
    ::= { bwFlashCallWaitingGroupEntry 2 }

  bwFlashCallWaitingGroupNumAnswers OBJECT-TYPE
    SYNTAX      Counter32
    MAX-ACCESS  read-write
    STATUS      current
    DESCRIPTION 
        "This counter reflects the number of times the flash code results in the waiting call getting answered by a group"
    ::= { bwFlashCallWaitingGroupEntry 3 }

  bwFlashConsultationNumCalls OBJECT-TYPE
    SYNTAX      Counter32
    MAX-ACCESS  read-write
    STATUS      current
    DESCRIPTION 
        "This counter reflects the number of times a counsultation is attempted using the flash
         code and destination number"
    ::= { flashConsultation 1 }

  bwFlashConsultationSPTable OBJECT-TYPE
    SYNTAX      SEQUENCE OF BwFlashConsultationSPEntry
    MAX-ACCESS  not-accessible
    STATUS      current
    DESCRIPTION 
        "This table contains the counters for Flash Consultation service measurements for service providers"
    ::= { flashConsultation 2 }

  bwFlashConsultationSPEntry OBJECT-TYPE
    SYNTAX      BwFlashConsultationSPEntry
    MAX-ACCESS  not-accessible
    STATUS      current
    DESCRIPTION 
        "This row contains the counters for Flash Consultation service measurements for a service provider"
    INDEX       { bwFlashConsultationSPIndex }
    ::= { bwFlashConsultationSPTable 1 }

  BwFlashConsultationSPEntry ::= SEQUENCE {
    bwFlashConsultationSPIndex      Unsigned32,
    bwFlashConsultationSPID         DisplayString,
    bwFlashConsultationSPNumCalls   Counter32
  }

  bwFlashConsultationSPIndex OBJECT-TYPE
    SYNTAX      Unsigned32
    MAX-ACCESS  read-only
    STATUS      current
    DESCRIPTION 
        "This integer represents the a service provider index in the system"
    ::= { bwFlashConsultationSPEntry 1 }

  bwFlashConsultationSPID OBJECT-TYPE
    SYNTAX      DisplayString
    MAX-ACCESS  read-only
    STATUS      current
    DESCRIPTION 
        "This string represents a service provider ID"
    ::= { bwFlashConsultationSPEntry 2 }

  bwFlashConsultationSPNumCalls OBJECT-TYPE
    SYNTAX      Counter32
    MAX-ACCESS  read-write
    STATUS      current
    DESCRIPTION 
        "This counter reflects the number of times a counsultation is attempted using the flash code and destination number by a service provider"
    ::= { bwFlashConsultationSPEntry 3 }

  bwFlashConsultationGroupTable OBJECT-TYPE
    SYNTAX      SEQUENCE OF BwFlashConsultationGroupEntry
    MAX-ACCESS  not-accessible
    STATUS      current
    DESCRIPTION 
        "This table contains the counters for Flash Consultation service measurements for groups"
    ::= { flashConsultation 3 }

  bwFlashConsultationGroupEntry OBJECT-TYPE
    SYNTAX      BwFlashConsultationGroupEntry
    MAX-ACCESS  not-accessible
    STATUS      current
    DESCRIPTION 
        "This row contains the counters for Flash Consultation service measurements for a group"
    INDEX       { bwFlashConsultationGroupIndex }
    ::= { bwFlashConsultationGroupTable 1 }

  BwFlashConsultationGroupEntry ::= SEQUENCE {
    bwFlashConsultationGroupIndex       Unsigned32,
    bwFlashConsultationGroupID          DisplayString,
    bwFlashConsultationGroupNumCalls    Counter32
  }

  bwFlashConsultationGroupIndex OBJECT-TYPE
    SYNTAX      Unsigned32
    MAX-ACCESS  read-only
    STATUS      current
    DESCRIPTION 
        "This integer represents the a group index in the system"
    ::= { bwFlashConsultationGroupEntry 1 }

  bwFlashConsultationGroupID OBJECT-TYPE
    SYNTAX      DisplayString
    MAX-ACCESS  read-only
    STATUS      current
    DESCRIPTION 
        "This string represents a group ID"
    ::= { bwFlashConsultationGroupEntry 2 }

  bwFlashConsultationGroupNumCalls OBJECT-TYPE
    SYNTAX      Counter32
    MAX-ACCESS  read-write
    STATUS      current
    DESCRIPTION 
        "This counter reflects the number of times a counsultation is attempted using the flash code and destination number by a group"
    ::= { bwFlashConsultationGroupEntry 3 }

  bwFlashThreeWayCallNum3WC OBJECT-TYPE
    SYNTAX      Counter32
    MAX-ACCESS  read-write
    STATUS      current
    DESCRIPTION 
        "This counter reflects the number of times the flash results in two calls being joined
         into a conference"
    ::= { flashThreeWayCall 1 }

  bwFlashThreeWayCallSPTable OBJECT-TYPE
    SYNTAX      SEQUENCE OF BwFlashThreeWayCallSPEntry
    MAX-ACCESS  not-accessible
    STATUS      current
    DESCRIPTION 
        "This table contains the counters for Flash Three-Way Call service measurements for service providers"
    ::= { flashThreeWayCall 2 }

  bwFlashThreeWayCallSPEntry OBJECT-TYPE
    SYNTAX      BwFlashThreeWayCallSPEntry
    MAX-ACCESS  not-accessible
    STATUS      current
    DESCRIPTION 
        "This row contains the counters for Flash Three-Way Call service measurements for a service provider"
    INDEX       { bwFlashThreeWayCallSPIndex }
    ::= { bwFlashThreeWayCallSPTable 1 }

  BwFlashThreeWayCallSPEntry ::= SEQUENCE {
    bwFlashThreeWayCallSPIndex      Unsigned32,
    bwFlashThreeWayCallSPID         DisplayString,
    bwFlashThreeWayCallSPNum3WC     Counter32
  }

  bwFlashThreeWayCallSPIndex OBJECT-TYPE
    SYNTAX      Unsigned32
    MAX-ACCESS  read-only
    STATUS      current
    DESCRIPTION 
        "This integer represents the a service provider index in the system"
    ::= { bwFlashThreeWayCallSPEntry 1 }

  bwFlashThreeWayCallSPID OBJECT-TYPE
    SYNTAX      DisplayString
    MAX-ACCESS  read-only
    STATUS      current
    DESCRIPTION 
        "This string represents a service provider ID"
    ::= { bwFlashThreeWayCallSPEntry 2 }

  bwFlashThreeWayCallSPNum3WC OBJECT-TYPE
    SYNTAX      Counter32
    MAX-ACCESS  read-write
    STATUS      current
    DESCRIPTION 
        "This counter reflects the number of times the flash results in two calls being joined into a conference by a service provider"
    ::= { bwFlashThreeWayCallSPEntry 3 }

  bwFlashThreeWayCallGroupTable OBJECT-TYPE
    SYNTAX      SEQUENCE OF BwFlashThreeWayCallGroupEntry
    MAX-ACCESS  not-accessible
    STATUS      current
    DESCRIPTION 
        "This table contains the counters for Flash Three-Way Call service measurements for groups"
    ::= { flashThreeWayCall 3 }

  bwFlashThreeWayCallGroupEntry OBJECT-TYPE
    SYNTAX      BwFlashThreeWayCallGroupEntry
    MAX-ACCESS  not-accessible
    STATUS      current
    DESCRIPTION 
        "This row contains the counters for Flash Three-Way Call service measurements for a group"
    INDEX       { bwFlashThreeWayCallGroupIndex }
    ::= { bwFlashThreeWayCallGroupTable 1 }

  BwFlashThreeWayCallGroupEntry ::= SEQUENCE {
    bwFlashThreeWayCallGroupIndex   Unsigned32,
    bwFlashThreeWayCallGroupID      DisplayString,
    bwFlashThreeWayCallGroupNum3WC  Counter32
  }

  bwFlashThreeWayCallGroupIndex OBJECT-TYPE
    SYNTAX      Unsigned32
    MAX-ACCESS  read-only
    STATUS      current
    DESCRIPTION 
        "This integer represents the a group index in the system"
    ::= { bwFlashThreeWayCallGroupEntry 1 }

  bwFlashThreeWayCallGroupID OBJECT-TYPE
    SYNTAX      DisplayString
    MAX-ACCESS  read-only
    STATUS      current
    DESCRIPTION 
        "This string represents a group ID"
    ::= { bwFlashThreeWayCallGroupEntry 2 }

  bwFlashThreeWayCallGroupNum3WC OBJECT-TYPE
    SYNTAX      Counter32
    MAX-ACCESS  read-write
    STATUS      current
    DESCRIPTION 
        "This counter reflects the number of times the flash results in two calls being joined into a conference by a group"
    ::= { bwFlashThreeWayCallGroupEntry 3 }

  bwHuntGroupNumAttempts OBJECT-TYPE
    SYNTAX      Counter32
    MAX-ACCESS  read-write
    STATUS      current
    DESCRIPTION 
        "This is the number of incoming calls to a Hunt Group."
    ::= { huntGroups 1 }

  bwHuntGroupNumBusy OBJECT-TYPE
    SYNTAX      Counter32
    MAX-ACCESS  read-write
    STATUS      current
    DESCRIPTION 
        "This is the number of calls to a Hunt Group where no agent is available and the originator receives Busy Treatment."
    ::= { huntGroups 2 }

  bwHuntGroupsSPTable OBJECT-TYPE
    SYNTAX      SEQUENCE OF BwHuntGroupsSPEntry
    MAX-ACCESS  not-accessible
    STATUS      current
    DESCRIPTION 
        "This table contains the counters for Hunt Group service measurements for service providers"
    ::= { huntGroups 3 }

  bwHuntGroupsSPEntry OBJECT-TYPE
    SYNTAX      BwHuntGroupsSPEntry
    MAX-ACCESS  not-accessible
    STATUS      current
    DESCRIPTION 
        "This row contains the counters for Hunt Group service measurements for a service provider"
    INDEX       { bwHuntGroupsSPIndex }
    ::= { bwHuntGroupsSPTable 1 }

  BwHuntGroupsSPEntry ::= SEQUENCE {
    bwHuntGroupsSPIndex             Unsigned32,
    bwHuntGroupsSPID                DisplayString,
    bwHuntGroupSPNumAttempts        Counter32,
    bwHuntGroupSPNumBusy            Counter32
  }

  bwHuntGroupsSPIndex OBJECT-TYPE
    SYNTAX      Unsigned32
    MAX-ACCESS  read-only
    STATUS      current
    DESCRIPTION 
        "This integer represents the a service provider index in the system"
    ::= { bwHuntGroupsSPEntry 1 }

  bwHuntGroupsSPID OBJECT-TYPE
    SYNTAX      DisplayString
    MAX-ACCESS  read-only
    STATUS      current
    DESCRIPTION 
        "This string represents a service provider ID"
    ::= { bwHuntGroupsSPEntry 2 }

  bwHuntGroupSPNumAttempts OBJECT-TYPE
    SYNTAX      Counter32
    MAX-ACCESS  read-write
    STATUS      current
    DESCRIPTION 
        "This is the number of incoming calls to a Hunt Group.  There is one instance of this counter for each service provider defined in the system."
    ::= { bwHuntGroupsSPEntry 3 }

  bwHuntGroupSPNumBusy OBJECT-TYPE
    SYNTAX      Counter32
    MAX-ACCESS  read-write
    STATUS      current
    DESCRIPTION 
        "This is the number of calls to a Hunt Group where no agent is available and the originator receives Busy Treatment.  There is one instance of this counter for each service provider defined in the system."
    ::= { bwHuntGroupsSPEntry 4 }

  bwHuntGroupsGroupTable OBJECT-TYPE
    SYNTAX      SEQUENCE OF BwHuntGroupsGroupEntry
    MAX-ACCESS  not-accessible
    STATUS      current
    DESCRIPTION 
        "This table contains the counters for Hunt Group service measurements for groups"
    ::= { huntGroups 4 }

  bwHuntGroupsGroupEntry OBJECT-TYPE
    SYNTAX      BwHuntGroupsGroupEntry
    MAX-ACCESS  not-accessible
    STATUS      current
    DESCRIPTION 
        "This row contains the counters for Hunt Group service measurements for a group"
    INDEX       { bwHuntGroupsGroupIndex }
    ::= { bwHuntGroupsGroupTable 1 }

  BwHuntGroupsGroupEntry ::= SEQUENCE {
    bwHuntGroupsGroupIndex              Unsigned32,
    bwHuntGroupsGroupID                 DisplayString,
    bwHuntGroupsGroupNumAttempts        Counter32,
    bwHuntGroupsGroupNumBusy            Counter32
  }

  bwHuntGroupsGroupIndex OBJECT-TYPE
    SYNTAX      Unsigned32
    MAX-ACCESS  read-only
    STATUS      current
    DESCRIPTION 
        "This integer represents the a Group index in the system"
    ::= { bwHuntGroupsGroupEntry 1 }

  bwHuntGroupsGroupID OBJECT-TYPE
    SYNTAX      DisplayString
    MAX-ACCESS  read-only
    STATUS      current
    DESCRIPTION 
        "This string represents a Group ID"
    ::= { bwHuntGroupsGroupEntry 2 }

  bwHuntGroupsGroupNumAttempts OBJECT-TYPE
    SYNTAX      Counter32
    MAX-ACCESS  read-write
    STATUS      current
    DESCRIPTION 
        "This is the number of incoming calls to a Hunt Group.  There is one instance of this counter for each group defined in the system."
    ::= { bwHuntGroupsGroupEntry 3 }

  bwHuntGroupsGroupNumBusy OBJECT-TYPE
    SYNTAX      Counter32
    MAX-ACCESS  read-write
    STATUS      current
    DESCRIPTION 
        "This is the number of calls to a Hunt Group where no agent is available and the originator receives Busy Treatment.  There is one instance of this counter for each group defined in the system."
    ::= { bwHuntGroupsGroupEntry 4 }

  bwICPNumInterGroupBlocks OBJECT-TYPE
    SYNTAX      Counter32
    MAX-ACCESS  read-write
    STATUS      current
    DESCRIPTION 
        "This counter reflects the number of times this service denies a direct call from outside the group"
    ::= { incomingCallingPlan 1 }

  bwIncomingCallingPlanSPTable OBJECT-TYPE
    SYNTAX      SEQUENCE OF BwIncomingCallingPlanSPEntry
    MAX-ACCESS  not-accessible
    STATUS      current
    DESCRIPTION 
        "This table contains the counters for Incoming Calling Plan service measurements for service providers"
    ::= { incomingCallingPlan 2 }

  bwIncomingCallingPlanSPEntry OBJECT-TYPE
    SYNTAX      BwIncomingCallingPlanSPEntry
    MAX-ACCESS  not-accessible
    STATUS      current
    DESCRIPTION 
        "This row contains the counters for Incoming Calling Plan service measurements for a service provider"
    INDEX       { bwIncomingCallingPlanSPIndex }
    ::= { bwIncomingCallingPlanSPTable 1 }

  BwIncomingCallingPlanSPEntry ::= SEQUENCE {
    bwIncomingCallingPlanSPIndex    Unsigned32,
    bwIncomingCallingPlanSPID       DisplayString,
    bwICPSPNumInterGroupBlocks      Counter32,
    bwICPSPNumCollectCallBlocks     Counter32,
    bwICPSPNumIntraGroupBlocks      Counter32,
    bwICPSPNumOutsideCallerBlocks   Counter32
  }

  bwIncomingCallingPlanSPIndex OBJECT-TYPE
    SYNTAX      Unsigned32
    MAX-ACCESS  read-only
    STATUS      current
    DESCRIPTION 
        "This integer represents the a service provider index in the system"
    ::= { bwIncomingCallingPlanSPEntry 1 }

  bwIncomingCallingPlanSPID OBJECT-TYPE
    SYNTAX      DisplayString
    MAX-ACCESS  read-only
    STATUS      current
    DESCRIPTION 
        "Column Description This string represents a service provider ID"
    ::= { bwIncomingCallingPlanSPEntry 2 }

  bwICPSPNumInterGroupBlocks OBJECT-TYPE
    SYNTAX      Counter32
    MAX-ACCESS  read-write
    STATUS      current
    DESCRIPTION 
        "This counter reflects the number of times this service denies a direct call from outside the group for a service provider"
    ::= { bwIncomingCallingPlanSPEntry 3 }

  bwICPSPNumCollectCallBlocks OBJECT-TYPE
    SYNTAX      Counter32
    MAX-ACCESS  read-write
    STATUS      current
    DESCRIPTION 
        "This counter is incremented whenever the service denies a collect call for a service provider"
    ::= { bwIncomingCallingPlanSPEntry 4 }

  bwICPSPNumIntraGroupBlocks OBJECT-TYPE
    SYNTAX      Counter32
    MAX-ACCESS  read-write
    STATUS      current
    DESCRIPTION 
        "This counter is incremented whenever the service denies an intra-group call for a service provider"
    ::= { bwIncomingCallingPlanSPEntry 5 }

  bwICPSPNumOutsideCallerBlocks OBJECT-TYPE
    SYNTAX      Counter32
    MAX-ACCESS  read-write
    STATUS      current
    DESCRIPTION 
        "This counter reflects the number of times this service denies a call forwarded/transferred by a group member where the other party is outside the group for a service provider"
    ::= { bwIncomingCallingPlanSPEntry 6 }

  bwIncomingCallingPlanGroupTable OBJECT-TYPE
    SYNTAX      SEQUENCE OF BwIncomingCallingPlanGroupEntry
    MAX-ACCESS  not-accessible
    STATUS      current
    DESCRIPTION 
        "This table contains the counters for Incoming Calling Plan service measurements for groups"
    ::= { incomingCallingPlan 3 }

  bwIncomingCallingPlanGroupEntry OBJECT-TYPE
    SYNTAX      BwIncomingCallingPlanGroupEntry
    MAX-ACCESS  not-accessible
    STATUS      current
    DESCRIPTION 
        "This row contains the counters for Incoming Calling Plan service measurements for a group"
    INDEX       { bwIncomingCallingPlanGroupIndex }
    ::= { bwIncomingCallingPlanGroupTable 1 }

  BwIncomingCallingPlanGroupEntry ::= SEQUENCE {
    bwIncomingCallingPlanGroupIndex     Unsigned32,
    bwIncomingCallingPlanGroupID        DisplayString,
    bwICPGroupNumInterGroupBlocks       Counter32,
    bwICPGroupNumCollectCallBlocks      Counter32,
    bwICPGroupNumIntraGroupBlocks       Counter32,
    bwICPGroupNumOutsideCallerBlocks    Counter32
  }

  bwIncomingCallingPlanGroupIndex OBJECT-TYPE
    SYNTAX      Unsigned32
    MAX-ACCESS  read-only
    STATUS      current
    DESCRIPTION 
        "This integer represents the a group index in the system"
    ::= { bwIncomingCallingPlanGroupEntry 1 }

  bwIncomingCallingPlanGroupID OBJECT-TYPE
    SYNTAX      DisplayString
    MAX-ACCESS  read-only
    STATUS      current
    DESCRIPTION 
        "Column Description This string represents a group ID"
    ::= { bwIncomingCallingPlanGroupEntry 2 }

  bwICPGroupNumInterGroupBlocks OBJECT-TYPE
    SYNTAX      Counter32
    MAX-ACCESS  read-write
    STATUS      current
    DESCRIPTION 
        "This counter reflects the number of times this service denies a direct call from outside the group for a group"
    ::= { bwIncomingCallingPlanGroupEntry 3 }

  bwICPGroupNumCollectCallBlocks OBJECT-TYPE
    SYNTAX      Counter32
    MAX-ACCESS  read-write
    STATUS      current
    DESCRIPTION 
        "This counter is incremented whenever the service denies a collect call for a group"
    ::= { bwIncomingCallingPlanGroupEntry 4 }

  bwICPGroupNumIntraGroupBlocks OBJECT-TYPE
    SYNTAX      Counter32
    MAX-ACCESS  read-write
    STATUS      current
    DESCRIPTION 
        "This counter is incremented whenever the service denies an intra-group call for a group"
    ::= { bwIncomingCallingPlanGroupEntry 5 }

  bwICPGroupNumOutsideCallerBlocks OBJECT-TYPE
    SYNTAX      Counter32
    MAX-ACCESS  read-write
    STATUS      current
    DESCRIPTION 
        "This counter reflects the number of times this service denies a call forwarded/transferred by a group member where the other party is outside the group for a group"
    ::= { bwIncomingCallingPlanGroupEntry 6 }

  bwICPNumCollectCallBlocks OBJECT-TYPE
    SYNTAX      Counter32
    MAX-ACCESS  read-write
    STATUS      current
    DESCRIPTION 
        "This counter is incremented whenever the service denies a collect call"
    ::= { incomingCallingPlan 4 }

  bwICPNumIntraGroupBlocks OBJECT-TYPE
    SYNTAX      Counter32
    MAX-ACCESS  read-write
    STATUS      current
    DESCRIPTION 
        "This counter is incremented whenever the service denies an intra-group call"
    ::= { incomingCallingPlan 5 }

  bwICPNumOutsideCallerBlocks OBJECT-TYPE
    SYNTAX      Counter32
    MAX-ACCESS  read-write
    STATUS      current
    DESCRIPTION 
        "This counter reflects the number of times this service denies a call forwarded/transferred by a group member where the other party is outside the group"
    ::= { incomingCallingPlan 6 }

  bwIPPhoneNumForwards OBJECT-TYPE
    SYNTAX      Counter32
    MAX-ACCESS  read-write
    STATUS      current
    DESCRIPTION 
        "This counter reflects the number of times this service redirects a call on a request from
         an IP Phone"
    ::= { ipPhone 1 }

  bwIPPhoneSPTable OBJECT-TYPE
    SYNTAX      SEQUENCE OF BwIPPhoneSPEntry
    MAX-ACCESS  not-accessible
    STATUS      current
    DESCRIPTION 
        "This table contains the counters for IP Phone service measurements for service providers"
    ::= { ipPhone 2 }

  bwIPPhoneSPEntry OBJECT-TYPE
    SYNTAX      BwIPPhoneSPEntry
    MAX-ACCESS  not-accessible
    STATUS      current
    DESCRIPTION 
        "This row contains the counters for IP Phone service measurements for a service provider"
    INDEX       { bwIPPhoneSPIndex }
    ::= { bwIPPhoneSPTable 1 }

  BwIPPhoneSPEntry ::= SEQUENCE {
    bwIPPhoneSPIndex        Unsigned32,
    bwIPPhoneSPID           DisplayString,
    bwIPPhoneSPNumForwards  Counter32
  }

  bwIPPhoneSPIndex OBJECT-TYPE
    SYNTAX      Unsigned32
    MAX-ACCESS  read-only
    STATUS      current
    DESCRIPTION 
        "This integer represents the a service provider index in the system"
    ::= { bwIPPhoneSPEntry 1 }

  bwIPPhoneSPID OBJECT-TYPE
    SYNTAX      DisplayString
    MAX-ACCESS  read-only
    STATUS      current
    DESCRIPTION 
        "This string represents a service provider ID"
    ::= { bwIPPhoneSPEntry 2 }

  bwIPPhoneSPNumForwards OBJECT-TYPE
    SYNTAX      Counter32
    MAX-ACCESS  read-write
    STATUS      current
    DESCRIPTION 
        "This counter reflects the number of times this service redirects a call on a request from an IP Phone by a service provider"
    ::= { bwIPPhoneSPEntry 3 }

  bwIPPhoneGroupTable OBJECT-TYPE
    SYNTAX      SEQUENCE OF BwIPPhoneGroupEntry
    MAX-ACCESS  not-accessible
    STATUS      current
    DESCRIPTION 
        "This table contains the counters for IP Phone service measurements for groups"
    ::= { ipPhone 3 }

  bwIPPhoneGroupEntry OBJECT-TYPE
    SYNTAX      BwIPPhoneGroupEntry
    MAX-ACCESS  not-accessible
    STATUS      current
    DESCRIPTION 
        "This row contains the counters for IP Phone service measurements for a group"
    INDEX       { bwIPPhoneGroupIndex }
    ::= { bwIPPhoneGroupTable 1 }

  BwIPPhoneGroupEntry ::= SEQUENCE {
    bwIPPhoneGroupIndex         Unsigned32,
    bwIPPhoneGroupID            DisplayString,
    bwIPPhoneGroupNumForwards   Counter32
  }

  bwIPPhoneGroupIndex OBJECT-TYPE
    SYNTAX      Unsigned32
    MAX-ACCESS  read-only
    STATUS      current
    DESCRIPTION 
        "This integer represents the a group index in the system"
    ::= { bwIPPhoneGroupEntry 1 }

  bwIPPhoneGroupID OBJECT-TYPE
    SYNTAX      DisplayString
    MAX-ACCESS  read-only
    STATUS      current
    DESCRIPTION 
        "This string represents a group ID"
    ::= { bwIPPhoneGroupEntry 2 }

  bwIPPhoneGroupNumForwards OBJECT-TYPE
    SYNTAX      Counter32
    MAX-ACCESS  read-write
    STATUS      current
    DESCRIPTION 
        "This counter reflects the number of times this service redirects a call on a request from an IP Phone by a group"
    ::= { bwIPPhoneGroupEntry 3 }

  bwLNRNumRedials OBJECT-TYPE
    SYNTAX      Counter32
    MAX-ACCESS  read-write
    STATUS      current
    DESCRIPTION 
        "This counter reflects the number of times the flash code results in this service
         attempting to dial the last number called"
    ::= { lastNumberRedial 1 }

  bwLastNumberRedialSPTable OBJECT-TYPE
    SYNTAX      SEQUENCE OF BwLastNumberRedialSPEntry
    MAX-ACCESS  not-accessible
    STATUS      current
    DESCRIPTION 
        "This table contains the counters for Last Number Redial service measurements for service providers"
    ::= { lastNumberRedial 2 }

  bwLastNumberRedialSPEntry OBJECT-TYPE
    SYNTAX      BwLastNumberRedialSPEntry
    MAX-ACCESS  not-accessible
    STATUS      current
    DESCRIPTION 
        "This row contains the counters for Last Number Redial service measurements for a service provider"
    INDEX       { bwLastNumberRedialSPIndex }
    ::= { bwLastNumberRedialSPTable 1 }

  BwLastNumberRedialSPEntry ::= SEQUENCE {
    bwLastNumberRedialSPIndex   Unsigned32,
    bwLastNumberRedialSPID      DisplayString,
    bwLNRSPNumRedials           Counter32
  }

  bwLastNumberRedialSPIndex OBJECT-TYPE
    SYNTAX      Unsigned32
    MAX-ACCESS  read-only
    STATUS      current
    DESCRIPTION 
        "This integer represents the a service provider index in the system"
    ::= { bwLastNumberRedialSPEntry 1 }

  bwLastNumberRedialSPID OBJECT-TYPE
    SYNTAX      DisplayString
    MAX-ACCESS  read-only
    STATUS      current
    DESCRIPTION 
        "This string represents a service provider ID"
    ::= { bwLastNumberRedialSPEntry 2 }

  bwLNRSPNumRedials OBJECT-TYPE
    SYNTAX      Counter32
    MAX-ACCESS  read-write
    STATUS      current
    DESCRIPTION 
        "This counter reflects the number of times the flash code results in this service attempting to dial the last number called by a service provider"
    ::= { bwLastNumberRedialSPEntry 3 }

  bwLastNumberRedialGroupTable OBJECT-TYPE
    SYNTAX      SEQUENCE OF BwLastNumberRedialGroupEntry
    MAX-ACCESS  not-accessible
    STATUS      current
    DESCRIPTION 
        "This table contains the counters for Last Number Redial service measurements for groups"
    ::= { lastNumberRedial 3 }

  bwLastNumberRedialGroupEntry OBJECT-TYPE
    SYNTAX      BwLastNumberRedialGroupEntry
    MAX-ACCESS  not-accessible
    STATUS      current
    DESCRIPTION 
        "This row contains the counters for Last Number Redial service measurements for a group"
    INDEX       { bwLastNumberRedialGroupIndex }
    ::= { bwLastNumberRedialGroupTable 1 }

  BwLastNumberRedialGroupEntry ::= SEQUENCE {
    bwLastNumberRedialGroupIndex    Unsigned32,
    bwLastNumberRedialGroupID       DisplayString,
    bwLNRGroupNumRedials            Counter32
  }

  bwLastNumberRedialGroupIndex OBJECT-TYPE
    SYNTAX      Unsigned32
    MAX-ACCESS  read-only
    STATUS      current
    DESCRIPTION 
        "This integer represents the a group index in the system"
    ::= { bwLastNumberRedialGroupEntry 1 }

  bwLastNumberRedialGroupID OBJECT-TYPE
    SYNTAX      DisplayString
    MAX-ACCESS  read-only
    STATUS      current
    DESCRIPTION 
        "This string represents a group ID"
    ::= { bwLastNumberRedialGroupEntry 2 }

  bwLNRGroupNumRedials OBJECT-TYPE
    SYNTAX      Counter32
    MAX-ACCESS  read-write
    STATUS      current
    DESCRIPTION 
        "This counter reflects the number of times the flash code results in this service attempting to dial the last number called by a group"
    ::= { bwLastNumberRedialGroupEntry 3 }

  bwOCPNumGroupCallsBlocked OBJECT-TYPE
    SYNTAX      Counter32
    MAX-ACCESS  read-write
    STATUS      current
    DESCRIPTION 
        "This counter reflects the number of times an intra-group call is blocked"
    ::= { outgoingCallingPlan 1 }

  bwOCPNumLocalCallsBlocked OBJECT-TYPE
    SYNTAX      Counter32
    MAX-ACCESS  read-write
    STATUS      current
    DESCRIPTION 
        "This counter reflects the number of times a local call is blocked"
    ::= { outgoingCallingPlan 2 }

  bwOCPNumTollFreeCallsBlocked OBJECT-TYPE
    SYNTAX      Counter32
    MAX-ACCESS  read-write
    STATUS      current
    DESCRIPTION 
        "This counter reflects the number of times a toll free call is blocked"
    ::= { outgoingCallingPlan 3 }

  bwOCPNumTollCallsBlocked OBJECT-TYPE
    SYNTAX      Counter32
    MAX-ACCESS  read-write
    STATUS      current
    DESCRIPTION 
        "This counter reflects the number of times a toll call is blocked"
    ::= { outgoingCallingPlan 4 }

  bwOCPNumIntlCallsBlocked OBJECT-TYPE
    SYNTAX      Counter32
    MAX-ACCESS  read-write
    STATUS      current
    DESCRIPTION 
        "This counter reflects the number of times an international call is blocked"
    ::= { outgoingCallingPlan 5 }

  bwOCPNumOperatorAssistedCallsBlocked OBJECT-TYPE
    SYNTAX      Counter32
    MAX-ACCESS  read-write
    STATUS      current
    DESCRIPTION 
        "This counter reflects the number of times an operator assisted call is blocked"
    ::= { outgoingCallingPlan 6 }

  bwOCPNumChargeableDirAssistCallsBlocked OBJECT-TYPE
    SYNTAX      Counter32
    MAX-ACCESS  read-write
    STATUS      current
    DESCRIPTION 
        "This counter reflects the number of times a chargeable directory assistance call is
         blocked"
    ::= { outgoingCallingPlan 7 }

  bwOCPNumSpecialServices1CallsBlocked OBJECT-TYPE
    SYNTAX      Counter32
    MAX-ACCESS  read-write
    STATUS      current
    DESCRIPTION 
        "This counter reflects the number of times a special services call is blocked"
    ::= { outgoingCallingPlan 8 }

  bwOCPNumSpecialServices2CallsBlocked OBJECT-TYPE
    SYNTAX      Counter32
    MAX-ACCESS  read-write
    STATUS      current
    DESCRIPTION 
        "This counter reflects the number of times a special services call is blocked"
    ::= { outgoingCallingPlan 9 }

  bwOCPNumPremiumServices1CallsBlocked OBJECT-TYPE
    SYNTAX      Counter32
    MAX-ACCESS  read-write
    STATUS      current
    DESCRIPTION 
        "This counter reflects the number of times a premium services call is blocked"
    ::= { outgoingCallingPlan 10 }

  bwOCPNumPremiumServices2CallsBlocked OBJECT-TYPE
    SYNTAX      Counter32
    MAX-ACCESS  read-write
    STATUS      current
    DESCRIPTION 
        "This counter reflects the number of times a premium services call is blocked"
    ::= { outgoingCallingPlan 11 }

  bwOCPNumCasualCallsBlocked OBJECT-TYPE
    SYNTAX      Counter32
    MAX-ACCESS  read-write
    STATUS      current
    DESCRIPTION 
        "This counter reflects the number of times a casual equal access call is blocked"
    ::= { outgoingCallingPlan 12 }

  bwOCPNumURLDialingCallsBlocked OBJECT-TYPE
    SYNTAX      Counter32
    MAX-ACCESS  read-write
    STATUS      current
    DESCRIPTION 
        "This counter reflects the number of times a URL dialed call is blocked"
    ::= { outgoingCallingPlan 13 }

  bwOCPNumUnknownCallsBlocked OBJECT-TYPE
    SYNTAX      Counter32
    MAX-ACCESS  read-write
    STATUS      current
    DESCRIPTION 
        "This counter reflects the number of times an unknown call type is blocked"
    ::= { outgoingCallingPlan 14 }

  bwOutgoingCallingPlanSPTable OBJECT-TYPE
    SYNTAX      SEQUENCE OF BwOutgoingCallingPlanSPEntry
    MAX-ACCESS  not-accessible
    STATUS      current
    DESCRIPTION 
        "This table contains the counters for Outgoing Calling Plan service measurements for service providers"
    ::= { outgoingCallingPlan 15 }

  bwOutgoingCallingPlanSPEntry OBJECT-TYPE
    SYNTAX      BwOutgoingCallingPlanSPEntry
    MAX-ACCESS  not-accessible
    STATUS      current
    DESCRIPTION 
        "This row contains the counters for Outgoing Calling Plan service measurements for a service provider"
    INDEX       { bwOutgoingCallingPlanSPIndex }
    ::= { bwOutgoingCallingPlanSPTable 1 }

  BwOutgoingCallingPlanSPEntry ::= SEQUENCE {
    bwOutgoingCallingPlanSPIndex                Unsigned32,
    bwOutgoingCallingPlanSPID                   DisplayString,
    bwOCPSPNumGroupCallsBlocked                 Counter32,
    bwOCPSPNumLocalCallsBlocked                 Counter32,
    bwOCPSPNumTollFreeCallsBlocked              Counter32,
    bwOCPSPNumTollCallsBlocked                  Counter32,
    bwOCPSPNumIntlCallsBlocked                  Counter32,
    bwOCPSPNumOperatorAssistedCallsBlocked      Counter32,
    bwOCPSPNumChargeableDirAssistCallsBlocked   Counter32,
    bwOCPSPNumSpecialServices1CallsBlocked      Counter32,
    bwOCPSPNumSpecialServices2CallsBlocked      Counter32,
    bwOCPSPNumPremiumServices1CallsBlocked      Counter32,
    bwOCPSPNumPremiumServices2CallsBlocked      Counter32,
    bwOCPSPNumCasualCallsBlocked                Counter32,
    bwOCPSPNumURLDialingCallsBlocked            Counter32,
    bwOCPSPNumUnknownCallsBlocked               Counter32,
    bwOCPSPNumSuccessfulAuthorizations          Counter32,
    bwOCPSPNumUnsuccessfulAuthorizations        Counter32,
    bwOCPSPNumTransfers                         Counter32,
    bwOCPSACSPNumSuccessfulLock                 Counter32,
    bwOCPSACSPNumSuccessfulUnlock               Counter32,
    bwOCPSACSPNumUnsuccessfulLock               Counter32,
    bwOCPSACSPNumUnsuccessfulUnlock             Counter32,
    bwOCPSACSPNumUnsuccessfulCodeUsage          Counter32,
    bwOCPSPNumOutsideGroupTransferBlocks        Counter32
  }

  bwOutgoingCallingPlanSPIndex OBJECT-TYPE
    SYNTAX      Unsigned32
    MAX-ACCESS  read-only
    STATUS      current
    DESCRIPTION 
        "This integer represents the a service provider index in the system"
    ::= { bwOutgoingCallingPlanSPEntry 1 }

  bwOutgoingCallingPlanSPID OBJECT-TYPE
    SYNTAX      DisplayString
    MAX-ACCESS  read-only
    STATUS      current
    DESCRIPTION 
        "This string represents a service provider ID"
    ::= { bwOutgoingCallingPlanSPEntry 2 }

  bwOCPSPNumGroupCallsBlocked OBJECT-TYPE
    SYNTAX      Counter32
    MAX-ACCESS  read-write
    STATUS      current
    DESCRIPTION 
        "This counter reflects the number of times an intra-group call is blocked by a service provider"
    ::= { bwOutgoingCallingPlanSPEntry 3 }

  bwOCPSPNumLocalCallsBlocked OBJECT-TYPE
    SYNTAX      Counter32
    MAX-ACCESS  read-write
    STATUS      current
    DESCRIPTION 
        "This counter reflects the number of times a local call is blocked by a service provider"
    ::= { bwOutgoingCallingPlanSPEntry 4 }

  bwOCPSPNumTollFreeCallsBlocked OBJECT-TYPE
    SYNTAX      Counter32
    MAX-ACCESS  read-write
    STATUS      current
    DESCRIPTION 
        "This counter reflects the number of times a toll free call is blocked by a service provider"
    ::= { bwOutgoingCallingPlanSPEntry 5 }

  bwOCPSPNumTollCallsBlocked OBJECT-TYPE
    SYNTAX      Counter32
    MAX-ACCESS  read-write
    STATUS      current
    DESCRIPTION 
        "This counter reflects the number of times a toll call is blocked by a service provider"
    ::= { bwOutgoingCallingPlanSPEntry 6 }

  bwOCPSPNumIntlCallsBlocked OBJECT-TYPE
    SYNTAX      Counter32
    MAX-ACCESS  read-write
    STATUS      current
    DESCRIPTION 
        "This counter reflects the number of times an international call is blocked by a service provider"
    ::= { bwOutgoingCallingPlanSPEntry 7 }

  bwOCPSPNumOperatorAssistedCallsBlocked OBJECT-TYPE
    SYNTAX      Counter32
    MAX-ACCESS  read-write
    STATUS      current
    DESCRIPTION 
        "This counter reflects the number of times an operator assisted call is blocked by a service provider"
    ::= { bwOutgoingCallingPlanSPEntry 8 }

  bwOCPSPNumChargeableDirAssistCallsBlocked OBJECT-TYPE
    SYNTAX      Counter32
    MAX-ACCESS  read-write
    STATUS      current
    DESCRIPTION 
        "This counter reflects the number of times a chargeable directory assistance call is blocked by a service provider"
    ::= { bwOutgoingCallingPlanSPEntry 9 }

  bwOCPSPNumSpecialServices1CallsBlocked OBJECT-TYPE
    SYNTAX      Counter32
    MAX-ACCESS  read-write
    STATUS      current
    DESCRIPTION 
        "This counter reflects the number of times a special services call is blocked by a service provider"
    ::= { bwOutgoingCallingPlanSPEntry 10 }

  bwOCPSPNumSpecialServices2CallsBlocked OBJECT-TYPE
    SYNTAX      Counter32
    MAX-ACCESS  read-write
    STATUS      current
    DESCRIPTION 
        "This counter reflects the number of times a special services call is blocked by a service provider"
    ::= { bwOutgoingCallingPlanSPEntry 11 }

  bwOCPSPNumPremiumServices1CallsBlocked OBJECT-TYPE
    SYNTAX      Counter32
    MAX-ACCESS  read-write
    STATUS      current
    DESCRIPTION 
        "This counter reflects the number of times a premium services call is blocked by a service provider"
    ::= { bwOutgoingCallingPlanSPEntry 12 }

  bwOCPSPNumPremiumServices2CallsBlocked OBJECT-TYPE
    SYNTAX      Counter32
    MAX-ACCESS  read-write
    STATUS      current
    DESCRIPTION 
        "This counter reflects the number of times a premium services call is blocked by a service provider"
    ::= { bwOutgoingCallingPlanSPEntry 13 }

  bwOCPSPNumCasualCallsBlocked OBJECT-TYPE
    SYNTAX      Counter32
    MAX-ACCESS  read-write
    STATUS      current
    DESCRIPTION 
        "This counter reflects the number of times a casual equal access call is blocked by a service provider"
    ::= { bwOutgoingCallingPlanSPEntry 14 }

  bwOCPSPNumURLDialingCallsBlocked OBJECT-TYPE
    SYNTAX      Counter32
    MAX-ACCESS  read-write
    STATUS      current
    DESCRIPTION 
        "This counter reflects the number of times a URL dialed call is blocked by a service provider"
    ::= { bwOutgoingCallingPlanSPEntry 15 }

  bwOCPSPNumUnknownCallsBlocked OBJECT-TYPE
    SYNTAX      Counter32
    MAX-ACCESS  read-write
    STATUS      current
    DESCRIPTION 
        "This counter reflects the number of times an unknown call type is blocked by a service provider"
    ::= { bwOutgoingCallingPlanSPEntry 16 }

  bwOCPSPNumSuccessfulAuthorizations OBJECT-TYPE
    SYNTAX      Counter32
    MAX-ACCESS  read-write
    STATUS      current
    DESCRIPTION 
        "This counter reflects the number of times a caller enters a valid authorization code in order to establish a call for a given service provider."
    ::= { bwOutgoingCallingPlanSPEntry 17 }

  bwOCPSPNumUnsuccessfulAuthorizations OBJECT-TYPE
    SYNTAX      Counter32
    MAX-ACCESS  read-write
    STATUS      current
    DESCRIPTION 
        "This counter reflects the number of times a caller enters an invalid authorization code in order to establish a call for a given service provider."
    ::= { bwOutgoingCallingPlanSPEntry 18 }

  bwOCPSPNumTransfers OBJECT-TYPE
    SYNTAX      Counter32
    MAX-ACCESS  read-write
    STATUS      current
    DESCRIPTION 
        "This counter reflects the number of times OCP transfers the caller to a number where the caller's request will be handled for a given service provider."
    ::= { bwOutgoingCallingPlanSPEntry 19 }

  bwOCPSACSPNumSuccessfulLock OBJECT-TYPE
    SYNTAX      Counter32
    MAX-ACCESS  read-write
    STATUS      current
    DESCRIPTION 
        "This counter reflects the number of times the SAC lock feature access code is used successfully in order to lock calls for a given service provider"
    ::= { bwOutgoingCallingPlanSPEntry 20 }

  bwOCPSACSPNumSuccessfulUnlock OBJECT-TYPE
    SYNTAX      Counter32
    MAX-ACCESS  read-write
    STATUS      current
    DESCRIPTION 
        "This counter reflects the number of times the SAC unlock feature access code is used successfully in order to unlock calls for a given service provider"
    ::= { bwOutgoingCallingPlanSPEntry 21 }

  bwOCPSACSPNumUnsuccessfulLock OBJECT-TYPE
    SYNTAX      Counter32
    MAX-ACCESS  read-write
    STATUS      current
    DESCRIPTION 
        "This counter reflects the number of times the SAC lock feature access code is used unsuccessfully for a given service provider"
    ::= { bwOutgoingCallingPlanSPEntry 22 }

  bwOCPSACSPNumUnsuccessfulUnlock OBJECT-TYPE
    SYNTAX      Counter32
    MAX-ACCESS  read-write
    STATUS      current
    DESCRIPTION 
        "This counter reflects the number of times the SAC unlock feature access code is used unsuccessfully for a given service provider"
    ::= { bwOutgoingCallingPlanSPEntry 23 }

  bwOCPSACSPNumUnsuccessfulCodeUsage OBJECT-TYPE
    SYNTAX      Counter32
    MAX-ACCESS  read-write
    STATUS      current
    DESCRIPTION 
        "This counter reflects the number of times a stored SAC code is erased from the database because it fails to pass EOCP screening following a change in the EOCP plan that makes the stored SAC code obsolete for a given service provider"
    ::= { bwOutgoingCallingPlanSPEntry 24 }

  bwOCPSPNumOutsideGroupTransferBlocks OBJECT-TYPE
    SYNTAX      Counter32
    MAX-ACCESS  read-write
    STATUS      current
    DESCRIPTION 
        "This counter reflects the number of times this service denies call forwarding or transfer to a party outside of the group for a given service provider."
    ::= { bwOutgoingCallingPlanSPEntry 25 }

  bwOutgoingCallingPlanGroupTable OBJECT-TYPE
    SYNTAX      SEQUENCE OF BwOutgoingCallingPlanGroupEntry
    MAX-ACCESS  not-accessible
    STATUS      current
    DESCRIPTION 
        "This table contains the counters for Outgoing Calling Plan service measurements for groups"
    ::= { outgoingCallingPlan 16 }

  bwOutgoingCallingPlanGroupEntry OBJECT-TYPE
    SYNTAX      BwOutgoingCallingPlanGroupEntry
    MAX-ACCESS  not-accessible
    STATUS      current
    DESCRIPTION 
        "This row contains the counters for Outgoing Calling Plan service measurements for a group"
    INDEX       { bwOutgoingCallingPlanGroupIndex }
    ::= { bwOutgoingCallingPlanGroupTable 1 }

  BwOutgoingCallingPlanGroupEntry ::= SEQUENCE {
    bwOutgoingCallingPlanGroupIndex                 Unsigned32,
    bwOutgoingCallingPlanGroupID                    DisplayString,
    bwOCPGroupNumGroupCallsBlocked                  Counter32,
    bwOCPGroupNumLocalCallsBlocked                  Counter32,
    bwOCPGroupNumTollFreeCallsBlocked               Counter32,
    bwOCPGroupNumTollCallsBlocked                   Counter32,
    bwOCPGroupNumIntlCallsBlocked                   Counter32,
    bwOCPGroupNumOperatorAssistedCallsBlocked       Counter32,
    bwOCPGroupNumChargeableDirAssistCallsBlocked    Counter32,
    bwOCPGroupNumSpecialServices1CallsBlocked       Counter32,
    bwOCPGroupNumSpecialServices2CallsBlocked       Counter32,
    bwOCPGroupNumPremiumServices1CallsBlocked       Counter32,
    bwOCPGroupNumPremiumServices2CallsBlocked       Counter32,
    bwOCPGroupNumCasualCallsBlocked                 Counter32,
    bwOCPGroupNumURLDialingCallsBlocked             Counter32,
    bwOCPGroupNumUnknownCallsBlocked                Counter32,
    bwOCPGroupNumSuccessfulAuthorizations           Counter32,
    bwOCPGroupNumUnsuccessfulAuthorizations         Counter32,
    bwOCPGroupNumTransfers                          Counter32,
    bwOCPSACGroupNumSuccessfulLock                  Counter32,
    bwOCPSACGroupNumSuccessfulUnlock                Counter32,
    bwOCPSACGroupNumUnsuccessfulLock                Counter32,
    bwOCPSACGroupNumUnsuccessfulUnlock              Counter32,
    bwOCPSACGroupNumUnsuccessfulCodeUsage           Counter32,
    bwOCPGroupNumOutsideGroupTransferBlocks         Counter32
  }

  bwOutgoingCallingPlanGroupIndex OBJECT-TYPE
    SYNTAX      Unsigned32
    MAX-ACCESS  read-only
    STATUS      current
    DESCRIPTION 
        "This integer represents the a group index in the system"
    ::= { bwOutgoingCallingPlanGroupEntry 1 }

  bwOutgoingCallingPlanGroupID OBJECT-TYPE
    SYNTAX      DisplayString
    MAX-ACCESS  read-only
    STATUS      current
    DESCRIPTION 
        "This string represents a group ID"
    ::= { bwOutgoingCallingPlanGroupEntry 2 }

  bwOCPGroupNumGroupCallsBlocked OBJECT-TYPE
    SYNTAX      Counter32
    MAX-ACCESS  read-write
    STATUS      current
    DESCRIPTION 
        "This counter reflects the number of times an intra-group call is blocked by a group"
    ::= { bwOutgoingCallingPlanGroupEntry 3 }

  bwOCPGroupNumLocalCallsBlocked OBJECT-TYPE
    SYNTAX      Counter32
    MAX-ACCESS  read-write
    STATUS      current
    DESCRIPTION 
        "This counter reflects the number of times a local call is blocked by a group"
    ::= { bwOutgoingCallingPlanGroupEntry 4 }

  bwOCPGroupNumTollFreeCallsBlocked OBJECT-TYPE
    SYNTAX      Counter32
    MAX-ACCESS  read-write
    STATUS      current
    DESCRIPTION 
        "This counter reflects the number of times a toll free call is blocked by a group"
    ::= { bwOutgoingCallingPlanGroupEntry 5 }

  bwOCPGroupNumTollCallsBlocked OBJECT-TYPE
    SYNTAX      Counter32
    MAX-ACCESS  read-write
    STATUS      current
    DESCRIPTION 
        "This counter reflects the number of times a toll call is blocked by a group"
    ::= { bwOutgoingCallingPlanGroupEntry 6 }

  bwOCPGroupNumIntlCallsBlocked OBJECT-TYPE
    SYNTAX      Counter32
    MAX-ACCESS  read-write
    STATUS      current
    DESCRIPTION 
        "This counter reflects the number of times an international call is blocked by a group"
    ::= { bwOutgoingCallingPlanGroupEntry 7 }

  bwOCPGroupNumOperatorAssistedCallsBlocked OBJECT-TYPE
    SYNTAX      Counter32
    MAX-ACCESS  read-write
    STATUS      current
    DESCRIPTION 
        "This counter reflects the number of times an operator assisted call is blocked by a group"
    ::= { bwOutgoingCallingPlanGroupEntry 8 }

  bwOCPGroupNumChargeableDirAssistCallsBlocked OBJECT-TYPE
    SYNTAX      Counter32
    MAX-ACCESS  read-write
    STATUS      current
    DESCRIPTION 
        "This counter reflects the number of times a chargeable directory assistance call is blocked by a group"
    ::= { bwOutgoingCallingPlanGroupEntry 9 }

  bwOCPGroupNumSpecialServices1CallsBlocked OBJECT-TYPE
    SYNTAX      Counter32
    MAX-ACCESS  read-write
    STATUS      current
    DESCRIPTION 
        "This counter reflects the number of times a special services call is blocked by a group"
    ::= { bwOutgoingCallingPlanGroupEntry 10 }

  bwOCPGroupNumSpecialServices2CallsBlocked OBJECT-TYPE
    SYNTAX      Counter32
    MAX-ACCESS  read-write
    STATUS      current
    DESCRIPTION 
        "This counter reflects the number of times a special services call is blocked by a group"
    ::= { bwOutgoingCallingPlanGroupEntry 11 }

  bwOCPGroupNumPremiumServices1CallsBlocked OBJECT-TYPE
    SYNTAX      Counter32
    MAX-ACCESS  read-write
    STATUS      current
    DESCRIPTION 
        "This counter reflects the number of times a premium services call is blocked by a group"
    ::= { bwOutgoingCallingPlanGroupEntry 12 }

  bwOCPGroupNumPremiumServices2CallsBlocked OBJECT-TYPE
    SYNTAX      Counter32
    MAX-ACCESS  read-write
    STATUS      current
    DESCRIPTION 
        "This counter reflects the number of times a premium services call is blocked by a group"
    ::= { bwOutgoingCallingPlanGroupEntry 13 }

  bwOCPGroupNumCasualCallsBlocked OBJECT-TYPE
    SYNTAX      Counter32
    MAX-ACCESS  read-write
    STATUS      current
    DESCRIPTION 
        "This counter reflects the number of times a casual equal access call is blocked by a group"
    ::= { bwOutgoingCallingPlanGroupEntry 14 }

  bwOCPGroupNumURLDialingCallsBlocked OBJECT-TYPE
    SYNTAX      Counter32
    MAX-ACCESS  read-write
    STATUS      current
    DESCRIPTION 
        "This counter reflects the number of times a URL dialed call is blocked by a group"
    ::= { bwOutgoingCallingPlanGroupEntry 15 }

  bwOCPGroupNumUnknownCallsBlocked OBJECT-TYPE
    SYNTAX      Counter32
    MAX-ACCESS  read-write
    STATUS      current
    DESCRIPTION 
        "This counter reflects the number of times an unknown call type is blocked by a group"
    ::= { bwOutgoingCallingPlanGroupEntry 16 }

  bwOCPGroupNumSuccessfulAuthorizations OBJECT-TYPE
    SYNTAX      Counter32
    MAX-ACCESS  read-write
    STATUS      current
    DESCRIPTION 
        "This counter reflects the number of times a caller enters a valid authorization code in order to establish a call for a given group."
    ::= { bwOutgoingCallingPlanGroupEntry 17 }

  bwOCPGroupNumUnsuccessfulAuthorizations OBJECT-TYPE
    SYNTAX      Counter32
    MAX-ACCESS  read-write
    STATUS      current
    DESCRIPTION 
        "This counter reflects the number of times a caller enters an invalid authorization code in order to establish a call for a given group."
    ::= { bwOutgoingCallingPlanGroupEntry 18 }

  bwOCPGroupNumTransfers OBJECT-TYPE
    SYNTAX      Counter32
    MAX-ACCESS  read-write
    STATUS      current
    DESCRIPTION 
        "This counter reflects the number of times OCP transfers the caller to a number where the caller's request will be handled for a given group."
    ::= { bwOutgoingCallingPlanGroupEntry 19 }

  bwOCPSACGroupNumSuccessfulLock OBJECT-TYPE
    SYNTAX      Counter32
    MAX-ACCESS  read-write
    STATUS      current
    DESCRIPTION 
        "This counter reflects the number of times the SAC lock feature access code is used successfully in order to lock calls for a given group"
    ::= { bwOutgoingCallingPlanGroupEntry 20 }

  bwOCPSACGroupNumSuccessfulUnlock OBJECT-TYPE
    SYNTAX      Counter32
    MAX-ACCESS  read-write
    STATUS      current
    DESCRIPTION 
        "This counter reflects the number of times the SAC unlock feature access code is used successfully in order to unlock calls for a given group"
    ::= { bwOutgoingCallingPlanGroupEntry 21 }

  bwOCPSACGroupNumUnsuccessfulLock OBJECT-TYPE
    SYNTAX      Counter32
    MAX-ACCESS  read-write
    STATUS      current
    DESCRIPTION 
        "This counter reflects the number of times the SAC lock feature access code is used unsuccessfully for a given group"
    ::= { bwOutgoingCallingPlanGroupEntry 22 }

  bwOCPSACGroupNumUnsuccessfulUnlock OBJECT-TYPE
    SYNTAX      Counter32
    MAX-ACCESS  read-write
    STATUS      current
    DESCRIPTION 
        "This counter reflects the number of times the SAC unlock feature access code is used unsuccessfully for a given group"
    ::= { bwOutgoingCallingPlanGroupEntry 23 }

  bwOCPSACGroupNumUnsuccessfulCodeUsage OBJECT-TYPE
    SYNTAX      Counter32
    MAX-ACCESS  read-write
    STATUS      current
    DESCRIPTION 
        "This counter reflects the number of times a stored SAC code is erased from the database because it fails to pass EOCP screening following a change in the EOCP plan that makes the stored SAC code obsolete for a given group"
    ::= { bwOutgoingCallingPlanGroupEntry 24 }

  bwOCPGroupNumOutsideGroupTransferBlocks OBJECT-TYPE
    SYNTAX      Counter32
    MAX-ACCESS  read-write
    STATUS      current
    DESCRIPTION 
        "This counter reflects the number of times this service denies call forwarding or transfer to a party outside of the group for a given group."
    ::= { bwOutgoingCallingPlanGroupEntry 25 }

  bwOCPNumSuccessfulAuthorizations OBJECT-TYPE
    SYNTAX      Counter32
    MAX-ACCESS  read-write
    STATUS      current
    DESCRIPTION 
        "This counter reflects the number of times a caller enters a valid authorization code in order to establish a call."
    ::= { outgoingCallingPlan 17 }

  bwOCPNumUnsuccessfulAuthorizations OBJECT-TYPE
    SYNTAX      Counter32
    MAX-ACCESS  read-write
    STATUS      current
    DESCRIPTION 
        "This counter reflects the number of times a caller enters an invalid authorization code in order to establish a call."
    ::= { outgoingCallingPlan 18 }

  bwOCPNumTransfers OBJECT-TYPE
    SYNTAX      Counter32
    MAX-ACCESS  read-write
    STATUS      current
    DESCRIPTION 
        "This counter reflects the number of times OCP transfers the caller to a number where the caller's request will be handled."
    ::= { outgoingCallingPlan 19 }

  bwOCPSACNumSuccessfulLock OBJECT-TYPE
    SYNTAX      Counter32
    MAX-ACCESS  read-write
    STATUS      current
    DESCRIPTION 
        "This counter reflects the number of times the SAC lock feature access code is used successfully in order to lock calls"
    ::= { outgoingCallingPlan 20 }

  bwOCPSACNumSuccessfulUnlock OBJECT-TYPE
    SYNTAX      Counter32
    MAX-ACCESS  read-write
    STATUS      current
    DESCRIPTION 
        "This counter reflects the number of times the SAC unlock feature access code is used successfully in order to unlock calls"
    ::= { outgoingCallingPlan 21 }

  bwOCPSACNumUnsuccessfulLock OBJECT-TYPE
    SYNTAX      Counter32
    MAX-ACCESS  read-write
    STATUS      current
    DESCRIPTION 
        "This counter reflects the number of times the SAC lock feature access code is used unsuccessfully"
    ::= { outgoingCallingPlan 22 }

  bwOCPSACNumUnsuccessfulUnlock OBJECT-TYPE
    SYNTAX      Counter32
    MAX-ACCESS  read-write
    STATUS      current
    DESCRIPTION 
        "This counter reflects the number of times the SAC unlock feature access code is used unsuccessfully"
    ::= { outgoingCallingPlan 23 }

  bwOCPSACNumUnsuccessfulCodeUsage OBJECT-TYPE
    SYNTAX      Counter32
    MAX-ACCESS  read-write
    STATUS      current
    DESCRIPTION 
        "This counter reflects the number of times a stored SAC code is erased from the database because it fails to pass EOCP screening following a change in the EOCP plan that makes the stored SAC code obsolete"
    ::= { outgoingCallingPlan 24 }

  bwOCPNumOutsideGroupTransferBlocks OBJECT-TYPE
    SYNTAX      Counter32
    MAX-ACCESS  read-write
    STATUS      current
    DESCRIPTION 
        "This counter reflects the number of times this service denies call forwarding or transfer to a party outside of the group."
    ::= { outgoingCallingPlan 25 }

  bwPriorityAlertNumDistinctive OBJECT-TYPE
    SYNTAX      Counter32
    MAX-ACCESS  read-write
    STATUS      current
    DESCRIPTION 
        "This counter reflects the number of times an incoming or waiting call has a priority
         tone applied"
    ::= { priorityAlert 1 }

  bwPriorityAlertSPTable OBJECT-TYPE
    SYNTAX      SEQUENCE OF BwPriorityAlertSPEntry
    MAX-ACCESS  not-accessible
    STATUS      current
    DESCRIPTION 
        "This table contains the counters for Priority Alert service measurements for service providers"
    ::= { priorityAlert 2 }

  bwPriorityAlertSPEntry OBJECT-TYPE
    SYNTAX      BwPriorityAlertSPEntry
    MAX-ACCESS  not-accessible
    STATUS      current
    DESCRIPTION 
        "This row contains the counters for Priority Alert service measurements for a service provider"
    INDEX       { bwPriorityAlertSPIndex }
    ::= { bwPriorityAlertSPTable 1 }

  BwPriorityAlertSPEntry ::= SEQUENCE {
    bwPriorityAlertSPIndex              Unsigned32,
    bwPriorityAlertSPID                 DisplayString,
    bwPriorityAlertSPNumDistinctive     Counter32
  }

  bwPriorityAlertSPIndex OBJECT-TYPE
    SYNTAX      Unsigned32
    MAX-ACCESS  read-only
    STATUS      current
    DESCRIPTION 
        "This integer represents the a service provider index in the system"
    ::= { bwPriorityAlertSPEntry 1 }

  bwPriorityAlertSPID OBJECT-TYPE
    SYNTAX      DisplayString
    MAX-ACCESS  read-only
    STATUS      current
    DESCRIPTION 
        "This string represents a service provider ID"
    ::= { bwPriorityAlertSPEntry 2 }

  bwPriorityAlertSPNumDistinctive OBJECT-TYPE
    SYNTAX      Counter32
    MAX-ACCESS  read-write
    STATUS      current
    DESCRIPTION 
        "This counter reflects the number of times an incoming or waiting call has a priority tone applied by a service provider"
    ::= { bwPriorityAlertSPEntry 3 }

  bwPriorityAlertGroupTable OBJECT-TYPE
    SYNTAX      SEQUENCE OF BwPriorityAlertGroupEntry
    MAX-ACCESS  not-accessible
    STATUS      current
    DESCRIPTION 
        "This table contains the counters for Priority Alert service measurements for groups"
    ::= { priorityAlert 3 }

  bwPriorityAlertGroupEntry OBJECT-TYPE
    SYNTAX      BwPriorityAlertGroupEntry
    MAX-ACCESS  not-accessible
    STATUS      current
    DESCRIPTION 
        "This row contains the counters for Priority Alert service measurements for a group"
    INDEX       { bwPriorityAlertGroupIndex }
    ::= { bwPriorityAlertGroupTable 1 }

  BwPriorityAlertGroupEntry ::= SEQUENCE {
    bwPriorityAlertGroupIndex           Unsigned32,
    bwPriorityAlertGroupID              DisplayString,
    bwPriorityAlertGroupNumDistinctive  Counter32
  }

  bwPriorityAlertGroupIndex OBJECT-TYPE
    SYNTAX      Unsigned32
    MAX-ACCESS  read-only
    STATUS      current
    DESCRIPTION 
        "This integer represents the a group index in the system"
    ::= { bwPriorityAlertGroupEntry 1 }

  bwPriorityAlertGroupID OBJECT-TYPE
    SYNTAX      DisplayString
    MAX-ACCESS  read-only
    STATUS      current
    DESCRIPTION 
        "This string represents a group ID"
    ::= { bwPriorityAlertGroupEntry 2 }

  bwPriorityAlertGroupNumDistinctive OBJECT-TYPE
    SYNTAX      Counter32
    MAX-ACCESS  read-write
    STATUS      current
    DESCRIPTION 
        "This counter reflects the number of times an incoming or waiting call has a priority tone applied by a group"
    ::= { bwPriorityAlertGroupEntry 3 }

  bwSCANumAcceptances OBJECT-TYPE
    SYNTAX      Counter32
    MAX-ACCESS  read-write
    STATUS      current
    DESCRIPTION 
        "This counter reflects the number of times an incoming call meets a criteria for this
         service"
    ::= { selectiveCallAcceptance 1 }

  bwSelectiveCallAcceptanceSPTable OBJECT-TYPE
    SYNTAX      SEQUENCE OF BwSelectiveCallAcceptanceSPEntry
    MAX-ACCESS  not-accessible
    STATUS      current
    DESCRIPTION 
        "This table contains the counters for Selective Call Acceptance service measurements for service providers"
    ::= { selectiveCallAcceptance 2 }

  bwSelectiveCallAcceptanceSPEntry OBJECT-TYPE
    SYNTAX      BwSelectiveCallAcceptanceSPEntry
    MAX-ACCESS  not-accessible
    STATUS      current
    DESCRIPTION 
        "This row contains the counters for Selective Call Acceptance service measurements for a service provider"
    INDEX       { bwSelectiveCallAcceptanceSPIndex }
    ::= { bwSelectiveCallAcceptanceSPTable 1 }

  BwSelectiveCallAcceptanceSPEntry ::= SEQUENCE {
    bwSelectiveCallAcceptanceSPIndex    Unsigned32,
    bwSelectiveCallAcceptanceSPID       DisplayString,
    bwSCASPNumAcceptances               Counter32
  }

  bwSelectiveCallAcceptanceSPIndex OBJECT-TYPE
    SYNTAX      Unsigned32
    MAX-ACCESS  read-only
    STATUS      current
    DESCRIPTION 
        "This integer represents the a service provider index in the system"
    ::= { bwSelectiveCallAcceptanceSPEntry 1 }

  bwSelectiveCallAcceptanceSPID OBJECT-TYPE
    SYNTAX      DisplayString
    MAX-ACCESS  read-only
    STATUS      current
    DESCRIPTION 
        "This string represents a service provider ID"
    ::= { bwSelectiveCallAcceptanceSPEntry 2 }

  bwSCASPNumAcceptances OBJECT-TYPE
    SYNTAX      Counter32
    MAX-ACCESS  read-write
    STATUS      current
    DESCRIPTION 
        "This counter reflects the number of times an incoming call meets a criteria for this service by a service provider"
    ::= { bwSelectiveCallAcceptanceSPEntry 3 }

  bwSelectiveCallAcceptanceGroupTable OBJECT-TYPE
    SYNTAX      SEQUENCE OF BwSelectiveCallAcceptanceGroupEntry
    MAX-ACCESS  not-accessible
    STATUS      current
    DESCRIPTION 
        "This table contains the counters for Selective Call Acceptance service measurements for groups"
    ::= { selectiveCallAcceptance 3 }

  bwSelectiveCallAcceptanceGroupEntry OBJECT-TYPE
    SYNTAX      BwSelectiveCallAcceptanceGroupEntry
    MAX-ACCESS  not-accessible
    STATUS      current
    DESCRIPTION 
        "This row contains the counters for Selective Call Acceptance service measurements for a group"
    INDEX       { bwSelectiveCallAcceptanceGroupIndex }
    ::= { bwSelectiveCallAcceptanceGroupTable 1 }

  BwSelectiveCallAcceptanceGroupEntry ::= SEQUENCE {
    bwSelectiveCallAcceptanceGroupIndex     Unsigned32,
    bwSelectiveCallAcceptanceGroupID        DisplayString,
    bwSCAGroupNumAcceptances                Counter32
  }

  bwSelectiveCallAcceptanceGroupIndex OBJECT-TYPE
    SYNTAX      Unsigned32
    MAX-ACCESS  read-only
    STATUS      current
    DESCRIPTION 
        "This integer represents the a group index in the system"
    ::= { bwSelectiveCallAcceptanceGroupEntry 1 }

  bwSelectiveCallAcceptanceGroupID OBJECT-TYPE
    SYNTAX      DisplayString
    MAX-ACCESS  read-only
    STATUS      current
    DESCRIPTION 
        "This string represents a group ID"
    ::= { bwSelectiveCallAcceptanceGroupEntry 2 }

  bwSCAGroupNumAcceptances OBJECT-TYPE
    SYNTAX      Counter32
    MAX-ACCESS  read-write
    STATUS      current
    DESCRIPTION 
        "This counter reflects the number of times an incoming call meets a criteria for this service by a group"
    ::= { bwSelectiveCallAcceptanceGroupEntry 3 }

  bwSCFNumForwards OBJECT-TYPE
    SYNTAX      Counter32
    MAX-ACCESS  read-write
    STATUS      current
    DESCRIPTION 
        "This counter reflects the number of times a criteria is met for this service"
    ::= { selectiveCallForward 1 }

  bwSelectiveCallForwardSPTable OBJECT-TYPE
    SYNTAX      SEQUENCE OF BwSelectiveCallForwardSPEntry
    MAX-ACCESS  not-accessible
    STATUS      current
    DESCRIPTION 
        "This table contains the counters for Call Forwarding Selective service measurements for service providers"
    ::= { selectiveCallForward 2 }

  bwSelectiveCallForwardSPEntry OBJECT-TYPE
    SYNTAX      BwSelectiveCallForwardSPEntry
    MAX-ACCESS  not-accessible
    STATUS      current
    DESCRIPTION 
        "This row contains the counters for Call Forwarding Selective service measurements for a service provider"
    INDEX       { bwSelectiveCallForwardSPIndex }
    ::= { bwSelectiveCallForwardSPTable 1 }

  BwSelectiveCallForwardSPEntry ::= SEQUENCE {
    bwSelectiveCallForwardSPIndex   Unsigned32,
    bwSelectiveCallForwardSPID      DisplayString,
    bwSCFSPNumForwards              Counter32,
    bwSCFSPNumPhoneActivations      Counter32,
    bwSCFSPNumPhoneDeactivations    Counter32
  }

  bwSelectiveCallForwardSPIndex OBJECT-TYPE
    SYNTAX      Unsigned32
    MAX-ACCESS  read-only
    STATUS      current
    DESCRIPTION 
        "This integer represents the a service provider index in the system"
    ::= { bwSelectiveCallForwardSPEntry 1 }

  bwSelectiveCallForwardSPID OBJECT-TYPE
    SYNTAX      DisplayString
    MAX-ACCESS  read-only
    STATUS      current
    DESCRIPTION 
        "This string represents a service provider ID"
    ::= { bwSelectiveCallForwardSPEntry 2 }

  bwSCFSPNumForwards OBJECT-TYPE
    SYNTAX      Counter32
    MAX-ACCESS  read-write
    STATUS      current
    DESCRIPTION 
        "This counter reflects the number of times a criteria is met for this service by a service provider"
    ::= { bwSelectiveCallForwardSPEntry 3 }

  bwSCFSPNumPhoneActivations OBJECT-TYPE
    SYNTAX      Counter32
    MAX-ACCESS  read-write
    STATUS      current
    DESCRIPTION 
        "This is the number of times SCF has been activated via FAC for users in a given service provider."
    ::= { bwSelectiveCallForwardSPEntry 4 }

  bwSCFSPNumPhoneDeactivations OBJECT-TYPE
    SYNTAX      Counter32
    MAX-ACCESS  read-write
    STATUS      current
    DESCRIPTION 
        "This is the number of times SCF has been deactivated via FAC for users in a given service provider."
    ::= { bwSelectiveCallForwardSPEntry 5 }

  bwSelectiveCallForwardGroupTable OBJECT-TYPE
    SYNTAX      SEQUENCE OF BwSelectiveCallForwardGroupEntry
    MAX-ACCESS  not-accessible
    STATUS      current
    DESCRIPTION 
        "This table contains the counters for Call Forwarding Selective service measurements for groups"
    ::= { selectiveCallForward 3 }

  bwSelectiveCallForwardGroupEntry OBJECT-TYPE
    SYNTAX      BwSelectiveCallForwardGroupEntry
    MAX-ACCESS  not-accessible
    STATUS      current
    DESCRIPTION 
        "This row contains the counters for Call Forwarding Selective service measurements for a group"
    INDEX       { bwSelectiveCallForwardGroupIndex }
    ::= { bwSelectiveCallForwardGroupTable 1 }

  BwSelectiveCallForwardGroupEntry ::= SEQUENCE {
    bwSelectiveCallForwardGroupIndex    Unsigned32,
    bwSelectiveCallForwardGroupID       DisplayString,
    bwSCFGroupNumForwards               Counter32,
    bwSCFGroupNumPhoneActivations       Counter32,
    bwSCFGroupNumPhoneDeactivations     Counter32
  }

  bwSelectiveCallForwardGroupIndex OBJECT-TYPE
    SYNTAX      Unsigned32
    MAX-ACCESS  read-only
    STATUS      current
    DESCRIPTION 
        "This integer represents the a group index in the system"
    ::= { bwSelectiveCallForwardGroupEntry 1 }

  bwSelectiveCallForwardGroupID OBJECT-TYPE
    SYNTAX      DisplayString
    MAX-ACCESS  read-only
    STATUS      current
    DESCRIPTION 
        "This string represents a group ID"
    ::= { bwSelectiveCallForwardGroupEntry 2 }

  bwSCFGroupNumForwards OBJECT-TYPE
    SYNTAX      Counter32
    MAX-ACCESS  read-write
    STATUS      current
    DESCRIPTION 
        "This counter reflects the number of times a criteria is met for this service by a group"
    ::= { bwSelectiveCallForwardGroupEntry 3 }

  bwSCFGroupNumPhoneActivations OBJECT-TYPE
    SYNTAX      Counter32
    MAX-ACCESS  read-write
    STATUS      current
    DESCRIPTION 
        "TThis is the number of times SCF has been activated via FAC for users in a given group."
    ::= { bwSelectiveCallForwardGroupEntry 4 }

  bwSCFGroupNumPhoneDeactivations OBJECT-TYPE
    SYNTAX      Counter32
    MAX-ACCESS  read-write
    STATUS      current
    DESCRIPTION 
        "This is the number of times SCF has been deactivated via FAC for users in a given group."
    ::= { bwSelectiveCallForwardGroupEntry 5 }

  bwSCFNumPhoneActivations OBJECT-TYPE
    SYNTAX      Counter32
    MAX-ACCESS  read-write
    STATUS      current
    DESCRIPTION 
        "This is the number of times SCF has been activated via FAC."
    ::= { selectiveCallForward 4 }

  bwSCFNumPhoneDeactivations OBJECT-TYPE
    SYNTAX      Counter32
    MAX-ACCESS  read-write
    STATUS      current
    DESCRIPTION 
        "This is the number of times SCF has been deactivated via FAC."
    ::= { selectiveCallForward 5 }

  bwSCRNumRejects OBJECT-TYPE
    SYNTAX      Counter32
    MAX-ACCESS  read-write
    STATUS      current
    DESCRIPTION 
        "This counter reflects the number of times an incoming call meets a criteria for this
         service"
    ::= { selectiveCallRejection 1 }

  bwSelectiveCallRejectionSPTable OBJECT-TYPE
    SYNTAX      SEQUENCE OF BwSelectiveCallRejectionSPEntry
    MAX-ACCESS  not-accessible
    STATUS      current
    DESCRIPTION 
        "This table contains the counters for Selective Call Rejection service measurements for service providers"
    ::= { selectiveCallRejection 2 }

  bwSelectiveCallRejectionSPEntry OBJECT-TYPE
    SYNTAX      BwSelectiveCallRejectionSPEntry
    MAX-ACCESS  not-accessible
    STATUS      current
    DESCRIPTION 
        "This row contains the counters for Selective Call Rejection service measurements for a service provider"
    INDEX       { bwSelectiveCallRejectionSPIndex }
    ::= { bwSelectiveCallRejectionSPTable 1 }

  BwSelectiveCallRejectionSPEntry ::= SEQUENCE {
    bwSelectiveCallRejectionSPIndex     Unsigned32,
    bwSelectiveCallRejectionSPID        DisplayString,
    bwSCRSPNumRejects                   Counter32
  }

  bwSelectiveCallRejectionSPIndex OBJECT-TYPE
    SYNTAX      Unsigned32
    MAX-ACCESS  read-only
    STATUS      current
    DESCRIPTION 
        "This integer represents the a service provider index in the system"
    ::= { bwSelectiveCallRejectionSPEntry 1 }

  bwSelectiveCallRejectionSPID OBJECT-TYPE
    SYNTAX      DisplayString
    MAX-ACCESS  read-only
    STATUS      current
    DESCRIPTION 
        "This string represents a service provider ID"
    ::= { bwSelectiveCallRejectionSPEntry 2 }

  bwSCRSPNumRejects OBJECT-TYPE
    SYNTAX      Counter32
    MAX-ACCESS  read-write
    STATUS      current
    DESCRIPTION 
        "This counter reflects the number of times an incoming call meets a criteria for this service by a service provider"
    ::= { bwSelectiveCallRejectionSPEntry 3 }

  bwSelectiveCallRejectionGroupTable OBJECT-TYPE
    SYNTAX      SEQUENCE OF BwSelectiveCallRejectionGroupEntry
    MAX-ACCESS  not-accessible
    STATUS      current
    DESCRIPTION 
        "This table contains the counters for Selective Call Rejection service measurements for groups"
    ::= { selectiveCallRejection 3 }

  bwSelectiveCallRejectionGroupEntry OBJECT-TYPE
    SYNTAX      BwSelectiveCallRejectionGroupEntry
    MAX-ACCESS  not-accessible
    STATUS      current
    DESCRIPTION 
        "This row contains the counters for Selective Call Rejection service measurements for a group"
    INDEX       { bwSelectiveCallRejectionGroupIndex }
    ::= { bwSelectiveCallRejectionGroupTable 1 }

  BwSelectiveCallRejectionGroupEntry ::= SEQUENCE {
    bwSelectiveCallRejectionGroupIndex  Unsigned32,
    bwSelectiveCallRejectionGroupID     DisplayString,
    bwSCRGroupNumRejects                Counter32
  }

  bwSelectiveCallRejectionGroupIndex OBJECT-TYPE
    SYNTAX      Unsigned32
    MAX-ACCESS  read-only
    STATUS      current
    DESCRIPTION 
        "This integer represents the a group index in the system"
    ::= { bwSelectiveCallRejectionGroupEntry 1 }

  bwSelectiveCallRejectionGroupID OBJECT-TYPE
    SYNTAX      DisplayString
    MAX-ACCESS  read-only
    STATUS      current
    DESCRIPTION 
        "This string represents a group ID"
    ::= { bwSelectiveCallRejectionGroupEntry 2 }

  bwSCRGroupNumRejects OBJECT-TYPE
    SYNTAX      Counter32
    MAX-ACCESS  read-write
    STATUS      current
    DESCRIPTION 
        "This counter reflects the number of times an incoming call meets a criteria for this service by a group"
    ::= { bwSelectiveCallRejectionGroupEntry 3 }

  bwSimRingPersonalNumAttempts OBJECT-TYPE
    SYNTAX      Counter32
    MAX-ACCESS  read-write
    STATUS      current
    DESCRIPTION 
        "This counter reflects the number of times an incoming call attempt is received"
    ::= { simRingPersonal 1 }

  bwSimRingPersonalNumBusy OBJECT-TYPE
    SYNTAX      Counter32
    MAX-ACCESS  read-write
    STATUS      current
    DESCRIPTION 
        "This counter reflects the number of times that all parties to whom call delivery attempts
         are made, are busy"
    ::= { simRingPersonal 2 }

  bwSimRingPersonalSPTable OBJECT-TYPE
    SYNTAX      SEQUENCE OF BwSimRingPersonalSPEntry
    MAX-ACCESS  not-accessible
    STATUS      current
    DESCRIPTION 
        "This table contains the counters for Simultaneous Ring Personal service measurements for service providers"
    ::= { simRingPersonal 3 }

  bwSimRingPersonalSPEntry OBJECT-TYPE
    SYNTAX      BwSimRingPersonalSPEntry
    MAX-ACCESS  not-accessible
    STATUS      current
    DESCRIPTION 
        "This row contains the counters for Simultaneous Ring Personal service measurements for a service provider"
    INDEX       { bwSimRingPersonalSPIndex }
    ::= { bwSimRingPersonalSPTable 1 }

  BwSimRingPersonalSPEntry ::= SEQUENCE {
    bwSimRingPersonalSPIndex        Unsigned32,
    bwSimRingPersonalSPID           DisplayString,
    bwSimRingPersonalSPNumAttempts  Counter32,
    bwSimRingPersonalSPNumBusy      Counter32
  }

  bwSimRingPersonalSPIndex OBJECT-TYPE
    SYNTAX      Unsigned32
    MAX-ACCESS  read-only
    STATUS      current
    DESCRIPTION 
        "This integer represents the a service provider index in the system"
    ::= { bwSimRingPersonalSPEntry 1 }

  bwSimRingPersonalSPID OBJECT-TYPE
    SYNTAX      DisplayString
    MAX-ACCESS  read-only
    STATUS      current
    DESCRIPTION 
        "This string represents a service provider ID"
    ::= { bwSimRingPersonalSPEntry 2 }

  bwSimRingPersonalSPNumAttempts OBJECT-TYPE
    SYNTAX      Counter32
    MAX-ACCESS  read-write
    STATUS      current
    DESCRIPTION 
        "This counter reflects the number of times an incoming call attempt is received by a service provider"
    ::= { bwSimRingPersonalSPEntry 3 }

  bwSimRingPersonalSPNumBusy OBJECT-TYPE
    SYNTAX      Counter32
    MAX-ACCESS  read-write
    STATUS      current
    DESCRIPTION 
        "This counter reflects the number of times that all parties to whom call delivery attempts are made by a service provider, are busy"
    ::= { bwSimRingPersonalSPEntry 4 }

  bwSimRingPersonalGroupTable OBJECT-TYPE
    SYNTAX      SEQUENCE OF BwSimRingPersonalGroupEntry
    MAX-ACCESS  not-accessible
    STATUS      current
    DESCRIPTION 
        "This table contains the counters for Simultaneous Ring Personal service measurements for groups"
    ::= { simRingPersonal 4 }

  bwSimRingPersonalGroupEntry OBJECT-TYPE
    SYNTAX      BwSimRingPersonalGroupEntry
    MAX-ACCESS  not-accessible
    STATUS      current
    DESCRIPTION 
        "This row contains the counters for Simultaneous Ring Personal service measurements for a group"
    INDEX       { bwSimRingPersonalGroupIndex }
    ::= { bwSimRingPersonalGroupTable 1 }

  BwSimRingPersonalGroupEntry ::= SEQUENCE {
    bwSimRingPersonalGroupIndex         Unsigned32,
    bwSimRingPersonalGroupID            DisplayString,
    bwSimRingPersonalGroupNumAttempts   Counter32,
    bwSimRingPersonalGroupNumBusy       Counter32
  }

  bwSimRingPersonalGroupIndex OBJECT-TYPE
    SYNTAX      Unsigned32
    MAX-ACCESS  read-only
    STATUS      current
    DESCRIPTION 
        "This integer represents the a group index in the system"
    ::= { bwSimRingPersonalGroupEntry 1 }

  bwSimRingPersonalGroupID OBJECT-TYPE
    SYNTAX      DisplayString
    MAX-ACCESS  read-only
    STATUS      current
    DESCRIPTION 
        "This string represents a group ID"
    ::= { bwSimRingPersonalGroupEntry 2 }

  bwSimRingPersonalGroupNumAttempts OBJECT-TYPE
    SYNTAX      Counter32
    MAX-ACCESS  read-write
    STATUS      current
    DESCRIPTION 
        "This counter reflects the number of times an incoming call attempt is received by a group"
    ::= { bwSimRingPersonalGroupEntry 3 }

  bwSimRingPersonalGroupNumBusy OBJECT-TYPE
    SYNTAX      Counter32
    MAX-ACCESS  read-write
    STATUS      current
    DESCRIPTION 
        "This counter reflects the number of times that all parties to whom call delivery attempts are made by a group, are busy"
    ::= { bwSimRingPersonalGroupEntry 4 }

-- Services :: voiceMessaging ...........................................

  bwVMNumBusyGreetingsPlayed OBJECT-TYPE
    SYNTAX      Counter32
    MAX-ACCESS  read-write
    STATUS      current
    DESCRIPTION 
        "This counter reflects the number of times a busy greeting is played to a caller"
    ::= { voiceMessaging 1 }

  bwVMNumNoAnswerGreetingsPlayed OBJECT-TYPE
    SYNTAX      Counter32
    MAX-ACCESS  read-write
    STATUS      current
    DESCRIPTION 
        "This counter reflects the number of times a no answer greeting is played"
    ::= { voiceMessaging 2 }

  bwVMNumMessagesLeft OBJECT-TYPE
    SYNTAX      Counter32
    MAX-ACCESS  read-write
    STATUS      current
    DESCRIPTION 
        "This counter reflects the number of times a voice message is recorded"
    ::= { voiceMessaging 3 }

  bwVMRNumBusyGreetingsRecorded OBJECT-TYPE
    SYNTAX      Counter32
    MAX-ACCESS  read-write
    STATUS      current
    DESCRIPTION 
        "This counter reflects the number of times a busy greeting is recorded over the phone"
    ::= { voiceMessaging 4 }

  bwVMRNumNoAnswerGreetingsRecorded OBJECT-TYPE
    SYNTAX      Counter32
    MAX-ACCESS  read-write
    STATUS      current
    DESCRIPTION 
        "This counter reflects the number of times a no answer greeting is recorded over the
         phone"
    ::= { voiceMessaging 5 }

  bwVMRNumPersonalizedNamesRecorded OBJECT-TYPE
    SYNTAX      Counter32
    MAX-ACCESS  read-write
    STATUS      current
    DESCRIPTION 
        "This counter reflects the number of times a personalized name greeting is recorded
         over the phone"
    ::= { voiceMessaging 6 }

  bwVMRNumLoginAttempts OBJECT-TYPE
    SYNTAX      Counter32
    MAX-ACCESS  read-write
    STATUS      current
    DESCRIPTION 
        "This counter reflects the number of times a user attempts a login over the phone"
    ::= { voiceMessaging 7 }

  bwVMRNumLoginFailures OBJECT-TYPE
    SYNTAX      Counter32
    MAX-ACCESS  read-write
    STATUS      current
    DESCRIPTION 
        "This counter reflects the number of times a user login attempt fails"
    ::= { voiceMessaging 8 }

  bwVMRNumComposeSendAttempts OBJECT-TYPE
    SYNTAX      Counter32
    MAX-ACCESS  read-write
    STATUS      current
    DESCRIPTION 
        "This counter reflects the number of times a composed message is sent to a user"
    ::= { voiceMessaging 9 }

  bwVMRNumComposeSendGroupAttempts OBJECT-TYPE
    SYNTAX      Counter32
    MAX-ACCESS  read-write
    STATUS      current
    DESCRIPTION 
        "This counter reflects the number of times a composed message is sent to a group"
    ::= { voiceMessaging 10 }

  bwVMRNumForwardSendAttempts OBJECT-TYPE
    SYNTAX      Counter32
    MAX-ACCESS  read-write
    STATUS      current
    DESCRIPTION 
        "This counter reflects the number of times a forwarded message is sent to a user"
    ::= { voiceMessaging 11 }

  bwVMRNumForwardSendGroupAttempts OBJECT-TYPE
    SYNTAX      Counter32
    MAX-ACCESS  read-write
    STATUS      current
    DESCRIPTION 
        "This counter reflects the number of times a forwarded message is sent to a group"
    ::= { voiceMessaging 12 }

  bwVMRNumReplySendAttempts OBJECT-TYPE
    SYNTAX      Counter32
    MAX-ACCESS  read-write
    STATUS      current
    DESCRIPTION 
        "This counter reflects the number of times a message reply is sent"
    ::= { voiceMessaging 13 }

  bwVMRNumSendFailed OBJECT-TYPE
    SYNTAX      Counter32
    MAX-ACCESS  read-write
    STATUS      current
    DESCRIPTION 
        "This counter reflects the number of times an attempt to send a message to a user failed"
    ::= { voiceMessaging 14 }

  bwVMRNumSendGroupFailed OBJECT-TYPE
    SYNTAX      Counter32
    MAX-ACCESS  read-write
    STATUS      current
    DESCRIPTION 
        "This counter reflects the number of times an attempt to send a message to a group failed"
    ::= { voiceMessaging 15 }

  bwVMRDeleteAllMsgsAttempts OBJECT-TYPE
    SYNTAX      Counter32
    MAX-ACCESS  read-write
    STATUS      current
    DESCRIPTION 
        "This counter reflects the number of times a user attempts to delete all messages"
    ::= { voiceMessaging 16 }

  bwVMRCallBackAttempts OBJECT-TYPE
    SYNTAX      Counter32
    MAX-ACCESS  read-write
    STATUS      current
    DESCRIPTION 
        "This counter reflects the number of times a user attempts to callback the caller"
    ::= { voiceMessaging 17 }

  bwVPNumAABusHoursGreetingRecorded OBJECT-TYPE
    SYNTAX      Counter32
    MAX-ACCESS  read-write
    STATUS      current
    DESCRIPTION 
        "This counter reflects the number of times an AA business hours greeting is recorded over the phone"
    ::= { voiceMessaging 19 }

  bwVPNumAAAfterHoursGreetingRecorded OBJECT-TYPE
    SYNTAX      Counter32
    MAX-ACCESS  read-write
    STATUS      current
    DESCRIPTION 
        "This counter reflects the number of times an AA after hours greeting is recorded over the phone"
    ::= { voiceMessaging 20 }

  bwVPNumCFADestinationChanged OBJECT-TYPE
    SYNTAX      Counter32
    MAX-ACCESS  read-write
    STATUS      current
    DESCRIPTION 
        "This counter reflects the number of times a CFA destination is changed over the phone"
    ::= { voiceMessaging 21 }

  bwVPNumPasscodeChanged OBJECT-TYPE
    SYNTAX      Counter32
    MAX-ACCESS  read-write
    STATUS      current
    DESCRIPTION 
        "This counter reflects the number of times a Voice Portal passcode is changed over the phone"
    ::= { voiceMessaging 22 }

  bwVoiceMessagingSPTable OBJECT-TYPE
    SYNTAX      SEQUENCE OF BwVoiceMessagingSPEntry
    MAX-ACCESS  not-accessible
    STATUS      current
    DESCRIPTION 
        "This table contains the counters for Voice Messaging service measurements for service providers"
    ::= { voiceMessaging 23 }

  bwVoiceMessagingSPEntry OBJECT-TYPE
    SYNTAX      BwVoiceMessagingSPEntry
    MAX-ACCESS  not-accessible
    STATUS      current
    DESCRIPTION 
        "This row contains the counters for Voice Messaging service measurements for a service provider"
    INDEX       { bwVoiceMessagingSPIndex }
    ::= { bwVoiceMessagingSPTable 1 }

  BwVoiceMessagingSPEntry ::= SEQUENCE {
    bwVoiceMessagingSPIndex                     Unsigned32,
    bwVoiceMessagingSPID                        DisplayString,
    bwVMSPNumBusyGreetingsPlayed                Counter32,
    bwVMSPNumNoAnswerGreetingsPlayed            Counter32,
    bwVMSPNumMessagesLeft                       Counter32,
    bwVMRSPNumBusyGreetingsRecorded             Counter32,
    bwVMRSPNumNoAnswerGreetingsRecorded         Counter32,
    bwVMRSPNumPersonalizedNamesRecorded         Counter32,
    bwVMRSPNumLoginAttempts                     Counter32,
    bwVMRSPNumLoginFailures                     Counter32,
    bwVMRSPNumComposeSendAttempts               Counter32,
    bwVMRSPNumComposeSendGroupAttempts          Counter32,
    bwVMRSPNumForwardSendAttempts               Counter32,
    bwVMRSPNumForwardSendGroupAttempts          Counter32,
    bwVMRSPNumReplySendAttempts                 Counter32,
    bwVMRSPNumSendFailed                        Counter32,
    bwVMRSPNumSendGroupFailed                   Counter32,
    bwVMRSPDeleteAllMsgsAttempts                Counter32,
    bwVMRSPCallBackAttempts                     Counter32,
    bwVPSPNumAABusHoursGreetingRecorded         Counter32,
    bwVPSPNumAAAfterHoursGreetingRecorded       Counter32,
    bwVPSPNumCFADestinationChanged              Counter32,
    bwVPSPNumPasscodeChanged                    Counter32,
    bwVMRSPNumComposeSendListAttempts           Counter32,
    bwVMRSPNumForwardSendListAttempts           Counter32,
    bwVMRSPNumSendListFailed                    Counter32,
    bwVPSPGreetingRecorded                      Counter32,
    bwVMSPGreetingRecorded                      Counter32,
    bwVPCSPCall                                 Counter32,
    bwSPMultiMediaMsgDeposit                    Counter32,
    bwVMSPMultiMediaGreetingRecorded            Counter32,
    bwAutoAttendantSPMultiMediaPromptRecorded   Counter32,
    bwMessagingSPQuery                          Counter32,
    bwMessagingSPQueryNoUser                    Counter32,
    bwMessagingSPQueryNoMailbox                 Counter32,
    bwVPSPNumAAHolidayGreetingRecorded          Counter32
  }

  bwVoiceMessagingSPIndex OBJECT-TYPE
    SYNTAX      Unsigned32
    MAX-ACCESS  read-only
    STATUS      current
    DESCRIPTION 
        "This integer represents the a service provider index in the system"
    ::= { bwVoiceMessagingSPEntry 1 }

  bwVoiceMessagingSPID OBJECT-TYPE
    SYNTAX      DisplayString
    MAX-ACCESS  read-only
    STATUS      current
    DESCRIPTION 
        "This string represents a service provider ID"
    ::= { bwVoiceMessagingSPEntry 2 }

  bwVMSPNumBusyGreetingsPlayed OBJECT-TYPE
    SYNTAX      Counter32
    MAX-ACCESS  read-write
    STATUS      current
    DESCRIPTION 
        "This counter reflects the number of times a busy greeting is played to a caller by a service provider"
    ::= { bwVoiceMessagingSPEntry 3 }

  bwVMSPNumNoAnswerGreetingsPlayed OBJECT-TYPE
    SYNTAX      Counter32
    MAX-ACCESS  read-write
    STATUS      current
    DESCRIPTION 
        "This counter reflects the number of times a no answer greeting is played by a service provider"
    ::= { bwVoiceMessagingSPEntry 4 }

  bwVMSPNumMessagesLeft OBJECT-TYPE
    SYNTAX      Counter32
    MAX-ACCESS  read-write
    STATUS      current
    DESCRIPTION 
        "This counter reflects the number of times a voice message is recorded by a service provider"
    ::= { bwVoiceMessagingSPEntry 5 }

  bwVMRSPNumBusyGreetingsRecorded OBJECT-TYPE
    SYNTAX      Counter32
    MAX-ACCESS  read-write
    STATUS      current
    DESCRIPTION 
        "This counter reflects the number of times a busy greeting is recorded over the phone by a service provider"
    ::= { bwVoiceMessagingSPEntry 6 }

  bwVMRSPNumNoAnswerGreetingsRecorded OBJECT-TYPE
    SYNTAX      Counter32
    MAX-ACCESS  read-write
    STATUS      current
    DESCRIPTION 
        "This counter reflects the number of times a no answer greeting is recorded over the phone by a service provider"
    ::= { bwVoiceMessagingSPEntry 7 }

  bwVMRSPNumPersonalizedNamesRecorded OBJECT-TYPE
    SYNTAX      Counter32
    MAX-ACCESS  read-write
    STATUS      current
    DESCRIPTION 
        "This counter reflects the number of times a personalized name greeting is recorded over the phone by a service provider"
    ::= { bwVoiceMessagingSPEntry 8 }

  bwVMRSPNumLoginAttempts OBJECT-TYPE
    SYNTAX      Counter32
    MAX-ACCESS  read-write
    STATUS      current
    DESCRIPTION 
        "This counter reflects the number of times a user attempts a login over the phone by a service provider"
    ::= { bwVoiceMessagingSPEntry 9 }

  bwVMRSPNumLoginFailures OBJECT-TYPE
    SYNTAX      Counter32
    MAX-ACCESS  read-write
    STATUS      current
    DESCRIPTION 
        "This counter reflects the number of times a user login attempt fails by a service provider"
    ::= { bwVoiceMessagingSPEntry 10 }

  bwVMRSPNumComposeSendAttempts OBJECT-TYPE
    SYNTAX      Counter32
    MAX-ACCESS  read-write
    STATUS      current
    DESCRIPTION 
        "This counter reflects the number of times a composed message is sent to a user by a service provider"
    ::= { bwVoiceMessagingSPEntry 11 }

  bwVMRSPNumComposeSendGroupAttempts OBJECT-TYPE
    SYNTAX      Counter32
    MAX-ACCESS  read-write
    STATUS      current
    DESCRIPTION 
        "This counter reflects the number of times a composed message is sent to a group by a service provider"
    ::= { bwVoiceMessagingSPEntry 12 }

  bwVMRSPNumForwardSendAttempts OBJECT-TYPE
    SYNTAX      Counter32
    MAX-ACCESS  read-write
    STATUS      current
    DESCRIPTION 
        "This counter reflects the number of times a forwarded message is sent to a user by a service provider"
    ::= { bwVoiceMessagingSPEntry 13 }

  bwVMRSPNumForwardSendGroupAttempts OBJECT-TYPE
    SYNTAX      Counter32
    MAX-ACCESS  read-write
    STATUS      current
    DESCRIPTION 
        "This counter reflects the number of times a forwarded message is sent to a group by a service provider"
    ::= { bwVoiceMessagingSPEntry 14 }

  bwVMRSPNumReplySendAttempts OBJECT-TYPE
    SYNTAX      Counter32
    MAX-ACCESS  read-write
    STATUS      current
    DESCRIPTION 
        "This counter reflects the number of times a message reply is sent by a service provider"
    ::= { bwVoiceMessagingSPEntry 15 }

  bwVMRSPNumSendFailed OBJECT-TYPE
    SYNTAX      Counter32
    MAX-ACCESS  read-write
    STATUS      current
    DESCRIPTION 
        "This counter reflects the number of times an attempt to send a message to a user failed by a service provider"
    ::= { bwVoiceMessagingSPEntry 16 }

  bwVMRSPNumSendGroupFailed OBJECT-TYPE
    SYNTAX      Counter32
    MAX-ACCESS  read-write
    STATUS      current
    DESCRIPTION 
        "This counter reflects the number of times an attempt to send a message to a group failed by a service provider"
    ::= { bwVoiceMessagingSPEntry 17 }

  bwVMRSPDeleteAllMsgsAttempts OBJECT-TYPE
    SYNTAX      Counter32
    MAX-ACCESS  read-write
    STATUS      current
    DESCRIPTION 
        "This counter reflects the number of times a user attempts to delete all messages by a service provider"
    ::= { bwVoiceMessagingSPEntry 18 }

  bwVMRSPCallBackAttempts OBJECT-TYPE
    SYNTAX      Counter32
    MAX-ACCESS  read-write
    STATUS      current
    DESCRIPTION 
        "This counter reflects the number of times a user attempts to callback the caller by a service provider"
    ::= { bwVoiceMessagingSPEntry 19 }

  bwVPSPNumAABusHoursGreetingRecorded OBJECT-TYPE
    SYNTAX      Counter32
    MAX-ACCESS  read-write
    STATUS      current
    DESCRIPTION 
        "This counter reflects the number of times an AA business hours greeting is recorded over the phone by a service provider"
    ::= { bwVoiceMessagingSPEntry 21 }

  bwVPSPNumAAAfterHoursGreetingRecorded OBJECT-TYPE
    SYNTAX      Counter32
    MAX-ACCESS  read-write
    STATUS      current
    DESCRIPTION 
        "This counter reflects the number of times an AA after hours greeting is recorded over the phone by a service provider"
    ::= { bwVoiceMessagingSPEntry 22 }

  bwVPSPNumCFADestinationChanged OBJECT-TYPE
    SYNTAX      Counter32
    MAX-ACCESS  read-write
    STATUS      current
    DESCRIPTION 
        "This counter reflects the number of times a CFA destination is changed over the phone by a service provider"
    ::= { bwVoiceMessagingSPEntry 23 }

  bwVPSPNumPasscodeChanged OBJECT-TYPE
    SYNTAX      Counter32
    MAX-ACCESS  read-write
    STATUS      current
    DESCRIPTION 
        "This counter reflects the number of times a Voice Portal is changed over the phone by a service provider"
    ::= { bwVoiceMessagingSPEntry 24 }

  bwVMRSPNumComposeSendListAttempts OBJECT-TYPE
    SYNTAX      Counter32
    MAX-ACCESS  read-write
    STATUS      current
    DESCRIPTION 
        "This counter reflects the number of times a composed message is sent to a distribution list by a service provider"
    ::= { bwVoiceMessagingSPEntry 25 }

  bwVMRSPNumForwardSendListAttempts OBJECT-TYPE
    SYNTAX      Counter32
    MAX-ACCESS  read-write
    STATUS      current
    DESCRIPTION 
        "This counter reflects the number of times a forwarded message is sent to a distribution list by a service provider"
    ::= { bwVoiceMessagingSPEntry 26 }

  bwVMRSPNumSendListFailed OBJECT-TYPE
    SYNTAX      Counter32
    MAX-ACCESS  read-write
    STATUS      current
    DESCRIPTION 
        "This counter reflects the number of times an attempt to send a message to a distribution list failed for a service provider (NOT incremented in case of partial failures)"
    ::= { bwVoiceMessagingSPEntry 27 }

  bwVPSPGreetingRecorded OBJECT-TYPE
    SYNTAX      Counter32
    MAX-ACCESS  read-write
    STATUS      current
    DESCRIPTION 
        "Number of times a user recorded a branded Voice Messaging greeting for a given service provider"
    ::= { bwVoiceMessagingSPEntry 28 }

  bwVMSPGreetingRecorded OBJECT-TYPE
    SYNTAX      Counter32
    MAX-ACCESS  read-write
    STATUS      current
    DESCRIPTION 
        "Number of times a user recorded a branded Voice Portal greeting for a given service provider"
    ::= { bwVoiceMessagingSPEntry 29 }

  bwVPCSPCall OBJECT-TYPE
    SYNTAX      Counter32
    MAX-ACCESS  read-write
    STATUS      current
    DESCRIPTION 
        "Number of times a user from a specific service provider initiated a call with Voice Portal Calling"
    ::= { bwVoiceMessagingSPEntry 30 }

  bwSPMultiMediaMsgDeposit OBJECT-TYPE
    SYNTAX      Counter32
    MAX-ACCESS  read-write
    STATUS      current
    DESCRIPTION 
        "Number of times a user has received a multimedia message for a given service provider"
    ::= { bwVoiceMessagingSPEntry 31 }

  bwVMSPMultiMediaGreetingRecorded OBJECT-TYPE
    SYNTAX      Counter32
    MAX-ACCESS  read-write
    STATUS      current
    DESCRIPTION 
        "Number of time a user has recorded a multimedia message via the Voice Portal for a given service provider"
    ::= { bwVoiceMessagingSPEntry 32 }

  bwAutoAttendantSPMultiMediaPromptRecorded OBJECT-TYPE
    SYNTAX      Counter32
    MAX-ACCESS  read-write
    STATUS      current
    DESCRIPTION 
        "Number of times an administrator has recorded an AA prompt via the Voice Portal for a given service provider"
    ::= { bwVoiceMessagingSPEntry 33 }

  bwMessagingSPQuery OBJECT-TYPE
    SYNTAX      Counter32
    MAX-ACCESS  read-write
    STATUS      current
    DESCRIPTION 
        "This counter is incremented whenever a request for remote user mailbox information is sent out for a given service provider."
    ::= { bwVoiceMessagingSPEntry 34 }

  bwMessagingSPQueryNoUser OBJECT-TYPE
    SYNTAX      Counter32
    MAX-ACCESS  read-write
    STATUS      current
    DESCRIPTION 
        "This counter is incremented whenever a request for remote user mailbox information results in a user not found error for a given service provider."
    ::= { bwVoiceMessagingSPEntry 35 }

  bwMessagingSPQueryNoMailbox OBJECT-TYPE
    SYNTAX      Counter32
    MAX-ACCESS  read-write
    STATUS      current
    DESCRIPTION 
        "This counter is incremented whenever a request for remote user mailbox information results in an error because the remote mailbox is disabled, full, or not configured for a given service provider."
    ::= { bwVoiceMessagingSPEntry 36 }

  bwVPSPNumAAHolidayGreetingRecorded OBJECT-TYPE
    SYNTAX      Counter32
    MAX-ACCESS  read-write
    STATUS      current
    DESCRIPTION 
        "Number of times a user recorded an Auto Attendant Holiday greeting for a given service provider."
-- @feature:154400
    ::= { bwVoiceMessagingSPEntry 37 }

  bwVMRNumComposeSendListAttempts OBJECT-TYPE
    SYNTAX      Counter32
    MAX-ACCESS  read-write
    STATUS      current
    DESCRIPTION 
        "This counter reflects the number of times a composed message is sent to a distribution list"
    ::= { voiceMessaging 24 }

  bwVMRNumForwardSendListAttempts OBJECT-TYPE
    SYNTAX      Counter32
    MAX-ACCESS  read-write
    STATUS      current
    DESCRIPTION 
        "This counter reflects the number of times a forwarded message is sent to a distribution list"
    ::= { voiceMessaging 25 }

  bwVMRNumSendListFailed OBJECT-TYPE
    SYNTAX      Counter32
    MAX-ACCESS  read-write
    STATUS      current
    DESCRIPTION 
        "This counter reflects the number of times an attempt to send a message to a distribution list has failed (NOT incremented in case of partial failures)"
    ::= { voiceMessaging 26 }

  bwVPGreetingRecorded OBJECT-TYPE
    SYNTAX      Counter32
    MAX-ACCESS  read-write
    STATUS      current
    DESCRIPTION 
        "Number of times a user recorded a branded Voice Portal greeting"
    ::= { voiceMessaging 27 }

  bwVMGreetingRecorded OBJECT-TYPE
    SYNTAX      Counter32
    MAX-ACCESS  read-write
    STATUS      current
    DESCRIPTION 
        "Number of times a user recorded a branded Voice Messaging greeting"
    ::= { voiceMessaging 28 }

  bwVoiceMessagingGroupTable OBJECT-TYPE
    SYNTAX      SEQUENCE OF BwVoiceMessagingGroupEntry
    MAX-ACCESS  not-accessible
    STATUS      current
    DESCRIPTION 
        "This table contains the counters for Voice Messaging service measurements for groups"
    ::= { voiceMessaging 29 }

  bwVoiceMessagingGroupEntry OBJECT-TYPE
    SYNTAX      BwVoiceMessagingGroupEntry
    MAX-ACCESS  not-accessible
    STATUS      current
    DESCRIPTION 
        "This row contains the counters for Voice Messaging service measurements for a group"
    INDEX       { bwVoiceMessagingGroupIndex }
    ::= { bwVoiceMessagingGroupTable 1 }

  BwVoiceMessagingGroupEntry ::= SEQUENCE {
    bwVoiceMessagingGroupIndex                      Unsigned32,
    bwVoiceMessagingGroupID                         DisplayString,
    bwVMGroupNumBusyGreetingsPlayed                 Counter32,
    bwVMGroupNumNoAnswerGreetingsPlayed             Counter32,
    bwVMGroupNumMessagesLeft                        Counter32,
    bwVMRGroupNumBusyGreetingsRecorded              Counter32,
    bwVMRGroupNumNoAnswerGreetingsRecorded          Counter32,
    bwVMRGroupNumPersonalizedNamesRecorded          Counter32,
    bwVMRGroupNumLoginAttempts                      Counter32,
    bwVMRGroupNumLoginFailures                      Counter32,
    bwVMRGroupNumComposeSendAttempts                Counter32,
    bwVMRGroupNumComposeSendGroupAttempts           Counter32,
    bwVMRGroupNumForwardSendAttempts                Counter32,
    bwVMRGroupNumForwardSendGroupAttempts           Counter32,
    bwVMRGroupNumReplySendAttempts                  Counter32,
    bwVMRGroupNumSendFailed                         Counter32,
    bwVMRGroupNumSendGroupFailed                    Counter32,
    bwVMRGroupDeleteAllMsgsAttempts                 Counter32,
    bwVMRGroupCallBackAttempts                      Counter32,
    bwVPGroupNumAABusHoursGreetingRecorded          Counter32,
    bwVPGroupNumAAAfterHoursGreetingRecorded        Counter32,
    bwVPGroupNumCFADestinationChanged               Counter32,
    bwVPGroupNumPasscodeChanged                     Counter32,
    bwVMRGroupNumComposeSendListAttempts            Counter32,
    bwVMRGroupNumForwardSendListAttempts            Counter32,
    bwVMRGroupNumSendListFailed                     Counter32,
    bwVPGroupGreetingRecorded                       Counter32,
    bwVMGroupGreetingRecorded                       Counter32,
    bwVPCGroupCall                                  Counter32,
    bwGroupMultiMediaMsgDeposit                     Counter32,
    bwVMGroupMultiMediaGreetingRecorded             Counter32,
    bwAutoAttendantGroupMultiMediaPromptRecorded    Counter32,
    bwMessagingGroupQuery                           Counter32,
    bwMessagingGroupQueryNoUser                     Counter32,
    bwMessagingGroupQueryNoMailbox                  Counter32,
    bwVPGroupNumAAHolidayGreetingRecorded           Counter32
  }

  bwVoiceMessagingGroupIndex OBJECT-TYPE
    SYNTAX      Unsigned32
    MAX-ACCESS  read-only
    STATUS      current
    DESCRIPTION 
        "This integer represents the a group index in the system"
    ::= { bwVoiceMessagingGroupEntry 1 }

  bwVoiceMessagingGroupID OBJECT-TYPE
    SYNTAX      DisplayString
    MAX-ACCESS  read-only
    STATUS      current
    DESCRIPTION 
        "This string represents a group ID"
    ::= { bwVoiceMessagingGroupEntry 2 }

  bwVMGroupNumBusyGreetingsPlayed OBJECT-TYPE
    SYNTAX      Counter32
    MAX-ACCESS  read-write
    STATUS      current
    DESCRIPTION 
        "This counter reflects the number of times a busy greeting is played to a caller by a group"
    ::= { bwVoiceMessagingGroupEntry 3 }

  bwVMGroupNumNoAnswerGreetingsPlayed OBJECT-TYPE
    SYNTAX      Counter32
    MAX-ACCESS  read-write
    STATUS      current
    DESCRIPTION 
        "This counter reflects the number of times a no answer greeting is played by a group"
    ::= { bwVoiceMessagingGroupEntry 4 }

  bwVMGroupNumMessagesLeft OBJECT-TYPE
    SYNTAX      Counter32
    MAX-ACCESS  read-write
    STATUS      current
    DESCRIPTION 
        "This counter reflects the number of times a voice message is recorded by a group"
    ::= { bwVoiceMessagingGroupEntry 5 }

  bwVMRGroupNumBusyGreetingsRecorded OBJECT-TYPE
    SYNTAX      Counter32
    MAX-ACCESS  read-write
    STATUS      current
    DESCRIPTION 
        "This counter reflects the number of times a busy greeting is recorded over the phone by a group"
    ::= { bwVoiceMessagingGroupEntry 6 }

  bwVMRGroupNumNoAnswerGreetingsRecorded OBJECT-TYPE
    SYNTAX      Counter32
    MAX-ACCESS  read-write
    STATUS      current
    DESCRIPTION 
        "This counter reflects the number of times a no answer greeting is recorded over the phone by a group"
    ::= { bwVoiceMessagingGroupEntry 7 }

  bwVMRGroupNumPersonalizedNamesRecorded OBJECT-TYPE
    SYNTAX      Counter32
    MAX-ACCESS  read-write
    STATUS      current
    DESCRIPTION 
        "This counter reflects the number of times a personalized name greeting is recorded over the phone by a group"
    ::= { bwVoiceMessagingGroupEntry 8 }

  bwVMRGroupNumLoginAttempts OBJECT-TYPE
    SYNTAX      Counter32
    MAX-ACCESS  read-write
    STATUS      current
    DESCRIPTION 
        "This counter reflects the number of times a user attempts a login over the phone by a group"
    ::= { bwVoiceMessagingGroupEntry 9 }

  bwVMRGroupNumLoginFailures OBJECT-TYPE
    SYNTAX      Counter32
    MAX-ACCESS  read-write
    STATUS      current
    DESCRIPTION 
        "This counter reflects the number of times a user login attempt fails by a group"
    ::= { bwVoiceMessagingGroupEntry 10 }

  bwVMRGroupNumComposeSendAttempts OBJECT-TYPE
    SYNTAX      Counter32
    MAX-ACCESS  read-write
    STATUS      current
    DESCRIPTION 
        "This counter reflects the number of times a composed message is sent to a user by a group"
    ::= { bwVoiceMessagingGroupEntry 11 }

  bwVMRGroupNumComposeSendGroupAttempts OBJECT-TYPE
    SYNTAX      Counter32
    MAX-ACCESS  read-write
    STATUS      current
    DESCRIPTION 
        "This counter reflects the number of times a composed message is sent to a group by a group"
    ::= { bwVoiceMessagingGroupEntry 12 }

  bwVMRGroupNumForwardSendAttempts OBJECT-TYPE
    SYNTAX      Counter32
    MAX-ACCESS  read-write
    STATUS      current
    DESCRIPTION 
        "This counter reflects the number of times a forwarded message is sent to a user by a group"
    ::= { bwVoiceMessagingGroupEntry 13 }

  bwVMRGroupNumForwardSendGroupAttempts OBJECT-TYPE
    SYNTAX      Counter32
    MAX-ACCESS  read-write
    STATUS      current
    DESCRIPTION 
        "This counter reflects the number of times a forwarded message is sent to a group by a group"
    ::= { bwVoiceMessagingGroupEntry 14 }

  bwVMRGroupNumReplySendAttempts OBJECT-TYPE
    SYNTAX      Counter32
    MAX-ACCESS  read-write
    STATUS      current
    DESCRIPTION 
        "This counter reflects the number of times a message reply is sent by a group"
    ::= { bwVoiceMessagingGroupEntry 15 }

  bwVMRGroupNumSendFailed OBJECT-TYPE
    SYNTAX      Counter32
    MAX-ACCESS  read-write
    STATUS      current
    DESCRIPTION 
        "This counter reflects the number of times an attempt to send a message to a user failed by a group"
    ::= { bwVoiceMessagingGroupEntry 16 }

  bwVMRGroupNumSendGroupFailed OBJECT-TYPE
    SYNTAX      Counter32
    MAX-ACCESS  read-write
    STATUS      current
    DESCRIPTION 
        "This counter reflects the number of times an attempt to send a message to a group failed by a group"
    ::= { bwVoiceMessagingGroupEntry 17 }

  bwVMRGroupDeleteAllMsgsAttempts OBJECT-TYPE
    SYNTAX      Counter32
    MAX-ACCESS  read-write
    STATUS      current
    DESCRIPTION 
        "This counter reflects the number of times a user attempts to delete all messages by a group"
    ::= { bwVoiceMessagingGroupEntry 18 }

  bwVMRGroupCallBackAttempts OBJECT-TYPE
    SYNTAX      Counter32
    MAX-ACCESS  read-write
    STATUS      current
    DESCRIPTION 
        "This counter reflects the number of times a user attempts to callback the caller by a group"
    ::= { bwVoiceMessagingGroupEntry 19 }

  bwVPGroupNumAABusHoursGreetingRecorded OBJECT-TYPE
    SYNTAX      Counter32
    MAX-ACCESS  read-write
    STATUS      current
    DESCRIPTION 
        "This counter reflects the number of times an AA business hours greeting is recorded over the phone by a group"
    ::= { bwVoiceMessagingGroupEntry 21 }

  bwVPGroupNumAAAfterHoursGreetingRecorded OBJECT-TYPE
    SYNTAX      Counter32
    MAX-ACCESS  read-write
    STATUS      current
    DESCRIPTION 
        "This counter reflects the number of times an AA after hours greeting is recorded over the phone by a group"
    ::= { bwVoiceMessagingGroupEntry 22 }

  bwVPGroupNumCFADestinationChanged OBJECT-TYPE
    SYNTAX      Counter32
    MAX-ACCESS  read-write
    STATUS      current
    DESCRIPTION 
        "This counter reflects the number of times a CFA destination is changed over the phone by a group"
    ::= { bwVoiceMessagingGroupEntry 23 }

  bwVPGroupNumPasscodeChanged OBJECT-TYPE
    SYNTAX      Counter32
    MAX-ACCESS  read-write
    STATUS      current
    DESCRIPTION 
        "This counter reflects the number of times a Voice Portal is changed over the phone by a group"
    ::= { bwVoiceMessagingGroupEntry 24 }

  bwVMRGroupNumComposeSendListAttempts OBJECT-TYPE
    SYNTAX      Counter32
    MAX-ACCESS  read-write
    STATUS      current
    DESCRIPTION 
        "This counter reflects the number of times a composed message is sent to a distribution list by a group"
    ::= { bwVoiceMessagingGroupEntry 25 }

  bwVMRGroupNumForwardSendListAttempts OBJECT-TYPE
    SYNTAX      Counter32
    MAX-ACCESS  read-write
    STATUS      current
    DESCRIPTION 
        "This counter reflects the number of times a forwarded message is sent to a distribution list by a group"
    ::= { bwVoiceMessagingGroupEntry 26 }

  bwVMRGroupNumSendListFailed OBJECT-TYPE
    SYNTAX      Counter32
    MAX-ACCESS  read-write
    STATUS      current
    DESCRIPTION 
        "This counter reflects the number of times an attempt to send a message to a distribution list failed for a group (NOT incremented in case of partial failures)"
    ::= { bwVoiceMessagingGroupEntry 27 }

  bwVPGroupGreetingRecorded OBJECT-TYPE
    SYNTAX      Counter32
    MAX-ACCESS  read-write
    STATUS      current
    DESCRIPTION 
        "Number of times a user recorded a branded Voice Messaging greeting for a given group"
    ::= { bwVoiceMessagingGroupEntry 28 }

  bwVMGroupGreetingRecorded OBJECT-TYPE
    SYNTAX      Counter32
    MAX-ACCESS  read-write
    STATUS      current
    DESCRIPTION 
        "Number of times a user recorded a branded Voice Portal greeting for a given group"
    ::= { bwVoiceMessagingGroupEntry 29 }

  bwVPCGroupCall OBJECT-TYPE
    SYNTAX      Counter32
    MAX-ACCESS  read-write
    STATUS      current
    DESCRIPTION 
        "Number of times a user from a specific group initiated a call with Voice Portal Calling"
    ::= { bwVoiceMessagingGroupEntry 30 }

  bwGroupMultiMediaMsgDeposit OBJECT-TYPE
    SYNTAX      Counter32
    MAX-ACCESS  read-write
    STATUS      current
    DESCRIPTION 
        "Number of times a user has received a multimedia message for a given group"
    ::= { bwVoiceMessagingGroupEntry 31 }

  bwVMGroupMultiMediaGreetingRecorded OBJECT-TYPE
    SYNTAX      Counter32
    MAX-ACCESS  read-write
    STATUS      current
    DESCRIPTION 
        "Number of time a user has recorded a multimedia message via the Voice Portal for a given group"
    ::= { bwVoiceMessagingGroupEntry 32 }

  bwAutoAttendantGroupMultiMediaPromptRecorded OBJECT-TYPE
    SYNTAX      Counter32
    MAX-ACCESS  read-write
    STATUS      current
    DESCRIPTION 
        "Number of times an administrator has recorded an AA prompt via the Voice Portal for a given group"
    ::= { bwVoiceMessagingGroupEntry 33 }

  bwMessagingGroupQuery OBJECT-TYPE
    SYNTAX      Counter32
    MAX-ACCESS  read-write
    STATUS      current
    DESCRIPTION 
        "This counter is incremented whenever a request for remote user mailbox information is sent out for a given service provider."
    ::= { bwVoiceMessagingGroupEntry 34 }

  bwMessagingGroupQueryNoUser OBJECT-TYPE
    SYNTAX      Counter32
    MAX-ACCESS  read-write
    STATUS      current
    DESCRIPTION 
        "This counter is incremented whenever a request for remote user mailbox information results in a user not found error for a given service provider."
    ::= { bwVoiceMessagingGroupEntry 35 }

  bwMessagingGroupQueryNoMailbox OBJECT-TYPE
    SYNTAX      Counter32
    MAX-ACCESS  read-write
    STATUS      current
    DESCRIPTION 
        "This counter is incremented whenever a request for remote user mailbox information results in an error because the remote mailbox is disabled, full, or not configured for a given service provider."
    ::= { bwVoiceMessagingGroupEntry 36 }

  bwVPGroupNumAAHolidayGreetingRecorded OBJECT-TYPE
    SYNTAX      Counter32
    MAX-ACCESS  read-write
    STATUS      current
    DESCRIPTION 
        "Number of times a user recorded a Auto Attendant Holiday greeting for a given group."
-- @feature:154400
    ::= { bwVoiceMessagingGroupEntry 37 }

  bwVPCCall OBJECT-TYPE
    SYNTAX      Counter32
    MAX-ACCESS  read-write
    STATUS      current
    DESCRIPTION 
        "Number of times a user initiated a call with Voice Portal Calling"
    ::= { voiceMessaging 30 }

  bwMultiMediaMsgDeposit OBJECT-TYPE
    SYNTAX      Counter32
    MAX-ACCESS  read-write
    STATUS      current
    DESCRIPTION 
        "Number of times a user has received a multimedia message"
    ::= { voiceMessaging 31 }

  bwVMMultiMediaGreetingRecorded OBJECT-TYPE
    SYNTAX      Counter32
    MAX-ACCESS  read-write
    STATUS      current
    DESCRIPTION 
        "Number of time a user has recorded a multimedia message via the Voice Portal"
    ::= { voiceMessaging 32 }

  bwAutoAttendantMultiMediaPromptRecorded OBJECT-TYPE
    SYNTAX      Counter32
    MAX-ACCESS  read-write
    STATUS      current
    DESCRIPTION 
        "Number of times an administrator has recorded an AA prompt via the Voice Portal"
    ::= { voiceMessaging 33 }

  bwMessagingQuery OBJECT-TYPE
    SYNTAX      Counter32
    MAX-ACCESS  read-write
    STATUS      current
    DESCRIPTION 
        "This counter is incremented whenever a request for remote user mailbox information is sent out."
    ::= { voiceMessaging 34 }

  bwMessagingQueryNoUser OBJECT-TYPE
    SYNTAX      Counter32
    MAX-ACCESS  read-write
    STATUS      current
    DESCRIPTION 
        "This counter is incremented whenever a request for remote user mailbox information results in a user not found error."
    ::= { voiceMessaging 35 }

  bwMessagingQueryNoMailbox OBJECT-TYPE
    SYNTAX      Counter32
    MAX-ACCESS  read-write
    STATUS      current
    DESCRIPTION 
        "This counter is incremented whenever a request for remote user mailbox information results in an error because the remote mailbox is disabled, full, or not configured."
    ::= { voiceMessaging 36 }

  bwVPNumAAHolidayGreetingRecorded OBJECT-TYPE
    SYNTAX      Counter32
    MAX-ACCESS  read-write
    STATUS      current
    DESCRIPTION 
        "Number of times a user recorded a Auto Attendant Holiday greeting."
-- @feature:154400
    ::= { voiceMessaging 37 }

  bwSVPNumLoginAttempts OBJECT-TYPE
    SYNTAX      Counter32
    MAX-ACCESS  read-write
    STATUS      current
    DESCRIPTION 
        "Number of times a user attempts a login to a system voice portal over the phone."
-- @feature:142137
    ::= { voiceMessaging 38 }

  bwSVPNumLoginFailures OBJECT-TYPE
    SYNTAX      Counter32
    MAX-ACCESS  read-write
    STATUS      current
    DESCRIPTION 
        "Number of times a user fails to login to a system voice portal over the phone."
-- @feature:142137
    ::= { voiceMessaging 39 }
    
  bwVMmp3recordFail OBJECT-TYPE
    SYNTAX      Counter32
    MAX-ACCESS  read-write
    STATUS      current
    DESCRIPTION 
        "Number of times a request to record an MP3 voice message failed due to an insufficient number of encoders."
-- @feature:190717
    ::= { voiceMessaging 40 }    
    
  bwVMmp3playbackFail OBJECT-TYPE
    SYNTAX      Counter32
    MAX-ACCESS  read-write
    STATUS      current
    DESCRIPTION 
        "Number of times a request to play back an MP3 voice message failed due to an insufficient number of MP3 decoders."
-- @feature:190717
    ::= { voiceMessaging 41 }     

-- Services :: seriesCompletion ...........................................

  bwSeriesCompletionNumAttempts OBJECT-TYPE
    SYNTAX      Counter32
    MAX-ACCESS  read-write
    STATUS      current
    DESCRIPTION 
        "incremented whenever the series completion service forwards a call to the next user in the list"
    ::= { seriesCompletion 1 }

  bwSeriesCompletionNumBusy OBJECT-TYPE
    SYNTAX      Counter32
    MAX-ACCESS  read-write
    STATUS      current
    DESCRIPTION 
        "incremented whenever the series completion service reaches the end of the forwarding list, and no users are available"
    ::= { seriesCompletion 2 }

  bwSeriesCompletionSPTable OBJECT-TYPE
    SYNTAX      SEQUENCE OF BwSeriesCompletionSPEntry
    MAX-ACCESS  not-accessible
    STATUS      current
    DESCRIPTION 
        "This table contains the counters for Series Completion service measurements for service providers"
    ::= { seriesCompletion 3 }

  bwSeriesCompletionSPEntry OBJECT-TYPE
    SYNTAX      BwSeriesCompletionSPEntry
    MAX-ACCESS  not-accessible
    STATUS      current
    DESCRIPTION 
        "This row contains the counters for Series Completion service measurements for a service provider"
    INDEX       { bwSeriesCompletionSPIndex }
    ::= { bwSeriesCompletionSPTable 1 }

  BwSeriesCompletionSPEntry ::= SEQUENCE {
    bwSeriesCompletionSPIndex           Unsigned32,
    bwSeriesCompletionSPID              DisplayString,
    bwSeriesCompletionSPNumAttempts     Counter32,
    bwSeriesCompletionSPNumBusy         Counter32
  }

  bwSeriesCompletionSPIndex OBJECT-TYPE
    SYNTAX      Unsigned32
    MAX-ACCESS  read-only
    STATUS      current
    DESCRIPTION 
        "This integer represents the a service provider index in the system"
    ::= { bwSeriesCompletionSPEntry 1 }

  bwSeriesCompletionSPID OBJECT-TYPE
    SYNTAX      DisplayString
    MAX-ACCESS  read-only
    STATUS      current
    DESCRIPTION 
        "This string represents a service provider ID"
    ::= { bwSeriesCompletionSPEntry 2 }

  bwSeriesCompletionSPNumAttempts OBJECT-TYPE
    SYNTAX      Counter32
    MAX-ACCESS  read-write
    STATUS      current
    DESCRIPTION 
        "This counter reflects the number of times the series completion service forwards a call to the next user in the list by a service provider"
    ::= { bwSeriesCompletionSPEntry 3 }

  bwSeriesCompletionSPNumBusy OBJECT-TYPE
    SYNTAX      Counter32
    MAX-ACCESS  read-write
    STATUS      current
    DESCRIPTION 
        "This counter reflects the number of times the series completion service reaches the end of the forwarding list, and no users are available by a service provider"
    ::= { bwSeriesCompletionSPEntry 4 }

  bwSeriesCompletionGroupTable OBJECT-TYPE
    SYNTAX      SEQUENCE OF BwSeriesCompletionGroupEntry
    MAX-ACCESS  not-accessible
    STATUS      current
    DESCRIPTION 
        "This table contains the counters for Series Completion service measurements for groups"
    ::= { seriesCompletion 4 }

  bwSeriesCompletionGroupEntry OBJECT-TYPE
    SYNTAX      BwSeriesCompletionGroupEntry
    MAX-ACCESS  not-accessible
    STATUS      current
    DESCRIPTION 
        "This row contains the counters for Series Completion service measurements for a group"
    INDEX       { bwSeriesCompletionGroupIndex }
    ::= { bwSeriesCompletionGroupTable 1 }

  BwSeriesCompletionGroupEntry ::= SEQUENCE {
    bwSeriesCompletionGroupIndex        Unsigned32,
    bwSeriesCompletionGroupID           DisplayString,
    bwSeriesCompletionGroupNumAttempts  Counter32,
    bwSeriesCompletionGroupNumBusy      Counter32
  }

  bwSeriesCompletionGroupIndex OBJECT-TYPE
    SYNTAX      Unsigned32
    MAX-ACCESS  read-only
    STATUS      current
    DESCRIPTION 
        "This integer represents the a group index in the system"
    ::= { bwSeriesCompletionGroupEntry 1 }

  bwSeriesCompletionGroupID OBJECT-TYPE
    SYNTAX      DisplayString
    MAX-ACCESS  read-only
    STATUS      current
    DESCRIPTION 
        "This string represents a group ID"
    ::= { bwSeriesCompletionGroupEntry 2 }

  bwSeriesCompletionGroupNumAttempts OBJECT-TYPE
    SYNTAX      Counter32
    MAX-ACCESS  read-write
    STATUS      current
    DESCRIPTION 
        "This counter reflects the number of times the series completion service forwards a call to the next user in the list by a group"
    ::= { bwSeriesCompletionGroupEntry 3 }

  bwSeriesCompletionGroupNumBusy OBJECT-TYPE
    SYNTAX      Counter32
    MAX-ACCESS  read-write
    STATUS      current
    DESCRIPTION 
        "This counter reflects the number of times the series completion service reaches the end of the forwarding list, and no users are available by a group"
    ::= { bwSeriesCompletionGroupEntry 4 }

  bwInterceptUserOriginationInvocations OBJECT-TYPE
    SYNTAX      Counter32
    MAX-ACCESS  read-write
    STATUS      current
    DESCRIPTION 
        "incremented whenever the intercept user service blocks an originating call"
    ::= { intercept 1 }

  bwInterceptGroupOriginationInvocations OBJECT-TYPE
    SYNTAX      Counter32
    MAX-ACCESS  read-write
    STATUS      current
    DESCRIPTION 
        "incremented whenever the intercept group service blocks an originating call"
    ::= { intercept 2 }

  bwInterceptUserTerminationInvocations OBJECT-TYPE
    SYNTAX      Counter32
    MAX-ACCESS  read-write
    STATUS      current
    DESCRIPTION 
        "incremented whenever the intercept user service blocks a terminating call"
    ::= { intercept 3 }

  bwInterceptGroupTerminationInvocations OBJECT-TYPE
    SYNTAX      Counter32
    MAX-ACCESS  read-write
    STATUS      current
    DESCRIPTION 
        "incremented whenever the intercept group service blocks a terminating call"
    ::= { intercept 4 }

  bwInterceptTransfers OBJECT-TYPE
    SYNTAX      Counter32
    MAX-ACCESS  read-write
    STATUS      current
    DESCRIPTION 
        "incremented whenever the intercept service transfers a call"
    ::= { intercept 5 }

  bwInterceptSPTable OBJECT-TYPE
    SYNTAX      SEQUENCE OF BwInterceptSPEntry
    MAX-ACCESS  not-accessible
    STATUS      current
    DESCRIPTION 
        "This table contains the counters for Intercept service measurements for service providers"
    ::= { intercept 6 }

  bwInterceptSPEntry OBJECT-TYPE
    SYNTAX      BwInterceptSPEntry
    MAX-ACCESS  not-accessible
    STATUS      current
    DESCRIPTION 
        "This row contains the counters for Intercept service measurements for a service provider"
    INDEX       { bwInterceptSPIndex }
    ::= { bwInterceptSPTable 1 }

  BwInterceptSPEntry ::= SEQUENCE {
    bwInterceptSPIndex                          Unsigned32,
    bwInterceptSPID                             DisplayString,
    bwInterceptSPUserOriginationInvocations     Counter32,
    bwInterceptSPGroupOriginationInvocations    Counter32,
    bwInterceptSPUserTerminationInvocations     Counter32,
    bwInterceptSPGroupTerminationInvocations    Counter32,
    bwInterceptSPTransfers                      Counter32
  }

  bwInterceptSPIndex OBJECT-TYPE
    SYNTAX      Unsigned32
    MAX-ACCESS  read-only
    STATUS      current
    DESCRIPTION 
        "This integer represents the a service provider index in the system"
    ::= { bwInterceptSPEntry 1 }

  bwInterceptSPID OBJECT-TYPE
    SYNTAX      DisplayString
    MAX-ACCESS  read-only
    STATUS      current
    DESCRIPTION 
        "This string represents a service provider ID"
    ::= { bwInterceptSPEntry 2 }

  bwInterceptSPUserOriginationInvocations OBJECT-TYPE
    SYNTAX      Counter32
    MAX-ACCESS  read-write
    STATUS      current
    DESCRIPTION 
        "This counter reflects the number of times the intercept user service blocks an originating call by a service provider"
    ::= { bwInterceptSPEntry 3 }

  bwInterceptSPGroupOriginationInvocations OBJECT-TYPE
    SYNTAX      Counter32
    MAX-ACCESS  read-write
    STATUS      current
    DESCRIPTION 
        "This counter reflects the number of times the intercept group service blocks an originating call by a service provider"
    ::= { bwInterceptSPEntry 4 }

  bwInterceptSPUserTerminationInvocations OBJECT-TYPE
    SYNTAX      Counter32
    MAX-ACCESS  read-write
    STATUS      current
    DESCRIPTION 
        "This counter reflects the number of times the intercept user service blocks a terminating call by a service provider"
    ::= { bwInterceptSPEntry 5 }

  bwInterceptSPGroupTerminationInvocations OBJECT-TYPE
    SYNTAX      Counter32
    MAX-ACCESS  read-write
    STATUS      current
    DESCRIPTION 
        "This counter reflects the number of times the intercept group service blocks a terminating call by a service provider"
    ::= { bwInterceptSPEntry 6 }

  bwInterceptSPTransfers OBJECT-TYPE
    SYNTAX      Counter32
    MAX-ACCESS  read-write
    STATUS      current
    DESCRIPTION 
        "This counter reflects the number of times the intercept service transfers a call by a service provider"
    ::= { bwInterceptSPEntry 7 }

  bwInterceptGroupTable OBJECT-TYPE
    SYNTAX      SEQUENCE OF BwInterceptGroupEntry
    MAX-ACCESS  not-accessible
    STATUS      current
    DESCRIPTION 
        "This table contains the counters for Intercept service measurements for groups"
    ::= { intercept 7 }

  bwInterceptGroupEntry OBJECT-TYPE
    SYNTAX      BwInterceptGroupEntry
    MAX-ACCESS  not-accessible
    STATUS      current
    DESCRIPTION 
        "This row contains the counters for Intercept service measurements for a service provider"
    INDEX       { bwInterceptGroupIndex }
    ::= { bwInterceptGroupTable 1 }

  BwInterceptGroupEntry ::= SEQUENCE {
    bwInterceptGroupIndex                           Unsigned32,
    bwInterceptGroupID                              DisplayString,
    bwInterceptGroupUserOriginationInvocations      Counter32,
    bwInterceptGroupGroupOriginationInvocations     Counter32,
    bwInterceptGroupUserTerminationInvocations      Counter32,
    bwInterceptGroupGroupTerminationInvocations     Counter32,
    bwInterceptGroupTransfers                       Counter32
  }

  bwInterceptGroupIndex OBJECT-TYPE
    SYNTAX      Unsigned32
    MAX-ACCESS  read-only
    STATUS      current
    DESCRIPTION 
        "This integer represents the a service provider index in the system"
    ::= { bwInterceptGroupEntry 1 }

  bwInterceptGroupID OBJECT-TYPE
    SYNTAX      DisplayString
    MAX-ACCESS  read-only
    STATUS      current
    DESCRIPTION 
        "This string represents a service provider ID"
    ::= { bwInterceptGroupEntry 2 }

  bwInterceptGroupUserOriginationInvocations OBJECT-TYPE
    SYNTAX      Counter32
    MAX-ACCESS  read-write
    STATUS      current
    DESCRIPTION 
        "This counter reflects the number of times the intercept user service blocks an originating call by a service provider"
    ::= { bwInterceptGroupEntry 3 }

  bwInterceptGroupGroupOriginationInvocations OBJECT-TYPE
    SYNTAX      Counter32
    MAX-ACCESS  read-write
    STATUS      current
    DESCRIPTION 
        "This counter reflects the number of times the intercept group service blocks an originating call by a service provider"
    ::= { bwInterceptGroupEntry 4 }

  bwInterceptGroupUserTerminationInvocations OBJECT-TYPE
    SYNTAX      Counter32
    MAX-ACCESS  read-write
    STATUS      current
    DESCRIPTION 
        "This counter reflects the number of times the intercept user service blocks a terminating call by a service provider"
    ::= { bwInterceptGroupEntry 5 }

  bwInterceptGroupGroupTerminationInvocations OBJECT-TYPE
    SYNTAX      Counter32
    MAX-ACCESS  read-write
    STATUS      current
    DESCRIPTION 
        "This counter reflects the number of times the intercept group service blocks a terminating call by a service provider"
    ::= { bwInterceptGroupEntry 6 }

  bwInterceptGroupTransfers OBJECT-TYPE
    SYNTAX      Counter32
    MAX-ACCESS  read-write
    STATUS      current
    DESCRIPTION 
        "This counter reflects the number of times the intercept service transfers a call by a service provider"
    ::= { bwInterceptGroupEntry 7 }

  bwICGroupPortLimitExceeded OBJECT-TYPE
    SYNTAX      Counter32
    MAX-ACCESS  read-write
    STATUS      current
    DESCRIPTION 
        "This statistics indicates that all instant conferencing ports allocated to a group are in use."
    ::= { instantConferencing 1 }

  bwICNumAttempts OBJECT-TYPE
    SYNTAX      Counter32
    MAX-ACCESS  read-write
    STATUS      current
    DESCRIPTION 
        "This statistics indicates the number of instant conferencing attempted"
    ::= { instantConferencing 2 }

  bwInstantConferencingSPTable OBJECT-TYPE
    SYNTAX      SEQUENCE OF BwInstantConferencingSPEntry
    MAX-ACCESS  not-accessible
    STATUS      current
    DESCRIPTION 
        "This table contains the counters for Instant Conferencing service measurements for service providers"
    ::= { instantConferencing 3 }

  bwInstantConferencingSPEntry OBJECT-TYPE
    SYNTAX      BwInstantConferencingSPEntry
    MAX-ACCESS  not-accessible
    STATUS      current
    DESCRIPTION 
        "This row contains the counters for Instant Conferencing service measurements for a service provider"
    INDEX       { bwInstantConferencingSPIndex }
    ::= { bwInstantConferencingSPTable 1 }

  BwInstantConferencingSPEntry ::= SEQUENCE {
    bwInstantConferencingSPIndex    Unsigned32,
    bwInstantConferencingSPID       DisplayString,
    bwICSPGroupPortLimitExceeded    Counter32,
    bwICSPNumAttempts               Counter32,
    bwICSPOutdialNumAttempts        Counter32
  }

  bwInstantConferencingSPIndex OBJECT-TYPE
    SYNTAX      Unsigned32
    MAX-ACCESS  read-only
    STATUS      current
    DESCRIPTION 
        "This integer represents the a service provider index in the system"
    ::= { bwInstantConferencingSPEntry 1 }

  bwInstantConferencingSPID OBJECT-TYPE
    SYNTAX      DisplayString
    MAX-ACCESS  read-only
    STATUS      current
    DESCRIPTION 
        "This string represents a service provider ID"
    ::= { bwInstantConferencingSPEntry 2 }

  bwICSPGroupPortLimitExceeded OBJECT-TYPE
    SYNTAX      Counter32
    MAX-ACCESS  read-write
    STATUS      current
    DESCRIPTION 
        "This statistics indicates that all instant conferencing ports allocated to a group are in use by a service provider"
    ::= { bwInstantConferencingSPEntry 3 }

  bwICSPNumAttempts OBJECT-TYPE
    SYNTAX      Counter32
    MAX-ACCESS  read-write
    STATUS      current
    DESCRIPTION 
        "This statistics indicates the number of instant conferencing attempted by a service provider"
    ::= { bwInstantConferencingSPEntry 4 }

  bwICSPOutdialNumAttempts OBJECT-TYPE
    SYNTAX      Counter32
    MAX-ACCESS  read-write
    STATUS      current
    DESCRIPTION 
        "This counter is incremented each time an outcall attempt is processed by a conference bridge for a given service provider"
    ::= { bwInstantConferencingSPEntry 5 }

  bwInstantConferencingGroupTable OBJECT-TYPE
    SYNTAX      SEQUENCE OF BwInstantConferencingGroupEntry
    MAX-ACCESS  not-accessible
    STATUS      current
    DESCRIPTION 
        "This table contains the counters for Instant Conferencing service measurements for groups"
    ::= { instantConferencing 4 }

  bwInstantConferencingGroupEntry OBJECT-TYPE
    SYNTAX      BwInstantConferencingGroupEntry
    MAX-ACCESS  not-accessible
    STATUS      current
    DESCRIPTION 
        "This row contains the counters for Instant Conferencing service measurements for a group"
    INDEX       { bwInstantConferencingGroupIndex }
    ::= { bwInstantConferencingGroupTable 1 }

  BwInstantConferencingGroupEntry ::= SEQUENCE {
    bwInstantConferencingGroupIndex     Unsigned32,
    bwInstantConferencingGroupID        DisplayString,
    bwICGroupGroupPortLimitExceeded     Counter32,
    bwICGroupNumAttempts                Counter32,
    bwICGroupOutdialNumAttempts         Counter32
  }

  bwInstantConferencingGroupIndex OBJECT-TYPE
    SYNTAX      Unsigned32
    MAX-ACCESS  read-only
    STATUS      current
    DESCRIPTION 
        "This integer represents the a group index in the system"
    ::= { bwInstantConferencingGroupEntry 1 }

  bwInstantConferencingGroupID OBJECT-TYPE
    SYNTAX      DisplayString
    MAX-ACCESS  read-only
    STATUS      current
    DESCRIPTION 
        "This string represents a group ID"
    ::= { bwInstantConferencingGroupEntry 2 }

  bwICGroupGroupPortLimitExceeded OBJECT-TYPE
    SYNTAX      Counter32
    MAX-ACCESS  read-write
    STATUS      current
    DESCRIPTION 
        "This statistics indicates that all instant conferencing ports allocated to a group are in use by a group"
    ::= { bwInstantConferencingGroupEntry 3 }

  bwICGroupNumAttempts OBJECT-TYPE
    SYNTAX      Counter32
    MAX-ACCESS  read-write
    STATUS      current
    DESCRIPTION 
        "This statistics indicates the number of instant conferencing attempted by a group"
    ::= { bwInstantConferencingGroupEntry 4 }

  bwICGroupOutdialNumAttempts OBJECT-TYPE
    SYNTAX      Counter32
    MAX-ACCESS  read-write
    STATUS      current
    DESCRIPTION 
        "This counter is incremented each time an outcall attempt is processed by a conference bridge for a given group"
    ::= { bwInstantConferencingGroupEntry 5 }

  bwInstantConferencingBridgeTable OBJECT-TYPE
    SYNTAX      SEQUENCE OF BwInstantConferencingBridgeEntry
    MAX-ACCESS  not-accessible
    STATUS      current
    DESCRIPTION 
        "This table is used to track the usage against all bridges defined in the system"
    ::= { instantConferencing 5 }

  bwInstantConferencingBridgeEntry OBJECT-TYPE
    SYNTAX      BwInstantConferencingBridgeEntry
    MAX-ACCESS  not-accessible
    STATUS      current
    DESCRIPTION 
        "This row contains the counters for Instant Conferencing service measurements for a bridge"
    INDEX       { bwInstantConferencingBridgeIndex }
    ::= { bwInstantConferencingBridgeTable 1 }

  BwInstantConferencingBridgeEntry ::= SEQUENCE {
    bwInstantConferencingBridgeIndex            Unsigned32,
    bwInstantConferencingBridgeName             DisplayString,
    bwInstantConferencingBridgeGroupName        DisplayString,
    bwInstantConferencingCurrentUsage           Gauge32,
    bwInstantConferencingTodaysPeakUsage        Gauge32,
    bwInstantConferencingYesterdaysPeakUsage    Gauge32
  }

  bwInstantConferencingBridgeIndex OBJECT-TYPE
    SYNTAX      Unsigned32
    MAX-ACCESS  read-only
    STATUS      current
    DESCRIPTION 
        "This integer represents the a bridge index in the system"
    ::= { bwInstantConferencingBridgeEntry 1 }

  bwInstantConferencingBridgeName OBJECT-TYPE
    SYNTAX      DisplayString
    MAX-ACCESS  read-only
    STATUS      current
    DESCRIPTION 
        "The name of the conference bridge referenced by this index"
    ::= { bwInstantConferencingBridgeEntry 2 }

  bwInstantConferencingBridgeGroupName OBJECT-TYPE
    SYNTAX      DisplayString
    MAX-ACCESS  read-only
    STATUS      current
    DESCRIPTION 
        "The name of the group that owns the conference bridge referenced by this index"
    ::= { bwInstantConferencingBridgeEntry 3 }

  bwInstantConferencingCurrentUsage OBJECT-TYPE
    SYNTAX      Gauge32
    MAX-ACCESS  read-only
    STATUS      current
    DESCRIPTION 
        "The number of ports currently in use in this bridge"
    ::= { bwInstantConferencingBridgeEntry 4 }

  bwInstantConferencingTodaysPeakUsage OBJECT-TYPE
    SYNTAX      Gauge32
    MAX-ACCESS  read-only
    STATUS      current
    DESCRIPTION 
        "The maximum number of ports that were simultaneously in use for this bridge today"
    ::= { bwInstantConferencingBridgeEntry 5 }

  bwInstantConferencingYesterdaysPeakUsage OBJECT-TYPE
    SYNTAX      Gauge32
    MAX-ACCESS  read-only
    STATUS      current
    DESCRIPTION 
        "The maximum number of ports that were simultaneously in use for this bridge yesterday"
    ::= { bwInstantConferencingBridgeEntry 6 }

  bwICOutdialNumAttempts OBJECT-TYPE
    SYNTAX      Counter32
    MAX-ACCESS  read-write
    STATUS      current
    DESCRIPTION 
        "This counter is incremented each time an outcall attempt is processed by a conference bridge"
    ::= { instantConferencing 6 }

  bwCallingLineIDDeliveryBlockPerCallBlocks OBJECT-TYPE
    SYNTAX      Counter32
    MAX-ACCESS  read-write
    STATUS      current
    DESCRIPTION 
        "This counter reflects the number of times the per call calling line ID delivery block service is invoked."
    ::= { callingLineIDDeliveryBlock 1 }

  bwCallingLineIDDeliveryBlockSPTable OBJECT-TYPE
    SYNTAX      SEQUENCE OF BwCallingLineIDDeliveryBlockSPEntry
    MAX-ACCESS  not-accessible
    STATUS      current
    DESCRIPTION 
        "Table used to report the calling line id blocking statistics per service providers"
    ::= { callingLineIDDeliveryBlock 2 }

  bwCallingLineIDDeliveryBlockSPEntry OBJECT-TYPE
    SYNTAX      BwCallingLineIDDeliveryBlockSPEntry
    MAX-ACCESS  not-accessible
    STATUS      current
    DESCRIPTION 
        "This row contains the counters for the per call calling line ID delivery block service measurements for a service provider."
    INDEX       { bwCallingLineIDDeliveryBlockSPIndex }
    ::= { bwCallingLineIDDeliveryBlockSPTable 1 }

  BwCallingLineIDDeliveryBlockSPEntry ::= SEQUENCE {
    bwCallingLineIDDeliveryBlockSPIndex             Unsigned32,
    bwCallingLineIDDeliveryBlockSPID                DisplayString,
    bwCallingLineIDDeliveryBlockSPPerCallBlocks     Counter32,
    bwCallingLineIDDeliveryPerCallSP                Counter32
  }

  bwCallingLineIDDeliveryBlockSPIndex OBJECT-TYPE
    SYNTAX      Unsigned32
    MAX-ACCESS  read-only
    STATUS      current
    DESCRIPTION 
        "This integer represents the service provider index in the system."
    ::= { bwCallingLineIDDeliveryBlockSPEntry 1 }

  bwCallingLineIDDeliveryBlockSPID OBJECT-TYPE
    SYNTAX      DisplayString
    MAX-ACCESS  read-only
    STATUS      current
    DESCRIPTION 
        "This string represents a service provider ID"
    ::= { bwCallingLineIDDeliveryBlockSPEntry 2 }

  bwCallingLineIDDeliveryBlockSPPerCallBlocks OBJECT-TYPE
    SYNTAX      Counter32
    MAX-ACCESS  read-write
    STATUS      current
    DESCRIPTION 
        "This counter reflects the number of times the per call calling line ID delivery block service is invoked for this service provider."
    ::= { bwCallingLineIDDeliveryBlockSPEntry 3 }

  bwCallingLineIDDeliveryPerCallSP OBJECT-TYPE
    SYNTAX      Counter32
    MAX-ACCESS  read-write
    STATUS      current
    DESCRIPTION 
        "This counter reflects the number of times the calling line ID delivery per call service is invoked for this service provider."
    ::= { bwCallingLineIDDeliveryBlockSPEntry 4 }

  bwCallingLineIDDeliveryBlockGroupTable OBJECT-TYPE
    SYNTAX      SEQUENCE OF BwCallingLineIDDeliveryBlockGroupEntry
    MAX-ACCESS  not-accessible
    STATUS      current
    DESCRIPTION 
        "Table used to report the calling line id blocking statistics per groups"
    ::= { callingLineIDDeliveryBlock 3 }

  bwCallingLineIDDeliveryBlockGroupEntry OBJECT-TYPE
    SYNTAX      BwCallingLineIDDeliveryBlockGroupEntry
    MAX-ACCESS  not-accessible
    STATUS      current
    DESCRIPTION 
        "This row contains the counters for the per call calling line ID delivery block service measurements for a group."
    INDEX       { bwCallingLineIDDeliveryBlockGroupIndex }
    ::= { bwCallingLineIDDeliveryBlockGroupTable 1 }

  BwCallingLineIDDeliveryBlockGroupEntry ::= SEQUENCE {
    bwCallingLineIDDeliveryBlockGroupIndex          Unsigned32,
    bwCallingLineIDDeliveryBlockGroupID             DisplayString,
    bwCallingLineIDDeliveryBlockGroupPerCallBlocks  Counter32,
    bwCallingLineIDDeliveryPerCallGroup             Counter32
  }

  bwCallingLineIDDeliveryBlockGroupIndex OBJECT-TYPE
    SYNTAX      Unsigned32
    MAX-ACCESS  read-only
    STATUS      current
    DESCRIPTION 
        "This integer represents the group index in the system."
    ::= { bwCallingLineIDDeliveryBlockGroupEntry 1 }

  bwCallingLineIDDeliveryBlockGroupID OBJECT-TYPE
    SYNTAX      DisplayString
    MAX-ACCESS  read-only
    STATUS      current
    DESCRIPTION 
        "This string represents a group ID"
    ::= { bwCallingLineIDDeliveryBlockGroupEntry 2 }

  bwCallingLineIDDeliveryBlockGroupPerCallBlocks OBJECT-TYPE
    SYNTAX      Counter32
    MAX-ACCESS  read-write
    STATUS      current
    DESCRIPTION 
        "This counter reflects the number of times the per call calling line ID delivery block service is invoked for this group."
    ::= { bwCallingLineIDDeliveryBlockGroupEntry 3 }

  bwCallingLineIDDeliveryPerCallGroup OBJECT-TYPE
    SYNTAX      Counter32
    MAX-ACCESS  read-write
    STATUS      current
    DESCRIPTION 
        "This counter reflects the number of times the calling line ID delivery per call service is invoked for this group."
    ::= { bwCallingLineIDDeliveryBlockGroupEntry 4 }

  bwCallingLineIDDeliveryPerCall OBJECT-TYPE
    SYNTAX      Counter32
    MAX-ACCESS  read-write
    STATUS      current
    DESCRIPTION 
        "This counter reflects the number of times the per call calling line ID delivery service is invoked."
    ::= { callingLineIDDeliveryBlock 4 }

  bwSessionAuditNumCallsAudited OBJECT-TYPE
    SYNTAX      Counter32
    MAX-ACCESS  read-write
    STATUS      current
    DESCRIPTION 
        "Number of calls that are audited when a Session Audit is invoked."
    ::= { sessionAudit 1 }

  bwSessionAuditNumEndpointsAudited OBJECT-TYPE
    SYNTAX      Counter32
    MAX-ACCESS  read-write
    STATUS      current
    DESCRIPTION 
        "Number of endpoints that are audited when a Session Audit is invoked."
    ::= { sessionAudit 2 }

  bwSessionAuditNumCallsFailedAudit OBJECT-TYPE
    SYNTAX      Counter32
    MAX-ACCESS  read-write
    STATUS      current
    DESCRIPTION 
        "Number of times the SessionAudit service received a failure on a call being audited."
    ::= { sessionAudit 3 }

  bwSessionAuditNumEndpointsFailedAudit OBJECT-TYPE
    SYNTAX      Counter32
    MAX-ACCESS  read-write
    STATUS      current
    DESCRIPTION 
        "Number of times the SessionAudit service received a failure on an endpoint being audited."
    ::= { sessionAudit 4 }

  bwSessionAuditSPTable OBJECT-TYPE
    SYNTAX      SEQUENCE OF BwSessionAuditSPEntry
    MAX-ACCESS  not-accessible
    STATUS      current
    DESCRIPTION 
        "This table contains Session Audit service measurements at a service provider level."
    ::= { sessionAudit 5 }

  bwSessionAuditSPEntry OBJECT-TYPE
    SYNTAX      BwSessionAuditSPEntry
    MAX-ACCESS  not-accessible
    STATUS      current
    DESCRIPTION 
        "Each row contains the service counters for the SessionAudit service for each service provider in the system."
    INDEX       { bwSessionAuditSPIndex }
    ::= { bwSessionAuditSPTable 1 }

  BwSessionAuditSPEntry ::= SEQUENCE {
    bwSessionAuditSPIndex                       Unsigned32,
    bwSessionAuditSPID                          DisplayString,
    bwSessionAuditSPNumCallsAudited             Counter32,
    bwSessionAuditSPNumEndpointsAudited         Counter32,
    bwSessionAuditSPNumCallsFailedAudit         Counter32,
    bwSessionAuditSPNumEndpointsFailedAudit     Counter32
  }

  bwSessionAuditSPIndex OBJECT-TYPE
    SYNTAX      Unsigned32
    MAX-ACCESS  read-only
    STATUS      current
    DESCRIPTION 
        "This column represents the index of the service provider in the system."
    ::= { bwSessionAuditSPEntry 1 }

  bwSessionAuditSPID OBJECT-TYPE
    SYNTAX      DisplayString
    MAX-ACCESS  read-only
    STATUS      current
    DESCRIPTION 
        "This column represents a service provider ID."
    ::= { bwSessionAuditSPEntry 2 }

  bwSessionAuditSPNumCallsAudited OBJECT-TYPE
    SYNTAX      Counter32
    MAX-ACCESS  read-write
    STATUS      current
    DESCRIPTION 
        "Number of calls that are audited when a Session Audit is invoked, per service provider."
    ::= { bwSessionAuditSPEntry 3 }

  bwSessionAuditSPNumEndpointsAudited OBJECT-TYPE
    SYNTAX      Counter32
    MAX-ACCESS  read-write
    STATUS      current
    DESCRIPTION 
        "Number of endpoints that are audited when a Session Audit is invoked, per service provider."
    ::= { bwSessionAuditSPEntry 4 }

  bwSessionAuditSPNumCallsFailedAudit OBJECT-TYPE
    SYNTAX      Counter32
    MAX-ACCESS  read-write
    STATUS      current
    DESCRIPTION 
        "Number of times the SessionAudit service received a failure on a call being audited, per service provider."
    ::= { bwSessionAuditSPEntry 5 }

  bwSessionAuditSPNumEndpointsFailedAudit OBJECT-TYPE
    SYNTAX      Counter32
    MAX-ACCESS  read-write
    STATUS      current
    DESCRIPTION 
        "Number of times the SessionAudit service received a failure on an endpoint being audited, per service provider."
    ::= { bwSessionAuditSPEntry 6 }

  bwSessionAuditGroupTable OBJECT-TYPE
    SYNTAX      SEQUENCE OF BwSessionAuditGroupEntry
    MAX-ACCESS  not-accessible
    STATUS      current
    DESCRIPTION 
        "This table contains Session Audit service measurements at a group level."
    ::= { sessionAudit 6 }

  bwSessionAuditGroupEntry OBJECT-TYPE
    SYNTAX      BwSessionAuditGroupEntry
    MAX-ACCESS  not-accessible
    STATUS      current
    DESCRIPTION 
        "Each row contains the service counters for the SessionAudit service for each group in the system."
    INDEX       { bwSessionAuditGroupIndex }
    ::= { bwSessionAuditGroupTable 1 }

  BwSessionAuditGroupEntry ::= SEQUENCE {
    bwSessionAuditGroupIndex                    Unsigned32,
    bwSessionAuditGroupID                       DisplayString,
    bwSessionAuditGroupNumCallsAudited          Counter32,
    bwSessionAuditGroupNumEndpointsAudited      Counter32,
    bwSessionAuditGroupNumCallsFailedAudit      Counter32,
    bwSessionAuditGroupNumEndpointsFailedAudit  Counter32
  }

  bwSessionAuditGroupIndex OBJECT-TYPE
    SYNTAX      Unsigned32
    MAX-ACCESS  read-only
    STATUS      current
    DESCRIPTION 
        "This column represents the index of the group in the system."
    ::= { bwSessionAuditGroupEntry 1 }

  bwSessionAuditGroupID OBJECT-TYPE
    SYNTAX      DisplayString
    MAX-ACCESS  read-only
    STATUS      current
    DESCRIPTION 
        "This column represents a group ID."
    ::= { bwSessionAuditGroupEntry 2 }

  bwSessionAuditGroupNumCallsAudited OBJECT-TYPE
    SYNTAX      Counter32
    MAX-ACCESS  read-write
    STATUS      current
    DESCRIPTION 
        "Number of calls that are audited when a Session Audit is invoked, per group."
    ::= { bwSessionAuditGroupEntry 3 }

  bwSessionAuditGroupNumEndpointsAudited OBJECT-TYPE
    SYNTAX      Counter32
    MAX-ACCESS  read-write
    STATUS      current
    DESCRIPTION 
        "Number of endpoints that are audited when a Session Audit is invoked, per group."
    ::= { bwSessionAuditGroupEntry 4 }

  bwSessionAuditGroupNumCallsFailedAudit OBJECT-TYPE
    SYNTAX      Counter32
    MAX-ACCESS  read-write
    STATUS      current
    DESCRIPTION 
        "Number of times the SessionAudit service received a failure on a call being audited, per group."
    ::= { bwSessionAuditGroupEntry 5 }

  bwSessionAuditGroupNumEndpointsFailedAudit OBJECT-TYPE
    SYNTAX      Counter32
    MAX-ACCESS  read-write
    STATUS      current
    DESCRIPTION 
        "Number of times the SessionAudit service received a failure on an endpoint being audited, per group."
    ::= { bwSessionAuditGroupEntry 6 }

  bwWindowsMessagingIMSessionSuccessCounter OBJECT-TYPE
    SYNTAX      Counter32
    MAX-ACCESS  read-write
    STATUS      current
    DESCRIPTION 
        "The number of times we successfully initiate a windows messaging session of type IM"
    ::= { windowsMessaging 1 }

  bwCallWaitingSPTable OBJECT-TYPE
    SYNTAX      SEQUENCE OF BwCallWaitingSPEntry
    MAX-ACCESS  not-accessible
    STATUS      current
    DESCRIPTION 
        "This counter table will be indexed per service provider."
    ::= { callWaiting 1 }

  bwCallWaitingSPEntry OBJECT-TYPE
    SYNTAX      BwCallWaitingSPEntry
    MAX-ACCESS  not-accessible
    STATUS      current
    DESCRIPTION 
        "Each row contains the service counters for the CallWaiting service for each service provider in the system."
    INDEX       { bwCallWaitingSPIndex }
    ::= { bwCallWaitingSPTable 1 }

  BwCallWaitingSPEntry ::= SEQUENCE {
    bwCallWaitingSPIndex            Unsigned32,
    bwCallWaitingSPID               DisplayString,
    bwCWSPNumPhoneCancellations     Counter32
  }

  bwCallWaitingSPIndex OBJECT-TYPE
    SYNTAX      Unsigned32
    MAX-ACCESS  read-only
    STATUS      current
    DESCRIPTION 
        "This column represents the index of the service provider in the system."
    ::= { bwCallWaitingSPEntry 1 }

  bwCallWaitingSPID OBJECT-TYPE
    SYNTAX      DisplayString
    MAX-ACCESS  read-only
    STATUS      current
    DESCRIPTION 
        "This string represents a service provider ID"
    ::= { bwCallWaitingSPEntry 2 }

  bwCWSPNumPhoneCancellations OBJECT-TYPE
    SYNTAX      Counter32
    MAX-ACCESS  read-write
    STATUS      current
    DESCRIPTION 
        "Number of times CW has been cancelled via FAC for users in a given service provider."
    ::= { bwCallWaitingSPEntry 3 }

  bwCWNumPhoneCancellations OBJECT-TYPE
    SYNTAX      Counter32
    MAX-ACCESS  read-write
    STATUS      current
    DESCRIPTION 
        "Total number of times CW has been cancelled via FAC."
    ::= { callWaiting 2 }

  bwCallWaitingGroupTable OBJECT-TYPE
    SYNTAX      SEQUENCE OF BwCallWaitingGroupEntry
    MAX-ACCESS  not-accessible
    STATUS      current
    DESCRIPTION 
        "This counter table will be indexed per group."
    ::= { callWaiting 3 }

  bwCallWaitingGroupEntry OBJECT-TYPE
    SYNTAX      BwCallWaitingGroupEntry
    MAX-ACCESS  not-accessible
    STATUS      current
    DESCRIPTION 
        "Each row contains the service counters for the CallWaiting service for each group in the system."
    INDEX       { bwCallWaitingGroupIndex }
    ::= { bwCallWaitingGroupTable 1 }

  BwCallWaitingGroupEntry ::= SEQUENCE {
    bwCallWaitingGroupIndex         Unsigned32,
    bwCallWaitingGroupID            DisplayString,
    bwCWGroupNumPhoneCancellations  Counter32
  }

  bwCallWaitingGroupIndex OBJECT-TYPE
    SYNTAX      Unsigned32
    MAX-ACCESS  read-only
    STATUS      current
    DESCRIPTION 
        "This column represents the index of the group in the system."
    ::= { bwCallWaitingGroupEntry 1 }

  bwCallWaitingGroupID OBJECT-TYPE
    SYNTAX      DisplayString
    MAX-ACCESS  read-only
    STATUS      current
    DESCRIPTION 
        "This string represents a group ID"
    ::= { bwCallWaitingGroupEntry 2 }

  bwCWGroupNumPhoneCancellations OBJECT-TYPE
    SYNTAX      Counter32
    MAX-ACCESS  read-write
    STATUS      current
    DESCRIPTION 
        "Number of times CW has been cancelled via FAC for users in a given group."
    ::= { bwCallWaitingGroupEntry 3 }

  bwAlternateNumbersSPTable OBJECT-TYPE
    SYNTAX      SEQUENCE OF BwAlternateNumbersSPEntry
    MAX-ACCESS  not-accessible
    STATUS      current
    DESCRIPTION 
        "This counter table will be indexed per service provider"
    ::= { alternateNumbers 1 }

  bwAlternateNumbersSPEntry OBJECT-TYPE
    SYNTAX      BwAlternateNumbersSPEntry
    MAX-ACCESS  not-accessible
    STATUS      current
    DESCRIPTION 
        "Each row contains the service counters for the Alternate Numbers service for each service provider in the system."
    INDEX       { bwAlternateNumbersSPIndex }
    ::= { bwAlternateNumbersSPTable 1 }

  BwAlternateNumbersSPEntry ::= SEQUENCE {
    bwAlternateNumbersSPIndex   Unsigned32,
    bwAlternateNumbersSPID      DisplayString,
    bwAlternateNumbersSPUsage   Counter32
  }

  bwAlternateNumbersSPIndex OBJECT-TYPE
    SYNTAX      Unsigned32
    MAX-ACCESS  read-only
    STATUS      current
    DESCRIPTION 
        "This column represents the index of the service provider in the system"
    ::= { bwAlternateNumbersSPEntry 1 }

  bwAlternateNumbersSPID OBJECT-TYPE
    SYNTAX      DisplayString
    MAX-ACCESS  read-only
    STATUS      current
    DESCRIPTION 
        "This string represents a service provider ID"
    ::= { bwAlternateNumbersSPEntry 2 }

  bwAlternateNumbersSPUsage OBJECT-TYPE
    SYNTAX      Counter32
    MAX-ACCESS  read-write
    STATUS      current
    DESCRIPTION 
        "Counts all call made to a user's alternate number system per service provider"
    ::= { bwAlternateNumbersSPEntry 3 }

  bwAlternateNumbersUsage OBJECT-TYPE
    SYNTAX      Counter32
    MAX-ACCESS  read-write
    STATUS      current
    DESCRIPTION 
        "Counts all call made to a user's alternate number system"
    ::= { alternateNumbers 2 }

  bwAlternateNumbersGroupTable OBJECT-TYPE
    SYNTAX      SEQUENCE OF BwAlternateNumbersGroupEntry
    MAX-ACCESS  not-accessible
    STATUS      current
    DESCRIPTION 
        "This counter table will be indexed per group"
    ::= { alternateNumbers 3 }

  bwAlternateNumbersGroupEntry OBJECT-TYPE
    SYNTAX      BwAlternateNumbersGroupEntry
    MAX-ACCESS  not-accessible
    STATUS      current
    DESCRIPTION 
        "Each row contains the service counters for the Alternate Numbers service for each group in the system."
    INDEX       { bwAlternateNumbersGroupIndex }
    ::= { bwAlternateNumbersGroupTable 1 }

  BwAlternateNumbersGroupEntry ::= SEQUENCE {
    bwAlternateNumbersGroupIndex    Unsigned32,
    bwAlternateNumbersGroupID       DisplayString,
    bwAlternateNumbersGroupUsage    Counter32
  }

  bwAlternateNumbersGroupIndex OBJECT-TYPE
    SYNTAX      Unsigned32
    MAX-ACCESS  read-only
    STATUS      current
    DESCRIPTION 
        "This column represents the index of the group in the system"
    ::= { bwAlternateNumbersGroupEntry 1 }

  bwAlternateNumbersGroupID OBJECT-TYPE
    SYNTAX      DisplayString
    MAX-ACCESS  read-only
    STATUS      current
    DESCRIPTION 
        "This string represents a group ID"
    ::= { bwAlternateNumbersGroupEntry 2 }

  bwAlternateNumbersGroupUsage OBJECT-TYPE
    SYNTAX      Counter32
    MAX-ACCESS  read-write
    STATUS      current
    DESCRIPTION 
        "Counts all call made to a user's alternate number system per group"
    ::= { bwAlternateNumbersGroupEntry 3 }

  bwCotActivation OBJECT-TYPE
    SYNTAX      Counter32
    MAX-ACCESS  read-write
    STATUS      current
    DESCRIPTION 
        "This is the number of times that an attempt is made to issue a Customer Originated trace."
    ::= { cot 1 }

  bwCotFailureNoId OBJECT-TYPE
    SYNTAX      Counter32
    MAX-ACCESS  read-write
    STATUS      current
    DESCRIPTION 
        "This is the number of times that an attempt to issue a Customer Originated trace failed."
    ::= { cot 2 }

  bwCotSPTable OBJECT-TYPE
    SYNTAX      SEQUENCE OF BwCotSPEntry
    MAX-ACCESS  not-accessible
    STATUS      current
    DESCRIPTION 
        "Counters for customer originated trace service measurements for service providers"
    ::= { cot 3 }

  bwCotSPEntry OBJECT-TYPE
    SYNTAX      BwCotSPEntry
    MAX-ACCESS  not-accessible
    STATUS      current
    DESCRIPTION 
        "Each row contains the service counters for the COT service for each service provider in the system."
    INDEX       { bwCotSPIndex }
    ::= { bwCotSPTable 1 }

  BwCotSPEntry ::= SEQUENCE {
    bwCotSPIndex              Unsigned32,
    bwCotSPID                 DisplayString,
    bwCotSPActivation         Counter32,
    bwCotSPFailureNoId        Counter32,
    bwMidCallCotSPActivation  Counter32,
    bwMidCallCotSPFailureNoId Counter32
  }

  bwCotSPIndex OBJECT-TYPE
    SYNTAX      Unsigned32
    MAX-ACCESS  read-only
    STATUS      current
    DESCRIPTION 
        "This column represents the index of the service provider in the system"
    ::= { bwCotSPEntry 1 }

  bwCotSPID OBJECT-TYPE
    SYNTAX      DisplayString
    MAX-ACCESS  read-only
    STATUS      current
    DESCRIPTION 
        "This string represents a service provider ID"
    ::= { bwCotSPEntry 2 }

  bwCotSPActivation OBJECT-TYPE
    SYNTAX      Counter32
    MAX-ACCESS  read-write
    STATUS      current
    DESCRIPTION 
        "This is the number of times that an attempt is made to issue a Customer Originated trace. There is one instance of this counter for each service provider defined in the system."
    ::= { bwCotSPEntry 3 }

  bwCotSPFailureNoId OBJECT-TYPE
    SYNTAX      Counter32
    MAX-ACCESS  read-write
    STATUS      current
    DESCRIPTION 
        "This is the number of times that an attempt to issue a Customer Originated trace failed. There is one instance of this counter for each service provider defined in the system."
    ::= { bwCotSPEntry 4 }

  bwMidCallCotSPActivation OBJECT-TYPE
    SYNTAX      Counter32
    MAX-ACCESS  read-write
    STATUS      current
    DESCRIPTION 
        "This is the number of times that an attempt is made to issue a mid-call Customer Originated trace. There is one instance of this counter for each service provider defined in the system."
    ::= { bwCotSPEntry 5 }

  bwMidCallCotSPFailureNoId OBJECT-TYPE
    SYNTAX      Counter32
    MAX-ACCESS  read-write
    STATUS      current
    DESCRIPTION 
        "This is the number of times that an attempt to issue a mid-call Customer Originated trace failed. There is one instance of this counter for each service provider defined in the system."
    ::= { bwCotSPEntry 6 }

  bwCotGroupTable OBJECT-TYPE
    SYNTAX      SEQUENCE OF BwCotGroupEntry
    MAX-ACCESS  not-accessible
    STATUS      current
    DESCRIPTION 
        "Counters for customer originated trace service measurements for groups"
    ::= { cot 4 }

  bwCotGroupEntry OBJECT-TYPE
    SYNTAX      BwCotGroupEntry
    MAX-ACCESS  not-accessible
    STATUS      current
    DESCRIPTION 
        "Each row contains the service counters for the COT service for each group in the system."
    INDEX       { bwCotGroupIndex }
    ::= { bwCotGroupTable 1 }

  BwCotGroupEntry ::= SEQUENCE {
    bwCotGroupIndex              Unsigned32,
    bwCotGroupID                 DisplayString,
    bwCotGroupActivation         Counter32,
    bwCotGroupFailureNoId        Counter32,
    bwMidCallCotGroupActivation  Counter32,
    bwMidCallCotGroupFailureNoId Counter32
  }

  bwCotGroupIndex OBJECT-TYPE
    SYNTAX      Unsigned32
    MAX-ACCESS  read-only
    STATUS      current
    DESCRIPTION 
        "This column represents the index of the group in the system"
    ::= { bwCotGroupEntry 1 }

  bwCotGroupID OBJECT-TYPE
    SYNTAX      DisplayString
    MAX-ACCESS  read-only
    STATUS      current
    DESCRIPTION 
        "This string represents a group ID"
    ::= { bwCotGroupEntry 2 }

  bwCotGroupActivation OBJECT-TYPE
    SYNTAX      Counter32
    MAX-ACCESS  read-write
    STATUS      current
    DESCRIPTION 
        "This is the number of times that an attempt is made to issue a Customer Originated trace.There is one instance of this counter for each group defined in the system."
    ::= { bwCotGroupEntry 3 }

  bwCotGroupFailureNoId OBJECT-TYPE
    SYNTAX      Counter32
    MAX-ACCESS  read-write
    STATUS      current
    DESCRIPTION 
        "This is the number of times that an attempt to issue a Customer Originated trace failed. There is one instance of this counter for each group defined in the system."
    ::= { bwCotGroupEntry 4 }

  bwMidCallCotGroupActivation OBJECT-TYPE
    SYNTAX      Counter32
    MAX-ACCESS  read-write
    STATUS      current
    DESCRIPTION 
        "This is the number of times that an attempt is made to issue a mid-call Customer Originated trace.There is one instance of this counter for each group defined in the system."
    ::= { bwCotGroupEntry 5 }

  bwMidCallCotGroupFailureNoId OBJECT-TYPE
    SYNTAX      Counter32
    MAX-ACCESS  read-write
    STATUS      current
    DESCRIPTION 
        "This is the number of times that an attempt to issue a mid-call Customer Originated trace failed. There is one instance of this counter for each group defined in the system."
    ::= { bwCotGroupEntry 6 }

  bwMidCallCotActivation OBJECT-TYPE
    SYNTAX      Counter32
    MAX-ACCESS  read-write
    STATUS      current
    DESCRIPTION 
        "This is the number of times that an attempt is made to issue a mid-call Customer Originated trace."
    ::= { cot 5 }

  bwMidCallCotFailureNoId OBJECT-TYPE
    SYNTAX      Counter32
    MAX-ACCESS  read-write
    STATUS      current
    DESCRIPTION 
        "This is the number of times that an attempt to issue a mid-call Customer Originated trace failed."
    ::= { cot 6 }

  bwSD8NumTimesDialed OBJECT-TYPE
    SYNTAX      Counter32
    MAX-ACCESS  read-write
    STATUS      current
    DESCRIPTION 
        "Total number of times a speed code has been dialed"
    ::= { sd8 1 }

  bwSD8NumTimesProgrammed OBJECT-TYPE
    SYNTAX      Counter32
    MAX-ACCESS  read-write
    STATUS      current
    DESCRIPTION 
        "Total number of times a speed code has been defined by a user via FAC"
    ::= { sd8 2 }

  bwSD8SPTable OBJECT-TYPE
    SYNTAX      SEQUENCE OF BwSD8SPEntry
    MAX-ACCESS  not-accessible
    STATUS      current
    DESCRIPTION 
        "Counters for SD8 service measurements for service providers"
    ::= { sd8 3 }

  bwSD8SPEntry OBJECT-TYPE
    SYNTAX      BwSD8SPEntry
    MAX-ACCESS  not-accessible
    STATUS      current
    DESCRIPTION 
        "Each row contains the service counters for the SD8 service for each service provider in the system."
    INDEX       { bwSD8SPIndex }
    ::= { bwSD8SPTable 1 }

  BwSD8SPEntry ::= SEQUENCE {
    bwSD8SPIndex                Unsigned32,
    bwSD8SPID                   DisplayString,
    bwSD8SPNumTimesDialed       Counter32,
    bwSD8SPNumTimesProgrammed   Counter32
  }

  bwSD8SPIndex OBJECT-TYPE
    SYNTAX      Unsigned32
    MAX-ACCESS  read-only
    STATUS      current
    DESCRIPTION 
        "This column represents the index of the service provider in the system"
    ::= { bwSD8SPEntry 1 }

  bwSD8SPID OBJECT-TYPE
    SYNTAX      DisplayString
    MAX-ACCESS  read-only
    STATUS      current
    DESCRIPTION 
        "This string represents a service provider ID"
    ::= { bwSD8SPEntry 2 }

  bwSD8SPNumTimesDialed OBJECT-TYPE
    SYNTAX      Counter32
    MAX-ACCESS  read-write
    STATUS      current
    DESCRIPTION 
        "Total Number of times a speed code has been dialed by users in a given service provider"
    ::= { bwSD8SPEntry 3 }

  bwSD8SPNumTimesProgrammed OBJECT-TYPE
    SYNTAX      Counter32
    MAX-ACCESS  read-write
    STATUS      current
    DESCRIPTION 
        "Total numberNumber of times a speed code has been defined via FAC by users in a given service provider"
    ::= { bwSD8SPEntry 4 }

  bwSD8GroupTable OBJECT-TYPE
    SYNTAX      SEQUENCE OF BwSD8GroupEntry
    MAX-ACCESS  not-accessible
    STATUS      current
    DESCRIPTION 
        "Counters for SD8 service measurements for groups"
    ::= { sd8 4 }

  bwSD8GroupEntry OBJECT-TYPE
    SYNTAX      BwSD8GroupEntry
    MAX-ACCESS  not-accessible
    STATUS      current
    DESCRIPTION 
        "Each row contains the service counters for the SD8 service for each group in the system."
    INDEX       { bwSD8GroupIndex }
    ::= { bwSD8GroupTable 1 }

  BwSD8GroupEntry ::= SEQUENCE {
    bwSD8GroupIndex                 Unsigned32,
    bwSD8GroupID                    DisplayString,
    bwSD8GroupNumTimesDialed        Counter32,
    bwSD8GroupNumTimesProgrammed    Counter32
  }

  bwSD8GroupIndex OBJECT-TYPE
    SYNTAX      Unsigned32
    MAX-ACCESS  read-only
    STATUS      current
    DESCRIPTION 
        "This column represents the index of the group in the system"
    ::= { bwSD8GroupEntry 1 }

  bwSD8GroupID OBJECT-TYPE
    SYNTAX      DisplayString
    MAX-ACCESS  read-only
    STATUS      current
    DESCRIPTION 
        "This string represents a group ID"
    ::= { bwSD8GroupEntry 2 }

  bwSD8GroupNumTimesDialed OBJECT-TYPE
    SYNTAX      Counter32
    MAX-ACCESS  read-write
    STATUS      current
    DESCRIPTION 
        "Total Number of times a speed code has been dialed by users in a given group"
    ::= { bwSD8GroupEntry 3 }

  bwSD8GroupNumTimesProgrammed OBJECT-TYPE
    SYNTAX      Counter32
    MAX-ACCESS  read-write
    STATUS      current
    DESCRIPTION 
        "Total numberNumber of times a speed code has been defined via FAC by users in a given group"
    ::= { bwSD8GroupEntry 4 }

  bwMusicOnHoldNumUses OBJECT-TYPE
    SYNTAX      Counter32
    MAX-ACCESS  read-write
    STATUS      current
    DESCRIPTION 
        "Total number of times Music On Hold has been used"
    ::= { musicOnHold 1 }

  bwMusicOnHoldSPTable OBJECT-TYPE
    SYNTAX      SEQUENCE OF BwMusicOnHoldSPEntry
    MAX-ACCESS  not-accessible
    STATUS      current
    DESCRIPTION 
        "Counters for Music On Hold service measurements for service providers"
    ::= { musicOnHold 2 }

  bwMusicOnHoldSPEntry OBJECT-TYPE
    SYNTAX      BwMusicOnHoldSPEntry
    MAX-ACCESS  not-accessible
    STATUS      current
    DESCRIPTION 
        "Each row contains the service counters for the Music On Hold service for each service provider in the system."
    INDEX       { bwMusicOnHoldSPIndex }
    ::= { bwMusicOnHoldSPTable 1 }

  BwMusicOnHoldSPEntry ::= SEQUENCE {
    bwMusicOnHoldSPIndex                        Unsigned32,
    bwMusicOnHoldSPID                           DisplayString,
    bwMusicOnHoldSPNumUses                      Counter32,
    bwMusicOnHoldSPExternalSourceNumFailures    Counter32
  }

  bwMusicOnHoldSPIndex OBJECT-TYPE
    SYNTAX      Unsigned32
    MAX-ACCESS  read-only
    STATUS      current
    DESCRIPTION 
        "This column represents the index of the service provider in the system"
    ::= { bwMusicOnHoldSPEntry 1 }

  bwMusicOnHoldSPID OBJECT-TYPE
    SYNTAX      DisplayString
    MAX-ACCESS  read-only
    STATUS      current
    DESCRIPTION 
        "This string represents a service provider ID"
    ::= { bwMusicOnHoldSPEntry 2 }

  bwMusicOnHoldSPNumUses OBJECT-TYPE
    SYNTAX      Counter32
    MAX-ACCESS  read-write
    STATUS      current
    DESCRIPTION 
        "The service provider counter is incremented every a user hears music on hold"
    ::= { bwMusicOnHoldSPEntry 3 }

  bwMusicOnHoldSPExternalSourceNumFailures OBJECT-TYPE
    SYNTAX      Counter32
    MAX-ACCESS  read-write
    STATUS      current
    DESCRIPTION 
        "This is the number of failures to terminate on music-on-hold source."
    ::= { bwMusicOnHoldSPEntry 4 }

  bwMusicOnHoldGroupTable OBJECT-TYPE
    SYNTAX      SEQUENCE OF BwMusicOnHoldGroupEntry
    MAX-ACCESS  not-accessible
    STATUS      current
    DESCRIPTION 
        "Counters for Music On Hold service measurements for groups"
    ::= { musicOnHold 3 }

  bwMusicOnHoldGroupEntry OBJECT-TYPE
    SYNTAX      BwMusicOnHoldGroupEntry
    MAX-ACCESS  not-accessible
    STATUS      current
    DESCRIPTION 
        "Each row contains the service counters for the Music On Hold service for each group in the system."
    INDEX       { bwMusicOnHoldGroupIndex }
    ::= { bwMusicOnHoldGroupTable 1 }

  BwMusicOnHoldGroupEntry ::= SEQUENCE {
    bwMusicOnHoldGroupIndex                         Unsigned32,
    bwMusicOnHoldGroupID                            DisplayString,
    bwMusicOnHoldGroupNumUses                       Counter32,
    bwMusicOnHoldGroupExternalSourceNumFailures     Counter32
  }

  bwMusicOnHoldGroupIndex OBJECT-TYPE
    SYNTAX      Unsigned32
    MAX-ACCESS  read-only
    STATUS      current
    DESCRIPTION 
        "This column represents the index of the group in the system"
    ::= { bwMusicOnHoldGroupEntry 1 }

  bwMusicOnHoldGroupID OBJECT-TYPE
    SYNTAX      DisplayString
    MAX-ACCESS  read-only
    STATUS      current
    DESCRIPTION 
        "This string represents a group ID"
    ::= { bwMusicOnHoldGroupEntry 2 }

  bwMusicOnHoldGroupNumUses OBJECT-TYPE
    SYNTAX      Counter32
    MAX-ACCESS  read-write
    STATUS      current
    DESCRIPTION 
        "The group counter is incremented every a user hears music on hold"
    ::= { bwMusicOnHoldGroupEntry 3 }

  bwMusicOnHoldGroupExternalSourceNumFailures OBJECT-TYPE
    SYNTAX      Counter32
    MAX-ACCESS  read-write
    STATUS      current
    DESCRIPTION 
        "This is the number of failures to terminate on music-on-hold source."
    ::= { bwMusicOnHoldGroupEntry 4 }

  bwMusicOnHoldExternalSourceNumFailures OBJECT-TYPE
    SYNTAX      Counter32
    MAX-ACCESS  read-write
    STATUS      current
    DESCRIPTION 
        "This counter is incremented whenever a caller is put on hold and the music-on-hold source could not be connected to the caller.  This counter is incremented in the context of the Music On Hold and Call Center services."
    ::= { musicOnHold 4 }

  bwCNAMQueriesSent OBJECT-TYPE
    SYNTAX      Counter32
    MAX-ACCESS  read-write
    STATUS      current
    DESCRIPTION 
        "Number of queries that have been sent to the external database inquiring the calling name information."
    ::= { callingNameRetrieval 1 }

  bwCNAMQueriesFailed OBJECT-TYPE
    SYNTAX      Counter32
    MAX-ACCESS  read-write
    STATUS      current
    DESCRIPTION 
        "Number of queries that have failed to the external database inquiring the calling name information."
    ::= { callingNameRetrieval 2 }

  bwCNAMQueriesTimeout OBJECT-TYPE
    SYNTAX      Counter32
    MAX-ACCESS  read-write
    STATUS      current
    DESCRIPTION 
        "Number of queries that have timed out to the external database inquiring the calling name information."
    ::= { callingNameRetrieval 3 }

  bwCNAMSPTable OBJECT-TYPE
    SYNTAX      SEQUENCE OF BwCNAMSPEntry
    MAX-ACCESS  not-accessible
    STATUS      current
    DESCRIPTION 
        "Counters for Calling Name service measurements for service providers"
    ::= { callingNameRetrieval 4 }

  bwCNAMSPEntry OBJECT-TYPE
    SYNTAX      BwCNAMSPEntry
    MAX-ACCESS  not-accessible
    STATUS      current
    DESCRIPTION 
        "Each row contains the service counters for the Calling Name service for each service provider in the system"
    INDEX       { bwCNAMSPIndex }
    ::= { bwCNAMSPTable 1 }

  BwCNAMSPEntry ::= SEQUENCE {
    bwCNAMSPIndex           Unsigned32,
    bwCNAMSPID              DisplayString,
    bwCNAMSPQueriesSent     Counter32,
    bwCNAMSPQueriesFailed   Counter32,
    bwCNAMSPQueriesTimeout  Counter32
  }

  bwCNAMSPIndex OBJECT-TYPE
    SYNTAX      Unsigned32
    MAX-ACCESS  read-only
    STATUS      current
    DESCRIPTION 
        "This column represents the index of the service provider in the system"
    ::= { bwCNAMSPEntry 1 }

  bwCNAMSPID OBJECT-TYPE
    SYNTAX      DisplayString
    MAX-ACCESS  read-only
    STATUS      current
    DESCRIPTION 
        "This string represents a service provider ID"
    ::= { bwCNAMSPEntry 2 }

  bwCNAMSPQueriesSent OBJECT-TYPE
    SYNTAX      Counter32
    MAX-ACCESS  read-write
    STATUS      current
    DESCRIPTION 
        "Number of queries that have been sent to the external database inquiring the calling name information for each service provider in the system."
    ::= { bwCNAMSPEntry 3 }

  bwCNAMSPQueriesFailed OBJECT-TYPE
    SYNTAX      Counter32
    MAX-ACCESS  read-write
    STATUS      current
    DESCRIPTION 
        "Number of queries that have failed to the external database inquiring the calling name information for each service provider in the system."
    ::= { bwCNAMSPEntry 4 }

  bwCNAMSPQueriesTimeout OBJECT-TYPE
    SYNTAX      Counter32
    MAX-ACCESS  read-write
    STATUS      current
    DESCRIPTION 
        "Number of queries that have timed out to the external database inquiring the calling name information for each service provider in the system."
    ::= { bwCNAMSPEntry 5 }

  bwCNAMGroupTable OBJECT-TYPE
    SYNTAX      SEQUENCE OF BwCNAMGroupEntry
    MAX-ACCESS  not-accessible
    STATUS      current
    DESCRIPTION 
        "Counters for Calling Name service measurements for groups"
    ::= { callingNameRetrieval 5 }

  bwCNAMGroupEntry OBJECT-TYPE
    SYNTAX      BwCNAMGroupEntry
    MAX-ACCESS  not-accessible
    STATUS      current
    DESCRIPTION 
        "Each row contains the service counters for the Calling Name service for each group in the system"
    INDEX       { bwCNAMGroupIndex }
    ::= { bwCNAMGroupTable 1 }

  BwCNAMGroupEntry ::= SEQUENCE {
    bwCNAMGroupIndex            Unsigned32,
    bwCNAMGroupID               DisplayString,
    bwCNAMGroupQueriesSent      Counter32,
    bwCNAMGroupQueriesFailed    Counter32,
    bwCNAMGroupQueriesTimeout   Counter32
  }

  bwCNAMGroupIndex OBJECT-TYPE
    SYNTAX      Unsigned32
    MAX-ACCESS  read-only
    STATUS      current
    DESCRIPTION 
        "This column represents the index of the group in the system"
    ::= { bwCNAMGroupEntry 1 }

  bwCNAMGroupID OBJECT-TYPE
    SYNTAX      DisplayString
    MAX-ACCESS  read-only
    STATUS      current
    DESCRIPTION 
        "This string represents a group ID"
    ::= { bwCNAMGroupEntry 2 }

  bwCNAMGroupQueriesSent OBJECT-TYPE
    SYNTAX      Counter32
    MAX-ACCESS  read-write
    STATUS      current
    DESCRIPTION 
        "Number of queries that have been sent to the external database inquiring the calling name information for each group in the system."
    ::= { bwCNAMGroupEntry 3 }

  bwCNAMGroupQueriesFailed OBJECT-TYPE
    SYNTAX      Counter32
    MAX-ACCESS  read-write
    STATUS      current
    DESCRIPTION 
        "Number of queries that have failed to the external database inquiring the calling name information for each group in the system."
    ::= { bwCNAMGroupEntry 4 }

  bwCNAMGroupQueriesTimeout OBJECT-TYPE
    SYNTAX      Counter32
    MAX-ACCESS  read-write
    STATUS      current
    DESCRIPTION 
        "Number of queries that have timed out to the external database inquiring the calling name information for each group in the system."
    ::= { bwCNAMGroupEntry 5 }

  bwThirdPartyMWIControlNotifyIns OBJECT-TYPE
    SYNTAX      Counter32
    MAX-ACCESS  read-write
    STATUS      current
    DESCRIPTION 
        "Number of times a MWI NOTIFY is received."
    ::= { thirdPartyMWIControl 1 }

  bwThirdPartyMWIControlNotifyFailures OBJECT-TYPE
    SYNTAX      Counter32
    MAX-ACCESS  read-write
    STATUS      current
    DESCRIPTION 
        "Number of times a MWI NOTIFY is received for an unknown user, or for a user who is not assigned the service."
    ::= { thirdPartyMWIControl 2 }

-- Services :: CallCenter ...........................................

  bwCallCenterSPTable OBJECT-TYPE
    SYNTAX      SEQUENCE OF BwCallCenterSPEntry
    MAX-ACCESS  not-accessible
    STATUS      current
    DESCRIPTION 
        "Counters for Call Center service measurements for service providers"
    ::= { callCenter 2 }

  bwCallCenterSPEntry OBJECT-TYPE
    SYNTAX      BwCallCenterSPEntry
    MAX-ACCESS  not-accessible
    STATUS      current
    DESCRIPTION 
        "Each row contains the service counters for the Call Center service for each service provider in the system"
    INDEX       { bwCallCenterSPIndex }
    ::= { bwCallCenterSPTable 1 }

  BwCallCenterSPEntry ::= SEQUENCE {
    bwCallCenterSPIndex                         Unsigned32,
    bwCallCenterSPID                            DisplayString,
    bwCallCenterSPNumCalls                      Counter32,
    bwCallCenterSPNumSizeOverflow               Counter32,
    bwCallCenterSPNumTimeOverflow               Counter32,
    bwCallCenterSPNumBouncedCalls               Counter32,
    bwCallCenterSPNumEntranceMessage            Counter32,
    bwCallCenterSPNumComfortMessage             Counter32,
    bwCallCenterSPNumComfortBypassMessage       Counter32,
    bwCallCenterSPNumStrandedMessage            Counter32,
    bwCallCenterSPNumNightServiceMessage        Counter32,
    bwCallCenterSPNumManualNightServiceMessage  Counter32,
    bwCallCenterSPNumHolidayServiceMessage      Counter32,
    bwCallCenterSPNumForcedForwardingMessage    Counter32,
    bwCallCenterSPNumOverflowMessage            Counter32,
    bwCallCenterSPNumHoldReminder               Counter32,
    bwCallCenterSPNumBouncedHeldCall            Counter32,
    bwCallCenterSPNumAgentWhisperMessage        Counter32,
    bwCallCenterSPNumOutgoingCall               Counter32,
    bwCallCenterSPNumEscalatedCalls             Counter32,
    bwCallCenterSPNumEscalatedCallsFailure      Counter32,
    bwCallCenterSPNumEmergencyCalls             Counter32,
    bwCallCenterSPNumEmergencyCallsFailure      Counter32,
    bwCallCenterSPNumQueuePositionMessage       Counter32,
    bwCallCenterSPNumQueueWaitTimeMessage       Counter32,
    bwCallCenterSPNumStrandedUnavailableMessage Counter32
  }

  bwCallCenterSPIndex OBJECT-TYPE
    SYNTAX      Unsigned32
    MAX-ACCESS  read-only
    STATUS      current
    DESCRIPTION 
        "This column represents the index of the service provider in the system"
    ::= { bwCallCenterSPEntry 1 }

  bwCallCenterSPID OBJECT-TYPE
    SYNTAX      DisplayString
    MAX-ACCESS  read-only
    STATUS      current
    DESCRIPTION 
        "This string represents a service provider ID"
    ::= { bwCallCenterSPEntry 2 }

  bwCallCenterSPNumCalls OBJECT-TYPE
    SYNTAX      Counter32
    MAX-ACCESS  read-write
    STATUS      current
    DESCRIPTION 
        "This is the number of incoming calls to a Call Center. There is one instance of this counter for each service provider defined in the system."
    ::= { bwCallCenterSPEntry 4 }

  bwCallCenterSPNumSizeOverflow OBJECT-TYPE
    SYNTAX      Counter32
    MAX-ACCESS  read-write
    STATUS      current
    DESCRIPTION 
        "This is the number of incoming calls (to a Call Center) that overflows based on the queue size. There is one instance of this counter for each service provider defined in the system."
    ::= { bwCallCenterSPEntry 5 }

  bwCallCenterSPNumTimeOverflow OBJECT-TYPE
    SYNTAX      Counter32
    MAX-ACCESS  read-write
    STATUS      current
    DESCRIPTION 
        "This is the number of incoming calls (to a Call Center) that overflows based on time. There is one instance of this counter for each service provider defined in the system."
    ::= { bwCallCenterSPEntry 6 }

  bwCallCenterSPNumBouncedCalls OBJECT-TYPE
    SYNTAX      Counter32
    MAX-ACCESS  read-write
    STATUS      current
    DESCRIPTION 
        "This is the number of calls (sent to an agent) that bounces. There is one instance of this counter for each service provider defined in the system."
    ::= { bwCallCenterSPEntry 7 }

  bwCallCenterSPNumEntranceMessage OBJECT-TYPE
    SYNTAX      Counter32
    MAX-ACCESS  read-write
    STATUS      current
    DESCRIPTION 
        "This is the number of times that the entrance message is played for a call to a Call Center. There is one instance of this counter for each service provider defined in the system."
    ::= { bwCallCenterSPEntry 8 }

  bwCallCenterSPNumComfortMessage OBJECT-TYPE
    SYNTAX      Counter32
    MAX-ACCESS  read-write
    STATUS      current
    DESCRIPTION 
        "This is the number of times that the comfort message is played for a call to a Call Center. There is one instance of this counter for each service provider defined in the system."
    ::= { bwCallCenterSPEntry 9 }

  bwCallCenterSPNumComfortBypassMessage OBJECT-TYPE
    SYNTAX      Counter32
    MAX-ACCESS  read-write
    STATUS      current
    DESCRIPTION 
        "This is the number of times that the comfort bypass message is played for a call to a Call Center. There is one instance of this counter for each service provider defined in the system."
    ::= { bwCallCenterSPEntry 10 }

  bwCallCenterSPNumStrandedMessage OBJECT-TYPE
    SYNTAX      Counter32
    MAX-ACCESS  read-write
    STATUS      current
    DESCRIPTION 
        "This is the number of times that the stranded message is played for a call to a Call Center. There is one instance of this counter for each service provider defined in the system."
    ::= { bwCallCenterSPEntry 11 }

  bwCallCenterSPNumNightServiceMessage OBJECT-TYPE
    SYNTAX      Counter32
    MAX-ACCESS  read-write
    STATUS      current
    DESCRIPTION 
        "This is the number of times that the Night Service message is played for a call to a Call Center. There is one instance of this counter for each service provider defined in the system."
    ::= { bwCallCenterSPEntry 12 }

  bwCallCenterSPNumManualNightServiceMessage OBJECT-TYPE
    SYNTAX      Counter32
    MAX-ACCESS  read-write
    STATUS      current
    DESCRIPTION 
        "This is the number of times that the manual Night Service message is played for a call to a Call Center. There is one instance of this counter for each service provider defined in the system."
    ::= { bwCallCenterSPEntry 13 }

  bwCallCenterSPNumHolidayServiceMessage OBJECT-TYPE
    SYNTAX      Counter32
    MAX-ACCESS  read-write
    STATUS      current
    DESCRIPTION 
        "This is the number of times that the Holiday Service message is played for a call to a Call Center. There is one instance of this counter for each service provider defined in the system."
    ::= { bwCallCenterSPEntry 14 }

  bwCallCenterSPNumForcedForwardingMessage OBJECT-TYPE
    SYNTAX      Counter32
    MAX-ACCESS  read-write
    STATUS      current
    DESCRIPTION 
        "This is the number of times that the Forced Forwarding message is played for a call to a Call Center. There is one instance of this counter for each service provider defined in the system."
    ::= { bwCallCenterSPEntry 15 }

  bwCallCenterSPNumOverflowMessage OBJECT-TYPE
    SYNTAX      Counter32
    MAX-ACCESS  read-write
    STATUS      current
    DESCRIPTION 
        "This is the number of times that the overflow message is played for a call to a Call Center.  There is one instance of this counter for each service provider defined in the system."
    ::= { bwCallCenterSPEntry 16 }

  bwCallCenterSPNumHoldReminder OBJECT-TYPE
    SYNTAX Counter32
    MAX-ACCESS read-write
    STATUS current
    DESCRIPTION "This is the number of times that the hold reminder is sent by the Call Center to an Agent.  There is one instance of this counter for each service provider defined in the system."
    ::= { bwCallCenterSPEntry 17 }

  bwCallCenterSPNumBouncedHeldCall OBJECT-TYPE
    SYNTAX Counter32
    MAX-ACCESS read-write
    STATUS current
    DESCRIPTION "This is the number of held calls (calls put on hold for specific amount of time by an agent) that bounces.  There is one instance of this counter for each service provider defined in the system."
    ::= { bwCallCenterSPEntry 18 }

  bwCallCenterSPNumAgentWhisperMessage OBJECT-TYPE
    SYNTAX Counter32
    MAX-ACCESS read-write
    STATUS current
    DESCRIPTION "This is the number of times that the agent whisper message is played for a call to a Call Center.  There is one instance of this counter for each service provider defined in the system."
    ::= { bwCallCenterSPEntry 19 }

  bwCallCenterSPNumOutgoingCall OBJECT-TYPE
    SYNTAX Counter32
    MAX-ACCESS read-write
    STATUS current
    DESCRIPTION "This is the number of times that a Call Center Agent makes an outgoing call as a Call Center.  There is one instance of this counter for each service provider defined in the system."
    ::= { bwCallCenterSPEntry 20 }

  bwCallCenterSPNumEscalatedCalls OBJECT-TYPE
    SYNTAX Counter32
    MAX-ACCESS read-write
    STATUS current
    DESCRIPTION "This is the number of times that an escalated call is successfully placed by an Agent to a Supervisor. There is one instance of this counter for each service provider defined in the system."
    ::= { bwCallCenterSPEntry 21 }

  bwCallCenterSPNumEscalatedCallsFailure OBJECT-TYPE
    SYNTAX Counter32
    MAX-ACCESS read-write
    STATUS current
    DESCRIPTION "This is the number of times that an escalated call failed to be placed from an Agent to a Supervisor. There is one instance of this counter for each service provider defined in the system."
    ::= { bwCallCenterSPEntry 22 }

  bwCallCenterSPNumEmergencyCalls OBJECT-TYPE
    SYNTAX      Counter32
    MAX-ACCESS  read-write
    STATUS      current
    DESCRIPTION 
        "This is the number of times that an emergency escalation is successful from an agent to a Supervisor. There is one instance of this counter for each service provider defined in the system."
    ::= { bwCallCenterSPEntry 23 }

  bwCallCenterSPNumEmergencyCallsFailure OBJECT-TYPE
    SYNTAX      Counter32
    MAX-ACCESS  read-write
    STATUS      current
    DESCRIPTION 
        "This is the number of times that an emergency invocation failed to be placed from an agent to a Supervisor. There is one instance of this counter for each service provider defined in the system."
    ::= { bwCallCenterSPEntry 24 }

  bwCallCenterSPNumQueuePositionMessage OBJECT-TYPE
    SYNTAX      Counter32
    MAX-ACCESS  read-write
    STATUS      current
    DESCRIPTION 
        "This is the number of times that the queue position message is played for a call to a Call Center. There is one instance of this counter for each service provider defined in the system."
    ::= { bwCallCenterSPEntry 25 }

  bwCallCenterSPNumQueueWaitTimeMessage OBJECT-TYPE
    SYNTAX      Counter32
    MAX-ACCESS  read-write
    STATUS      current
    DESCRIPTION 
        "This is the number of times that the queue wait time message is played for a call to a Call Center.  There is one instance of this counter for each service provider defined in the system."
    ::= { bwCallCenterSPEntry 26 }
    
  bwCallCenterSPNumStrandedUnavailableMessage OBJECT-TYPE
     SYNTAX      Counter32
     MAX-ACCESS  read-write
     STATUS      current
     DESCRIPTION 
         "This is the number of times that the Stranded Calls - Unavailable message is triggered to be played for a call to a call center.  There is one instance of this counter for each service provider defined in the system."
-- @feature:149564
    ::= { bwCallCenterSPEntry 27 }

  bwCallCenterGroupTable OBJECT-TYPE
    SYNTAX      SEQUENCE OF BwCallCenterGroupEntry
    MAX-ACCESS  not-accessible
    STATUS      current
    DESCRIPTION 
        "Counters for Call Center service measurements for groups"
    ::= { callCenter 3 }

  bwCallCenterGroupEntry OBJECT-TYPE
    SYNTAX      BwCallCenterGroupEntry
    MAX-ACCESS  not-accessible
    STATUS      current
    DESCRIPTION 
        "Each row contains the service counters for the Call Center service for each group in the system"
    INDEX       { bwCallCenterGroupIndex }
    ::= { bwCallCenterGroupTable 1 }

  BwCallCenterGroupEntry ::= SEQUENCE {
    bwCallCenterGroupIndex                          Unsigned32,
    bwCallCenterGroupID                             DisplayString,
    bwCallCenterGroupNumCalls                       Counter32,
    bwCallCenterGroupNumSizeOverflow                Counter32,
    bwCallCenterGroupNumTimeOverflow                Counter32,
    bwCallCenterGroupNumBouncedCalls                Counter32,
    bwCallCenterGroupNumEntranceMessage             Counter32,
    bwCallCenterGroupNumComfortMessage              Counter32,
    bwCallCenterGroupNumComfortBypassMessage        Counter32,
    bwCallCenterGroupNumStrandedMessage             Counter32,
    bwCallCenterGroupNumNightServiceMessage         Counter32,
    bwCallCenterGroupNumManualNightServiceMessage   Counter32,
    bwCallCenterGroupNumHolidayServiceMessage       Counter32,
    bwCallCenterGroupNumForcedForwardingMessage     Counter32,
    bwCallCenterGroupNumOverflowMessage             Counter32,
    bwCallCenterGroupNumHoldReminder                Counter32,
    bwCallCenterGroupNumBouncedHeldCall             Counter32,
    bwCallCenterGroupNumAgentWhisperMessage         Counter32,
    bwCallCenterGroupNumOutgoingCall                Counter32,
    bwCallCenterGroupNumEscalatedCalls              Counter32,
    bwCallCenterGroupNumEscalatedCallsFailure       Counter32,
    bwCallCenterGroupNumEmergencyCalls              Counter32,
    bwCallCenterGroupNumEmergencyCallsFailure       Counter32,
    bwCallCenterGroupNumQueuePositionMessage        Counter32,
    bwCallCenterGroupNumQueueWaitTimeMessage        Counter32,
    bwCallCenterGroupNumStrandedUnavailableMessage  Counter32
  }

  bwCallCenterGroupIndex OBJECT-TYPE
    SYNTAX      Unsigned32
    MAX-ACCESS  read-only
    STATUS      current
    DESCRIPTION 
        "This column represents the index of the group in the system"
    ::= { bwCallCenterGroupEntry 1 }

  bwCallCenterGroupID OBJECT-TYPE
    SYNTAX      DisplayString
    MAX-ACCESS  read-only
    STATUS      current
    DESCRIPTION 
        "This string represents a group ID"
    ::= { bwCallCenterGroupEntry 2 }

  bwCallCenterGroupNumCalls OBJECT-TYPE
    SYNTAX      Counter32
    MAX-ACCESS  read-write
    STATUS      current
    DESCRIPTION 
        "This is the number of incoming calls to a Call Center. There is one instance of this counter for each group defined in the system."
    ::= { bwCallCenterGroupEntry 4 }

  bwCallCenterGroupNumSizeOverflow OBJECT-TYPE
    SYNTAX      Counter32
    MAX-ACCESS  read-write
    STATUS      current
    DESCRIPTION 
        "This is the number of incoming calls (to a Call Center) that overflows based on the queue size. There is one instance of this counter for each group defined in the system."
    ::= { bwCallCenterGroupEntry 5 }

  bwCallCenterGroupNumTimeOverflow OBJECT-TYPE
    SYNTAX      Counter32
    MAX-ACCESS  read-write
    STATUS      current
    DESCRIPTION 
        "This is the number of incoming calls (to a Call Center) that overflows based on time. There is one instance of this counter for each group defined in the system."
    ::= { bwCallCenterGroupEntry 6 }

  bwCallCenterGroupNumBouncedCalls OBJECT-TYPE
    SYNTAX      Counter32
    MAX-ACCESS  read-write
    STATUS      current
    DESCRIPTION 
        "This is the number of calls (sent to an agent) that bounces. There is one instance of this counter for each group defined in the system."
    ::= { bwCallCenterGroupEntry 7 }

  bwCallCenterGroupNumEntranceMessage OBJECT-TYPE
    SYNTAX      Counter32
    MAX-ACCESS  read-write
    STATUS      current
    DESCRIPTION 
        "This is the number of times that the entrance message is played for a call to a Call Center. There is one instance of this counter for each group defined in the system."
    ::= { bwCallCenterGroupEntry 8 }

  bwCallCenterGroupNumComfortMessage OBJECT-TYPE
    SYNTAX      Counter32
    MAX-ACCESS  read-write
    STATUS      current
    DESCRIPTION 
        "This is the number of times that the comfort message is played for a call to a Call Center. There is one instance of this counter for each group defined in the system."
    ::= { bwCallCenterGroupEntry 9 }

  bwCallCenterGroupNumComfortBypassMessage OBJECT-TYPE
    SYNTAX      Counter32
    MAX-ACCESS  read-write
    STATUS      current
    DESCRIPTION 
        "This is the number of times that the comfort bypass message is played for a call to a Call Center. There is one instance of this counter for each group defined in the system."
    ::= { bwCallCenterGroupEntry 10 }

  bwCallCenterGroupNumStrandedMessage OBJECT-TYPE
    SYNTAX      Counter32
    MAX-ACCESS  read-write
    STATUS      current
    DESCRIPTION 
        "This is the number of times that the stranded message is played for a call to a Call Center. There is one instance of this counter for each group defined in the system."
    ::= { bwCallCenterGroupEntry 11 }

  bwCallCenterGroupNumNightServiceMessage OBJECT-TYPE
    SYNTAX      Counter32
    MAX-ACCESS  read-write
    STATUS      current
    DESCRIPTION 
        "This is the number of times that the Night Service message is played for a call to a Call Center. There is one instance of this counter for each group defined in the system."
    ::= { bwCallCenterGroupEntry 12 }

  bwCallCenterGroupNumManualNightServiceMessage OBJECT-TYPE
    SYNTAX      Counter32
    MAX-ACCESS  read-write
    STATUS      current
    DESCRIPTION 
        "This is the number of times that the manual Night Service message is played for a call to a Call Center. There is one instance of this counter for each group defined in the system."
    ::= { bwCallCenterGroupEntry 13 }

  bwCallCenterGroupNumHolidayServiceMessage OBJECT-TYPE
    SYNTAX      Counter32
    MAX-ACCESS  read-write
    STATUS      current
    DESCRIPTION 
        "This is the number of times that the Holiday Service message is played for a call to a Call Center. There is one instance of this counter for each group defined in the system."
    ::= { bwCallCenterGroupEntry 14 }

  bwCallCenterGroupNumForcedForwardingMessage OBJECT-TYPE
    SYNTAX      Counter32
    MAX-ACCESS  read-write
    STATUS      current
    DESCRIPTION 
        "This is the number of times that the Forced Forwarding message is played for a call to a Call Center. There is one instance of this counter for each group defined in the system."
    ::= { bwCallCenterGroupEntry 15 }

  bwCallCenterGroupNumOverflowMessage OBJECT-TYPE
    SYNTAX      Counter32
    MAX-ACCESS  read-write
    STATUS      current
    DESCRIPTION 
        "This is the number of times that the overflow message is played for a call to a Call Center.  There is one instance of this counter for each group defined in the system."
    ::= { bwCallCenterGroupEntry 16 }

  bwCallCenterGroupNumHoldReminder OBJECT-TYPE
    SYNTAX Counter32
    MAX-ACCESS read-write
    STATUS current
    DESCRIPTION "This is the number of times that the hold reminder is sent by the Call Center to an Agent.  There is one instance of this counter for each group defined in the system."
    ::= { bwCallCenterGroupEntry 17 }

  bwCallCenterGroupNumBouncedHeldCall OBJECT-TYPE
    SYNTAX Counter32
    MAX-ACCESS read-write
    STATUS current
    DESCRIPTION "This is the number of held calls (calls put on hold for specific amount of time by an agent) that bounces.  There is one instance of this counter for each group defined in the system."
    ::= { bwCallCenterGroupEntry 18 }

  bwCallCenterGroupNumAgentWhisperMessage OBJECT-TYPE
    SYNTAX Counter32
    MAX-ACCESS read-write
    STATUS current
    DESCRIPTION "This is the number of times that the agent whisper message is played for a call to a Call Center.  There is one instance of this counter for each group defined in the system."
    ::= { bwCallCenterGroupEntry 19 }

  bwCallCenterGroupNumOutgoingCall OBJECT-TYPE
    SYNTAX Counter32
    MAX-ACCESS read-write
    STATUS current
    DESCRIPTION "This is the number of times that a Call Center Agent makes an outgoing call as a Call Center.  There is one instance of this counter for each group defined in the system."
    ::= { bwCallCenterGroupEntry 20 }

  bwCallCenterGroupNumEscalatedCalls OBJECT-TYPE
    SYNTAX Counter32
    MAX-ACCESS read-write
    STATUS current
    DESCRIPTION "This is the number of times that an escalated call is successfully placed by an Agent to a Supervisor. There is one instance of this counter for each group defined in the system."
    ::= { bwCallCenterGroupEntry 21 }

  bwCallCenterGroupNumEscalatedCallsFailure OBJECT-TYPE
    SYNTAX Counter32
    MAX-ACCESS read-write
    STATUS current
    DESCRIPTION "This is the number of times that an escalated call failed to be placed from an Agent to a Supervisor. There is one instance of this counter for each group defined in the system."
    ::= { bwCallCenterGroupEntry 22 }

  bwCallCenterGroupNumEmergencyCalls OBJECT-TYPE
    SYNTAX      Counter32
    MAX-ACCESS  read-write
    STATUS      current
    DESCRIPTION 
        "This is the number of times that an emergency escalation is successful from an agent to a Supervisor. There is one instance of this counter for each group defined in the system."
    ::= { bwCallCenterGroupEntry 23 }

  bwCallCenterGroupNumEmergencyCallsFailure OBJECT-TYPE
    SYNTAX      Counter32
    MAX-ACCESS  read-write
    STATUS      current
    DESCRIPTION 
        "This is the number of times that an emergency invocatiion failed to be placed from an agent to a Supervisor.There is one instance of this counter for each group defined in the system."
    ::= { bwCallCenterGroupEntry 24 }

  bwCallCenterGroupNumQueuePositionMessage OBJECT-TYPE
    SYNTAX      Counter32
    MAX-ACCESS  read-write
    STATUS      current
    DESCRIPTION 
        "This is the number of times that the queue position message is played for a call to a Call Center.  There is one instance of this counter for each group defined in the system."
    ::= { bwCallCenterGroupEntry 25 }

  bwCallCenterGroupNumQueueWaitTimeMessage OBJECT-TYPE
    SYNTAX      Counter32
    MAX-ACCESS  read-write
    STATUS      current
    DESCRIPTION 
        "This is the number of times that the queue wait time message is played for a call to a Call Center.  There is one instance of this counter for each group defined in the system."
    ::= { bwCallCenterGroupEntry 26 }
    
  bwCallCenterGroupNumStrandedUnavailableMessage OBJECT-TYPE
    SYNTAX      Counter32
    MAX-ACCESS  read-write
    STATUS      current
    DESCRIPTION 
        "This is the number of times that the Stranded Calls - Unavailable message is triggered to be played for a call to a call center.  There is one instance of this counter for each group defined in the system."
-- @feature:149564
    ::= { bwCallCenterGroupEntry 27 }

  bwCallCenterNumCalls OBJECT-TYPE
    SYNTAX      Counter32
    MAX-ACCESS  read-write
    STATUS      current
    DESCRIPTION 
        "This is the number of incoming calls to a Call Center."
    ::= { callCenter 4 }

  bwCallCenterNumSizeOverflow OBJECT-TYPE
    SYNTAX      Counter32
    MAX-ACCESS  read-write
    STATUS      current
    DESCRIPTION 
        "This is the number of incoming calls (to a Call Center) that overflows based on the queue size."
    ::= { callCenter 5 }

  bwCallCenterNumTimeOverflow OBJECT-TYPE
    SYNTAX      Counter32
    MAX-ACCESS  read-write
    STATUS      current
    DESCRIPTION 
        "This is the number of incoming calls (to a Call Center) that overflows based on time."
    ::= { callCenter 6 }

  bwCallCenterNumBouncedCalls OBJECT-TYPE
    SYNTAX      Counter32
    MAX-ACCESS  read-write
    STATUS      current
    DESCRIPTION 
        "This is the number of calls (sent to an agent) that bounces."
    ::= { callCenter 7 }

  bwCallCenterNumEntranceMessage OBJECT-TYPE
    SYNTAX      Counter32
    MAX-ACCESS  read-write
    STATUS      current
    DESCRIPTION 
        "This is the number of times that the entrance message is played for a call to a Call Center."
    ::= { callCenter 8 }

  bwCallCenterNumComfortMessage OBJECT-TYPE
    SYNTAX      Counter32
    MAX-ACCESS  read-write
    STATUS      current
    DESCRIPTION 
        "This is the number of times that the comfort message is played for a call to a Call Center."
    ::= { callCenter 9 }

  bwCallCenterNumComfortBypassMessage OBJECT-TYPE
    SYNTAX      Counter32
    MAX-ACCESS  read-write
    STATUS      current
    DESCRIPTION 
        "This is the number of times that the comfort bypass message is played for a call to a Call Center."
    ::= { callCenter 10 }

  bwCallCenterNumStrandedMessage OBJECT-TYPE
    SYNTAX      Counter32
    MAX-ACCESS  read-write
    STATUS      current
    DESCRIPTION 
        "This is the number of times that the stranded message is played for a call to a Call Center."
    ::= { callCenter 11 }

  bwCallCenterNumNightServiceMessage OBJECT-TYPE
    SYNTAX      Counter32
    MAX-ACCESS  read-write
    STATUS      current
    DESCRIPTION 
        "This is the number of times that the Night Service message is played for a call to a Call Center."
    ::= { callCenter 12 }

  bwCallCenterNumManualNightServiceMessage OBJECT-TYPE
    SYNTAX      Counter32
    MAX-ACCESS  read-write
    STATUS      current
    DESCRIPTION 
        "This is the number of times that the manual Night Service message is played for a call to a Call Center."
    ::= { callCenter 13 }

  bwCallCenterNumHolidayServiceMessage OBJECT-TYPE
    SYNTAX      Counter32
    MAX-ACCESS  read-write
    STATUS      current
    DESCRIPTION 
        "This is the number of times that the Holiday Service message is played for a call to a Call Center."
    ::= { callCenter 14 }

  bwCallCenterNumForcedForwardingMessage OBJECT-TYPE
    SYNTAX      Counter32
    MAX-ACCESS  read-write
    STATUS      current
    DESCRIPTION 
        "This is the number of times that the Forced Forwarding message is played for a call to a Call Center."
    ::= { callCenter 15 }

  bwCallCenterNumOverflowMessage OBJECT-TYPE
    SYNTAX      Counter32
    MAX-ACCESS  read-write
    STATUS      current
    DESCRIPTION 
        "This is the number of times that the overflow message is played for a call to a Call Center."
    ::= { callCenter 16 }

  bwCallCenterNumHoldReminder OBJECT-TYPE
    SYNTAX Counter32
    MAX-ACCESS read-write
    STATUS current
    DESCRIPTION "This is the number of times that the hold reminder is sent by the Call Center to an Agent."
    ::= { callCenter 17 }

  bwCallCenterNumBouncedHeldCall OBJECT-TYPE
    SYNTAX Counter32
    MAX-ACCESS read-write
    STATUS current
    DESCRIPTION "This is the number of held calls (calls put on hold for specific amount of time by an agent) that bounces."
    ::= { callCenter 18 }

  bwCallCenterNumAgentWhisperMessage OBJECT-TYPE
    SYNTAX Counter32
    MAX-ACCESS read-write
    STATUS current
    DESCRIPTION "This is the number of times that the agent whisper message is played for a call to a Call Center."
    ::= { callCenter 19 }

  bwCallCenterNumOutgoingCall OBJECT-TYPE
    SYNTAX Counter32
    MAX-ACCESS read-write
    STATUS current
    DESCRIPTION "This is the number of times that a Call Center Agent makes an outgoing call as a Call Center."
    ::= { callCenter 20 }

  bwCallCenterNumEscalatedCalls OBJECT-TYPE
    SYNTAX Counter32
    MAX-ACCESS read-write
    STATUS current
    DESCRIPTION "This is the number of times that an escalated call is successfully placed by an Agent to a Supervisor."
    ::= { callCenter 21 }

  bwCallCenterNumEscalatedCallsFailure OBJECT-TYPE
    SYNTAX Counter32
    MAX-ACCESS read-write
    STATUS current
    DESCRIPTION "This is the number of times that an escalated call failed to be placed from an Agent to a Supervisor."
    ::= { callCenter 22 }

  bwCallCenterNumEmergencyCalls OBJECT-TYPE
    SYNTAX      Counter32
    MAX-ACCESS  read-write
    STATUS      current
    DESCRIPTION  "This is the number of times that an emergency escalation is successful from an agent to a Supervisor."
    ::= { callCenter 23 }

  bwCallCenterNumEmergencyCallsFailure OBJECT-TYPE
    SYNTAX      Counter32
    MAX-ACCESS  read-write
    STATUS      current
    DESCRIPTION  "This is the number of times that an emergency escalation failed to be placed from an agent to a Supervisor."
    ::= { callCenter 24 }

  bwCallCenterNumQueuePositionMessage OBJECT-TYPE
    SYNTAX      Counter32
    MAX-ACCESS  read-write
    STATUS      current
    DESCRIPTION "This is the number of times that the queue position message is played for a call to a Call Center."
    ::= { callCenter 25 }

  bwCallCenterNumQueueWaitTimeMessage OBJECT-TYPE
    SYNTAX      Counter32
    MAX-ACCESS  read-write
    STATUS      current
    DESCRIPTION "This is the number of times that the queue wait time message is played for a call to a Call Center."
    ::= { callCenter 26 }
    
  bwCallCenterNumStrandedUnavailableMessage OBJECT-TYPE
      SYNTAX      Counter32
      MAX-ACCESS  read-write
      STATUS      current
      DESCRIPTION 
          "This is the number of times that the Stranded Calls - Unavailable message is triggered to be played for a call to a call center."
-- @feature:149564
    ::= { callCenter 27 }

-- Services :: CallCenter :: ReportingQueue ...........................................

  callCenterReportingQueue OBJECT IDENTIFIER
    ::= { callCenter 28 }

  bwCallCenterReportingQueueSPTable OBJECT-TYPE
    SYNTAX      SEQUENCE OF BwCallCenterReportingQueueSPEntry
    MAX-ACCESS  not-accessible
    STATUS      obsolete
    DESCRIPTION 
        "Counters for Call Center Reporting Queue service measurements for service providers"
    ::= { callCenterReportingQueue 1 }

  bwCallCenterReportingQueueSPEntry OBJECT-TYPE
    SYNTAX      BwCallCenterReportingQueueSPEntry
    MAX-ACCESS  not-accessible
    STATUS      obsolete
    DESCRIPTION 
        "Each row contains the service counters for the Call Center Reporting Queue service for each service provider in the system"
    INDEX       { bwCallCenterReportingQueueSPIndex }
    ::= { bwCallCenterReportingQueueSPTable 1 }

  BwCallCenterReportingQueueSPEntry ::= SEQUENCE {
    bwCallCenterReportingQueueSPIndex                             Unsigned32,
    bwCallCenterReportingQueueSPID                                DisplayString,
    bwCallCenterReportingQueueSPEventsReported                    Counter32,
    bwCallCenterReportingQueueSPEventsIgnored                     Counter32,
    bwCallCenterReportingQueueSPEventsFailed                      Counter32,
    bwCallCenterReportingQueueSPAgentStartEventsReported          Counter32,
    bwCallCenterReportingQueueSPAgentBounceEventsReported         Counter32,
    bwCallCenterReportingQueueSPAgentAnswerEventsReported         Counter32,
    bwCallCenterReportingQueueSPAgentHoldEventsReported           Counter32,
    bwCallCenterReportingQueueSPAgentRetrieveEventsReported       Counter32,
    bwCallCenterReportingQueueSPAgentRedirectEventsReported       Counter32,
    bwCallCenterReportingQueueSPAgentReleaseEventsReported        Counter32,
    bwCallCenterReportingQueueSPAgentStateEventsReported          Counter32,
    bwCallCenterReportingQueueSPAgentDispCodeEventsReported       Counter32,
    bwCallCenterReportingQueueSPAgentConfigEventsReported         Counter32,
    bwCallCenterReportingQueueSPAcdOverflowSizeEventsReported     Counter32,
    bwCallCenterReportingQueueSPAcdOverflowTimeEventsReported     Counter32,
    bwCallCenterReportingQueueSPAcdForwardEventsReported          Counter32,
    bwCallCenterReportingQueueSPAcdHolidayServiceEventsReported   Counter32,
    bwCallCenterReportingQueueSPAcdNightServiceEventsReported     Counter32,
    bwCallCenterReportingQueueSPAcdAddEventsReported              Counter32,
    bwCallCenterReportingQueueSPAcdOfferEventsReported            Counter32,
    bwCallCenterReportingQueueSPAcdBounceEventsReported           Counter32,
    bwCallCenterReportingQueueSPAcdAnswerEventsReported           Counter32,
    bwCallCenterReportingQueueSPAcdTransferEventsReported         Counter32,
    bwCallCenterReportingQueueSPAcdReleaseEventsReported          Counter32,
    bwCallCenterReportingQueueSPAcdAbandonedEventsReported        Counter32,
    bwCallCenterReportingQueueSPAcdStrandedEventsReported         Counter32,
    bwCallCenterReportingQueueSPAcdEscapedEventsReported          Counter32,
    bwCallCenterReportingQueueSPAcdConfigEventsReported           Counter32,
    bwCallCenterReportingQueueSPAcdDnisConfigEventsReported       Counter32,
    bwCallCenterReportingQueueSPAcdSupervisorConfigEventsReported Counter32,
    bwCallCenterReportingQueueSPAcdAgentJoinEventsReported        Counter32,
    bwCallCenterReportingQueueSPAcdAgentAssignmentEventsReported  Counter32,
    bwCallCenterReportingQueueSPDatabaseFailures                  Counter32,
    bwCallCenterReportingQueueSPDatabaseInserts                   Counter32,
    bwCallCenterReportingQueueSPDatabaseUpdates                   Counter32,
    bwCallCenterReportingQueueSPDatabaseQueries                   Counter32,
    bwCallCenterReportingQueueSPDatabaseDeletes                   Counter32
    }

  bwCallCenterReportingQueueSPIndex OBJECT-TYPE
    SYNTAX      Unsigned32
    MAX-ACCESS  read-only
    STATUS      obsolete
    DESCRIPTION 
        "This column represents the index of the service provider in the system"
    ::= { bwCallCenterReportingQueueSPEntry 1 }

  bwCallCenterReportingQueueSPID OBJECT-TYPE
    SYNTAX      DisplayString
    MAX-ACCESS  read-only
    STATUS      obsolete
    DESCRIPTION 
        "This string represents a service provider ID"
    ::= { bwCallCenterReportingQueueSPEntry 2 }

  bwCallCenterReportingQueueSPEventsReported OBJECT-TYPE
    SYNTAX      Counter32
    MAX-ACCESS  read-write
    STATUS      obsolete
    DESCRIPTION 
        "Counts the number of Enhanced Reporting events reported by the call center service regardless of type.  There is one instance of this counter per service provider or enterprise defined in the system."
    ::= { bwCallCenterReportingQueueSPEntry 3 }

  bwCallCenterReportingQueueSPEventsIgnored OBJECT-TYPE
    SYNTAX      Counter32
    MAX-ACCESS  read-write
    STATUS      obsolete
    DESCRIPTION 
        "Counts the number of Enhanced Reporting events reported by the call center service that are ignored.  There is one instance of this counter per service provider or enterprise defined in the system.  While events are not generally ignored, certain situations cause this to occur.  One example is if the Enhanced Reporting is enabled for a call center, but no database has been configured to receive the reported data."
    ::= { bwCallCenterReportingQueueSPEntry 4 }

  bwCallCenterReportingQueueSPEventsFailed OBJECT-TYPE
    SYNTAX      Counter32
    MAX-ACCESS  read-write
    STATUS      obsolete
    DESCRIPTION 
        "Counts the number of Enhanced Reporting events reported by the call center service that failed to be recorded in the database.  There is one instance of this counter per service provider or enterprise defined in the system.  One example of failure is when events are reported while the database connection is down."
    ::= { bwCallCenterReportingQueueSPEntry 5 }

  bwCallCenterReportingQueueSPAgentStartEventsReported OBJECT-TYPE
    SYNTAX      Counter32
    MAX-ACCESS  read-write
    STATUS      obsolete
    DESCRIPTION 
        "Counts the number of agent start events reported by the call center service.  There is one instance of this counter per service provider or enterprise defined in the system."
    ::= { bwCallCenterReportingQueueSPEntry 6 }

  bwCallCenterReportingQueueSPAgentBounceEventsReported OBJECT-TYPE
    SYNTAX      Counter32
    MAX-ACCESS  read-write
    STATUS      obsolete
    DESCRIPTION 
        "Counts the number of agent bounce events reported by the call center service.  There is one instance of this counter per service provider or enterprise defined in the system."
    ::= { bwCallCenterReportingQueueSPEntry 7 }

  bwCallCenterReportingQueueSPAgentAnswerEventsReported OBJECT-TYPE
    SYNTAX      Counter32
    MAX-ACCESS  read-write
    STATUS      obsolete
    DESCRIPTION 
        "Counts the number of agent answer events reported by the call center service.  There is one instance of this counter per service provider or enterprise defined in the system."
    ::= { bwCallCenterReportingQueueSPEntry 8 }

  bwCallCenterReportingQueueSPAgentHoldEventsReported OBJECT-TYPE
    SYNTAX      Counter32
    MAX-ACCESS  read-write
    STATUS      obsolete
    DESCRIPTION 
        "Counts the number of agent hold events reported by the call center service.  There is one instance of this counter per service provider or enterprise defined in the system."
    ::= { bwCallCenterReportingQueueSPEntry 9 }

  bwCallCenterReportingQueueSPAgentRetrieveEventsReported OBJECT-TYPE
    SYNTAX      Counter32
    MAX-ACCESS  read-write
    STATUS      obsolete
    DESCRIPTION 
        "Counts the number of agent retrieve events reported by the call center service.  There is one instance of this counter per service provider or enterprise defined in the system."
    ::= { bwCallCenterReportingQueueSPEntry 10 }

  bwCallCenterReportingQueueSPAgentRedirectEventsReported OBJECT-TYPE
    SYNTAX      Counter32
    MAX-ACCESS  read-write
    STATUS      obsolete
    DESCRIPTION 
        "Counts the number of agent redirect events reported by the call center service.  There is one instance of this counter per service provider or enterprise defined in the system."
    ::= { bwCallCenterReportingQueueSPEntry 11 }

  bwCallCenterReportingQueueSPAgentReleaseEventsReported OBJECT-TYPE
    SYNTAX      Counter32
    MAX-ACCESS  read-write
    STATUS      obsolete
    DESCRIPTION 
        "Counts the number of agent release events reported by the call center service.  There is one instance of this counter per service provider or enterprise defined in the system."
    ::= { bwCallCenterReportingQueueSPEntry 12 }

  bwCallCenterReportingQueueSPAgentStateEventsReported OBJECT-TYPE
    SYNTAX      Counter32
    MAX-ACCESS  read-write
    STATUS      obsolete
    DESCRIPTION 
        "Counts the number of agent state events reported by the call center service.  There is one instance of this counter per service provider or enterprise defined in the system."
    ::= { bwCallCenterReportingQueueSPEntry 13 }

  bwCallCenterReportingQueueSPAgentDispCodeEventsReported OBJECT-TYPE
    SYNTAX      Counter32
    MAX-ACCESS  read-write
    STATUS      obsolete
    DESCRIPTION 
        "Counts the number of agent disposition code events reported by the call center service.  There is one instance of this counter per service provider or enterprise defined in the system."
    ::= { bwCallCenterReportingQueueSPEntry 14 }

  bwCallCenterReportingQueueSPAgentConfigEventsReported OBJECT-TYPE
    SYNTAX      Counter32
    MAX-ACCESS  read-write
    STATUS      obsolete
    DESCRIPTION 
        "Counts the number of agent configuration events reported by the call center service.  There is one instance of this counter per service provider or enterprise defined in the system."
    ::= { bwCallCenterReportingQueueSPEntry 15 }

  bwCallCenterReportingQueueSPAcdOverflowSizeEventsReported OBJECT-TYPE
    SYNTAX      Counter32
    MAX-ACCESS  read-write
    STATUS      obsolete
    DESCRIPTION 
        "Counts the number of agent configuration events reported by the call center service.  There is one instance of this counter per service provider or enterprise defined in the system."
    ::= { bwCallCenterReportingQueueSPEntry 16 }

  bwCallCenterReportingQueueSPAcdOverflowTimeEventsReported OBJECT-TYPE
    SYNTAX      Counter32
    MAX-ACCESS  read-write
    STATUS      obsolete
    DESCRIPTION 
        "Counts the number of ACD time overflow events reported by the call center service.  There is one instance of this counter per service provider or enterprise defined in the system."
    ::= { bwCallCenterReportingQueueSPEntry 17 }

  bwCallCenterReportingQueueSPAcdForwardEventsReported OBJECT-TYPE
    SYNTAX      Counter32
    MAX-ACCESS  read-write
    STATUS      obsolete
    DESCRIPTION 
        "Counts the number of ACD forward events reported by the call center service.  There is one instance of this counter per service provider or enterprise defined in the system."
    ::= { bwCallCenterReportingQueueSPEntry 18 }

  bwCallCenterReportingQueueSPAcdHolidayServiceEventsReported OBJECT-TYPE
    SYNTAX      Counter32
    MAX-ACCESS  read-write
    STATUS      obsolete
    DESCRIPTION 
        "Counts the number of ACD holiday service events reported by the call center service.  There is one instance of this counter per service provider or enterprise defined in the system."
    ::= { bwCallCenterReportingQueueSPEntry 19 }

  bwCallCenterReportingQueueSPAcdNightServiceEventsReported OBJECT-TYPE
    SYNTAX      Counter32
    MAX-ACCESS  read-write
    STATUS      obsolete
    DESCRIPTION 
        "Counts the number of ACD night service events reported by the call center service.  There is one instance of this counter per service provider or enterprise defined in the system."
    ::= { bwCallCenterReportingQueueSPEntry 20 }

  bwCallCenterReportingQueueSPAcdAddEventsReported OBJECT-TYPE
    SYNTAX      Counter32
    MAX-ACCESS  read-write
    STATUS      obsolete
    DESCRIPTION 
        "Counts the number of ACD add events reported by the call center service.  There is one instance of this counter per service provider or enterprise defined in the system."
    ::= { bwCallCenterReportingQueueSPEntry 21 }

  bwCallCenterReportingQueueSPAcdOfferEventsReported OBJECT-TYPE
    SYNTAX      Counter32
    MAX-ACCESS  read-write
    STATUS      obsolete
    DESCRIPTION 
        "Counts the number of ACD offer events reported by the call center service.  There is one instance of this counter per service provider or enterprise defined in the system."
    ::= { bwCallCenterReportingQueueSPEntry 22 }

  bwCallCenterReportingQueueSPAcdBounceEventsReported OBJECT-TYPE
    SYNTAX      Counter32
    MAX-ACCESS  read-write
    STATUS      obsolete
    DESCRIPTION 
        "Counts the number of ACD bounce events reported by the call center service.  There is one instance of this counter per service provider or enterprise defined in the system."
    ::= { bwCallCenterReportingQueueSPEntry 23 }

  bwCallCenterReportingQueueSPAcdAnswerEventsReported OBJECT-TYPE
    SYNTAX      Counter32
    MAX-ACCESS  read-write
    STATUS      obsolete
    DESCRIPTION 
        "Counts the number of ACD answer events reported by the call center service.  There is one instance of this counter per service provider or enterprise defined in the system."
    ::= { bwCallCenterReportingQueueSPEntry 24 }

  bwCallCenterReportingQueueSPAcdTransferEventsReported OBJECT-TYPE
    SYNTAX      Counter32
    MAX-ACCESS  read-write
    STATUS      obsolete
    DESCRIPTION 
        "Counts the number of ACD transfer events reported by the call center service.  There is one instance of this counter per service provider or enterprise defined in the system."
    ::= { bwCallCenterReportingQueueSPEntry 25 }

  bwCallCenterReportingQueueSPAcdReleaseEventsReported OBJECT-TYPE
    SYNTAX      Counter32
    MAX-ACCESS  read-write
    STATUS      obsolete
    DESCRIPTION 
        "Counts the number of ACD release events reported by the call center service.  There is one instance of this counter per service provider or enterprise defined in the system."
    ::= { bwCallCenterReportingQueueSPEntry 26 }

  bwCallCenterReportingQueueSPAcdAbandonedEventsReported OBJECT-TYPE
    SYNTAX      Counter32
    MAX-ACCESS  read-write
    STATUS      obsolete
    DESCRIPTION 
        "Counts the number of ACD abandoned events reported by the call center service.  There is one instance of this counter per service provider or enterprise defined in the system."
    ::= { bwCallCenterReportingQueueSPEntry 27 }

  bwCallCenterReportingQueueSPAcdStrandedEventsReported OBJECT-TYPE
    SYNTAX      Counter32
    MAX-ACCESS  read-write
    STATUS      obsolete
    DESCRIPTION 
        "Counts the number of ACD stranded events reported by the call center service.  There is one instance of this counter per service provider or enterprise defined in the system."
    ::= { bwCallCenterReportingQueueSPEntry 28 }

  bwCallCenterReportingQueueSPAcdEscapedEventsReported OBJECT-TYPE
    SYNTAX      Counter32
    MAX-ACCESS  read-write
    STATUS      obsolete
    DESCRIPTION 
        "Counts the number of ACD escaped events reported by the call center service.  There is one instance of this counter per service provider or enterprise defined in the system."
    ::= { bwCallCenterReportingQueueSPEntry 29 }

  bwCallCenterReportingQueueSPAcdConfigEventsReported OBJECT-TYPE
    SYNTAX      Counter32
    MAX-ACCESS  read-write
    STATUS      obsolete
    DESCRIPTION 
        "Counts the number of ACD configuration events reported by the call center service.  There is one instance of this counter per service provider or enterprise defined in the system."
    ::= { bwCallCenterReportingQueueSPEntry 30 }

  bwCallCenterReportingQueueSPAcdDnisConfigEventsReported OBJECT-TYPE
    SYNTAX      Counter32
    MAX-ACCESS  read-write
    STATUS      obsolete
    DESCRIPTION 
        "Counts the number of ACD DNIS configuration events reported by the call center service.  There is one instance of this counter per service provider or enterprise defined in the system."
    ::= { bwCallCenterReportingQueueSPEntry 31 }

  bwCallCenterReportingQueueSPAcdSupervisorConfigEventsReported OBJECT-TYPE
    SYNTAX      Counter32
    MAX-ACCESS  read-write
    STATUS      obsolete
    DESCRIPTION 
        "Counts the number of ACD supervisor configuration events reported by the call center service.  There is one instance of this counter per service provider or enterprise defined in the system."
    ::= { bwCallCenterReportingQueueSPEntry 32 }

  bwCallCenterReportingQueueSPAcdAgentJoinEventsReported OBJECT-TYPE
    SYNTAX      Counter32
    MAX-ACCESS  read-write
    STATUS      obsolete
    DESCRIPTION 
        "Counts the number of ACD agent join events reported by the call center service.  There is one instance of this counter per service provider or enterprise defined in the system."
    ::= { bwCallCenterReportingQueueSPEntry 33 }

  bwCallCenterReportingQueueSPAcdAgentAssignmentEventsReported OBJECT-TYPE
    SYNTAX      Counter32
    MAX-ACCESS  read-write
    STATUS      obsolete
    DESCRIPTION 
        "Counts the number of ACD agent assignment events reported by the call center service.  There is one instance of this counter per service provider or enterprise defined in the system."
    ::= { bwCallCenterReportingQueueSPEntry 34 }

  bwCallCenterReportingQueueSPDatabaseFailures OBJECT-TYPE
    SYNTAX      Counter32
    MAX-ACCESS  read-write
    STATUS      obsolete
    DESCRIPTION 
        "Counts the number of database failures incurred while recording data reported by the call center service.  There is one instance of this counter per service provider or enterprise defined in the system."
    ::= { bwCallCenterReportingQueueSPEntry 35 }

  bwCallCenterReportingQueueSPDatabaseInserts OBJECT-TYPE
    SYNTAX      Counter32
    MAX-ACCESS  read-write
    STATUS      obsolete
    DESCRIPTION 
        "Counts the number of database insert operations performed while recording data reported by the call center service.  There is one instance of this counter per service provider or enterprise defined in the system."
    ::= { bwCallCenterReportingQueueSPEntry 36 }

  bwCallCenterReportingQueueSPDatabaseUpdates OBJECT-TYPE
    SYNTAX      Counter32
    MAX-ACCESS  read-write
    STATUS      obsolete
    DESCRIPTION 
        "Counts the number of database update operations performed while recording data reported by the call center service.  There is one instance of this counter per service provider or enterprise defined in the system."
    ::= { bwCallCenterReportingQueueSPEntry 37 }

  bwCallCenterReportingQueueSPDatabaseQueries OBJECT-TYPE
    SYNTAX      Counter32
    MAX-ACCESS  read-write
    STATUS      obsolete
    DESCRIPTION 
        "Counts the number of database select operations performed while recording data reported by the call center service.  There is one instance of this counter per service provider or enterprise defined in the system."
    ::= { bwCallCenterReportingQueueSPEntry 38 }

  bwCallCenterReportingQueueSPDatabaseDeletes OBJECT-TYPE
    SYNTAX      Counter32
    MAX-ACCESS  read-write
    STATUS      obsolete
    DESCRIPTION 
        "Counts the number of database delete operations performed while recording data reported by the call center service.  There is one instance of this counter per service provider or enterprise defined in the system."
    ::= { bwCallCenterReportingQueueSPEntry 39 }

  bwCallCenterReportingQueueGroupTable OBJECT-TYPE
    SYNTAX      SEQUENCE OF BwCallCenterReportingQueueGroupEntry
    MAX-ACCESS  not-accessible
    STATUS      obsolete
    DESCRIPTION 
        "Counters for Call Center Reporting Queue service measurements for group"
    ::= { callCenterReportingQueue 2 }

  bwCallCenterReportingQueueGroupEntry OBJECT-TYPE
    SYNTAX      BwCallCenterReportingQueueGroupEntry
    MAX-ACCESS  not-accessible
    STATUS      obsolete
    DESCRIPTION 
        "Each row contains the service counters for the Call Center Reporting Queue service for each group in the system"
    INDEX       { bwCallCenterReportingQueueGroupIndex }
    ::= { bwCallCenterReportingQueueGroupTable 1 }

  BwCallCenterReportingQueueGroupEntry ::= SEQUENCE {
    bwCallCenterReportingQueueGroupIndex                             Unsigned32,
    bwCallCenterReportingQueueGroupID                                DisplayString,
    bwCallCenterReportingQueueGroupEventsReported                    Counter32,
    bwCallCenterReportingQueueGroupEventsIgnored                     Counter32,
    bwCallCenterReportingQueueGroupEventsFailed                      Counter32,
    bwCallCenterReportingQueueGroupAgentStartEventsReported          Counter32,
    bwCallCenterReportingQueueGroupAgentBounceEventsReported         Counter32,
    bwCallCenterReportingQueueGroupAgentAnswerEventsReported         Counter32,
    bwCallCenterReportingQueueGroupAgentHoldEventsReported           Counter32,
    bwCallCenterReportingQueueGroupAgentRetrieveEventsReported       Counter32,
    bwCallCenterReportingQueueGroupAgentRedirectEventsReported       Counter32,
    bwCallCenterReportingQueueGroupAgentReleaseEventsReported        Counter32,
    bwCallCenterReportingQueueGroupAgentStateEventsReported          Counter32,
    bwCallCenterReportingQueueGroupAgentDispCodeEventsReported       Counter32,
    bwCallCenterReportingQueueGroupAgentConfigEventsReported         Counter32,
    bwCallCenterReportingQueueGroupAcdOverflowSizeEventsReported     Counter32,
    bwCallCenterReportingQueueGroupAcdOverflowTimeEventsReported     Counter32,
    bwCallCenterReportingQueueGroupAcdForwardEventsReported          Counter32,
    bwCallCenterReportingQueueGroupAcdHolidayServiceEventsReported   Counter32,
    bwCallCenterReportingQueueGroupAcdNightServiceEventsReported     Counter32,
    bwCallCenterReportingQueueGroupAcdAddEventsReported              Counter32,
    bwCallCenterReportingQueueGroupAcdOfferEventsReported            Counter32,
    bwCallCenterReportingQueueGroupAcdBounceEventsReported           Counter32,
    bwCallCenterReportingQueueGroupAcdAnswerEventsReported           Counter32,
    bwCallCenterReportingQueueGroupAcdTransferEventsReported         Counter32,
    bwCallCenterReportingQueueGroupAcdReleaseEventsReported          Counter32,
    bwCallCenterReportingQueueGroupAcdAbandonedEventsReported        Counter32,
    bwCallCenterReportingQueueGroupAcdStrandedEventsReported         Counter32,
    bwCallCenterReportingQueueGroupAcdEscapedEventsReported          Counter32,
    bwCallCenterReportingQueueGroupAcdConfigEventsReported           Counter32,
    bwCallCenterReportingQueueGroupAcdDnisConfigEventsReported       Counter32,
    bwCallCenterReportingQueueGroupAcdSupervisorConfigEventsReported Counter32,
    bwCallCenterReportingQueueGroupAcdAgentJoinEventsReported        Counter32,
    bwCallCenterReportingQueueGroupAcdAgentAssignmentEventsReported  Counter32,
    bwCallCenterReportingQueueGroupDatabaseFailures                  Counter32,
    bwCallCenterReportingQueueGroupDatabaseInserts                   Counter32,
    bwCallCenterReportingQueueGroupDatabaseUpdates                   Counter32,
    bwCallCenterReportingQueueGroupDatabaseQueries                   Counter32,
    bwCallCenterReportingQueueGroupDatabaseDeletes                   Counter32
    }

  bwCallCenterReportingQueueGroupIndex OBJECT-TYPE
    SYNTAX      Unsigned32
    MAX-ACCESS  read-only
    STATUS      obsolete
    DESCRIPTION 
        "This column represents the index of the group in the system"
    ::= { bwCallCenterReportingQueueGroupEntry 1 }

  bwCallCenterReportingQueueGroupID OBJECT-TYPE
    SYNTAX      DisplayString
    MAX-ACCESS  read-only
    STATUS      obsolete
    DESCRIPTION 
        "This string represents a group ID"
    ::= { bwCallCenterReportingQueueGroupEntry 2 }

  bwCallCenterReportingQueueGroupEventsReported OBJECT-TYPE
    SYNTAX      Counter32
    MAX-ACCESS  read-write
    STATUS      obsolete
    DESCRIPTION 
        "Counts the number of Enhanced Reporting events reported by the call center service regardless of type.  There is one instance of this counter per group defined in the system."
    ::= { bwCallCenterReportingQueueGroupEntry 3 }

  bwCallCenterReportingQueueGroupEventsIgnored OBJECT-TYPE
    SYNTAX      Counter32
    MAX-ACCESS  read-write
    STATUS      obsolete
    DESCRIPTION 
        "Counts the number of Enhanced Reporting events reported by the call center service that are ignored.  There is one instance of this counter per group defined in the system.  While events are not generally ignored, certain situations cause this to occur.  One example is if the Enhanced Reporting is enabled for a call center, but no database has been configured to receive the reported data."
    ::= { bwCallCenterReportingQueueGroupEntry 4 }

  bwCallCenterReportingQueueGroupEventsFailed OBJECT-TYPE
    SYNTAX      Counter32
    MAX-ACCESS  read-write
    STATUS      obsolete
    DESCRIPTION 
        "Counts the number of Enhanced Reporting events reported by the call center service that failed to be recorded in the database.  There is one instance of this counter per group defined in the system.  One example of failure is when events are reported while the database connection is down."
    ::= { bwCallCenterReportingQueueGroupEntry 5 }

  bwCallCenterReportingQueueGroupAgentStartEventsReported OBJECT-TYPE
    SYNTAX      Counter32
    MAX-ACCESS  read-write
    STATUS      obsolete
    DESCRIPTION 
        "Counts the number of agent start events reported by the call center service.   There is one instance of this counter per group defined in the system."
    ::= { bwCallCenterReportingQueueGroupEntry 6 }

  bwCallCenterReportingQueueGroupAgentBounceEventsReported OBJECT-TYPE
    SYNTAX      Counter32
    MAX-ACCESS  read-write
    STATUS      obsolete
    DESCRIPTION 
        "Counts the number of agent bounce events reported by the call center service.  There is one instance of this counter per group defined in the system."
    ::= { bwCallCenterReportingQueueGroupEntry 7 }

  bwCallCenterReportingQueueGroupAgentAnswerEventsReported OBJECT-TYPE
    SYNTAX      Counter32
    MAX-ACCESS  read-write
    STATUS      obsolete
    DESCRIPTION 
        "Counts the number of agent answer events reported by the call center service.  There is one instance of this counter per service provider or enterprise defined in the system."
    ::= { bwCallCenterReportingQueueGroupEntry 8 }

  bwCallCenterReportingQueueGroupAgentHoldEventsReported OBJECT-TYPE
    SYNTAX      Counter32
    MAX-ACCESS  read-write
    STATUS      obsolete
    DESCRIPTION 
        "Counts the number of agent hold events reported by the call center service.   There is one instance of this counter per group defined in the system."
    ::= { bwCallCenterReportingQueueGroupEntry 9 }

  bwCallCenterReportingQueueGroupAgentRetrieveEventsReported OBJECT-TYPE
    SYNTAX      Counter32
    MAX-ACCESS  read-write
    STATUS      obsolete
    DESCRIPTION 
        "Counts the number of agent retrieve events reported by the call center service.   There is one instance of this counter per group defined in the system."
    ::= { bwCallCenterReportingQueueGroupEntry 10 }

  bwCallCenterReportingQueueGroupAgentRedirectEventsReported OBJECT-TYPE
    SYNTAX      Counter32
    MAX-ACCESS  read-write
    STATUS      obsolete
    DESCRIPTION 
        "Counts the number of agent redirect events reported by the call center service.   There is one instance of this counter per group defined in the system."
    ::= { bwCallCenterReportingQueueGroupEntry 11 }

  bwCallCenterReportingQueueGroupAgentReleaseEventsReported OBJECT-TYPE
    SYNTAX      Counter32
    MAX-ACCESS  read-write
    STATUS      obsolete
    DESCRIPTION 
        "Counts the number of agent release events reported by the call center service.   There is one instance of this counter per group defined in the system."
    ::= { bwCallCenterReportingQueueGroupEntry 12 }

  bwCallCenterReportingQueueGroupAgentStateEventsReported OBJECT-TYPE
    SYNTAX      Counter32
    MAX-ACCESS  read-write
    STATUS      obsolete
    DESCRIPTION 
        "Counts the number of agent state events reported by the call center service.   There is one instance of this counter per group defined in the system."
    ::= { bwCallCenterReportingQueueGroupEntry 13 }

  bwCallCenterReportingQueueGroupAgentDispCodeEventsReported OBJECT-TYPE
    SYNTAX      Counter32
    MAX-ACCESS  read-write
    STATUS      obsolete
    DESCRIPTION 
        "Counts the number of agent disposition code events reported by the call center service.   There is one instance of this counter per group defined in the system."
    ::= { bwCallCenterReportingQueueGroupEntry 14 }

  bwCallCenterReportingQueueGroupAgentConfigEventsReported OBJECT-TYPE
    SYNTAX      Counter32
    MAX-ACCESS  read-write
    STATUS      obsolete
    DESCRIPTION 
        "Counts the number of agent configuration events reported by the call center service.   There is one instance of this counter per group defined in the system."
    ::= { bwCallCenterReportingQueueGroupEntry 15 }

  bwCallCenterReportingQueueGroupAcdOverflowSizeEventsReported OBJECT-TYPE
    SYNTAX      Counter32
    MAX-ACCESS  read-write
    STATUS      obsolete
    DESCRIPTION 
        "Counts the number of ACD size overflow events reported by the call center service.   There is one instance of this counter per group defined in the system."
    ::= { bwCallCenterReportingQueueGroupEntry 16 }

  bwCallCenterReportingQueueGroupAcdOverflowTimeEventsReported OBJECT-TYPE
    SYNTAX      Counter32
    MAX-ACCESS  read-write
    STATUS      obsolete
    DESCRIPTION 
        "Counts the number of ACD time overflow events reported by the call center service.   There is one instance of this counter per group defined in the system."
    ::= { bwCallCenterReportingQueueGroupEntry 17 }

  bwCallCenterReportingQueueGroupAcdForwardEventsReported OBJECT-TYPE
    SYNTAX      Counter32
    MAX-ACCESS  read-write
    STATUS      obsolete
    DESCRIPTION 
        "Counts the number of ACD forward events reported by the call center service.   There is one instance of this counter per group defined in the system."
    ::= { bwCallCenterReportingQueueGroupEntry 18 }

  bwCallCenterReportingQueueGroupAcdHolidayServiceEventsReported OBJECT-TYPE
    SYNTAX      Counter32
    MAX-ACCESS  read-write
    STATUS      obsolete
    DESCRIPTION 
        "Counts the number of ACD holiday service events reported by the call center service.   There is one instance of this counter per group defined in the system."
    ::= { bwCallCenterReportingQueueGroupEntry 19 }

  bwCallCenterReportingQueueGroupAcdNightServiceEventsReported OBJECT-TYPE
    SYNTAX      Counter32
    MAX-ACCESS  read-write
    STATUS      obsolete
    DESCRIPTION 
        "Counts the number of ACD night service events reported by the call center service.   There is one instance of this counter per group defined in the system."
    ::= { bwCallCenterReportingQueueGroupEntry 20 }

  bwCallCenterReportingQueueGroupAcdAddEventsReported OBJECT-TYPE
    SYNTAX      Counter32
    MAX-ACCESS  read-write
    STATUS      obsolete
    DESCRIPTION 
        "Counts the number of ACD add events reported by the call center service.   There is one instance of this counter per group defined in the system."
    ::= { bwCallCenterReportingQueueGroupEntry 21 }

  bwCallCenterReportingQueueGroupAcdOfferEventsReported OBJECT-TYPE
    SYNTAX      Counter32
    MAX-ACCESS  read-write
    STATUS      obsolete
    DESCRIPTION 
        "Counts the number of ACD offer events reported by the call center service.   There is one instance of this counter per group defined in the system."
    ::= { bwCallCenterReportingQueueGroupEntry 22 }

  bwCallCenterReportingQueueGroupAcdBounceEventsReported OBJECT-TYPE
    SYNTAX      Counter32
    MAX-ACCESS  read-write
    STATUS      obsolete
    DESCRIPTION 
        "Counts the number of ACD bounce events reported by the call center service.   There is one instance of this counter per group defined in the system."
    ::= { bwCallCenterReportingQueueGroupEntry 23 }

  bwCallCenterReportingQueueGroupAcdAnswerEventsReported OBJECT-TYPE
    SYNTAX      Counter32
    MAX-ACCESS  read-write
    STATUS      obsolete
    DESCRIPTION 
        "Counts the number of ACD answer events reported by the call center service.   There is one instance of this counter per group defined in the system."
    ::= { bwCallCenterReportingQueueGroupEntry 24 }

  bwCallCenterReportingQueueGroupAcdTransferEventsReported OBJECT-TYPE
    SYNTAX      Counter32
    MAX-ACCESS  read-write
    STATUS      obsolete
    DESCRIPTION 
        "Counts the number of ACD transfer events reported by the call center service.   There is one instance of this counter per group defined in the system."
    ::= { bwCallCenterReportingQueueGroupEntry 25 }

  bwCallCenterReportingQueueGroupAcdReleaseEventsReported OBJECT-TYPE
    SYNTAX      Counter32
    MAX-ACCESS  read-write
    STATUS      obsolete
    DESCRIPTION 
        "Counts the number of ACD release events reported by the call center service.   There is one instance of this counter per group defined in the system."
    ::= { bwCallCenterReportingQueueGroupEntry 26 }

  bwCallCenterReportingQueueGroupAcdAbandonedEventsReported OBJECT-TYPE
    SYNTAX      Counter32
    MAX-ACCESS  read-write
    STATUS      obsolete
    DESCRIPTION 
        "Counts the number of ACD abandoned events reported by the call center service.   There is one instance of this counter per group defined in the system."
    ::= { bwCallCenterReportingQueueGroupEntry 27 }

  bwCallCenterReportingQueueGroupAcdStrandedEventsReported OBJECT-TYPE
    SYNTAX      Counter32
    MAX-ACCESS  read-write
    STATUS      obsolete
    DESCRIPTION 
        "Counts the number of ACD stranded events reported by the call center service.   There is one instance of this counter per group defined in the system."
    ::= { bwCallCenterReportingQueueGroupEntry 28 }

  bwCallCenterReportingQueueGroupAcdEscapedEventsReported OBJECT-TYPE
    SYNTAX      Counter32
    MAX-ACCESS  read-write
    STATUS      obsolete
    DESCRIPTION 
        "Counts the number of ACD escaped events reported by the call center service.   There is one instance of this counter per group defined in the system."
    ::= { bwCallCenterReportingQueueGroupEntry 29 }

  bwCallCenterReportingQueueGroupAcdConfigEventsReported OBJECT-TYPE
    SYNTAX      Counter32
    MAX-ACCESS  read-write
    STATUS      obsolete
    DESCRIPTION 
        "Counts the number of ACD configuration events reported by the call center service.   There is one instance of this counter per group defined in the system."
    ::= { bwCallCenterReportingQueueGroupEntry 30 }

  bwCallCenterReportingQueueGroupAcdDnisConfigEventsReported OBJECT-TYPE
    SYNTAX      Counter32
    MAX-ACCESS  read-write
    STATUS      obsolete
    DESCRIPTION 
        "Counts the number of ACD DNIS configuration events reported by the call center service.   There is one instance of this counter per group defined in the system."
    ::= { bwCallCenterReportingQueueGroupEntry 31 }

  bwCallCenterReportingQueueGroupAcdSupervisorConfigEventsReported OBJECT-TYPE
    SYNTAX      Counter32
    MAX-ACCESS  read-write
    STATUS      obsolete
    DESCRIPTION 
        "Counts the number of ACD supervisor configuration events reported by the call center service.   There is one instance of this counter per group defined in the system."
    ::= { bwCallCenterReportingQueueGroupEntry 32 }

  bwCallCenterReportingQueueGroupAcdAgentJoinEventsReported OBJECT-TYPE
    SYNTAX      Counter32
    MAX-ACCESS  read-write
    STATUS      obsolete
    DESCRIPTION 
        "Counts the number of ACD agent join events reported by the call center service.   There is one instance of this counter per group defined in the system."
    ::= { bwCallCenterReportingQueueGroupEntry 33 }

  bwCallCenterReportingQueueGroupAcdAgentAssignmentEventsReported OBJECT-TYPE
    SYNTAX      Counter32
    MAX-ACCESS  read-write
    STATUS      obsolete
    DESCRIPTION 
        "Counts the number of ACD agent assignment events reported by the call center service.   There is one instance of this counter per group defined in the system."
    ::= { bwCallCenterReportingQueueGroupEntry 34 }

  bwCallCenterReportingQueueGroupDatabaseFailures OBJECT-TYPE
    SYNTAX      Counter32
    MAX-ACCESS  read-write
    STATUS      obsolete
    DESCRIPTION 
        "Counts the number of database failures incurred while recording data reported by the call center service.  There is one instance of this counter per group defined in the system."
    ::= { bwCallCenterReportingQueueGroupEntry 35 }

  bwCallCenterReportingQueueGroupDatabaseInserts OBJECT-TYPE
    SYNTAX      Counter32
    MAX-ACCESS  read-write
    STATUS      obsolete
    DESCRIPTION 
        "Counts the number of database insert operations performed while recording data reported by the call center service.   There is one instance of this counter per group defined in the system."
    ::= { bwCallCenterReportingQueueGroupEntry 36 }

  bwCallCenterReportingQueueGroupDatabaseUpdates OBJECT-TYPE
    SYNTAX      Counter32
    MAX-ACCESS  read-write
    STATUS      obsolete
    DESCRIPTION 
        "Counts the number of database update operations performed while recording data reported by the call center service.   There is one instance of this counter per group defined in the system."
    ::= { bwCallCenterReportingQueueGroupEntry 37 }

  bwCallCenterReportingQueueGroupDatabaseQueries OBJECT-TYPE
    SYNTAX      Counter32
    MAX-ACCESS  read-write
    STATUS      obsolete
    DESCRIPTION 
        "Counts the number of database select operations performed while recording data reported by the call center service.   There is one instance of this counter per group defined in the system."
    ::= { bwCallCenterReportingQueueGroupEntry 38 }

  bwCallCenterReportingQueueGroupDatabaseDeletes OBJECT-TYPE
    SYNTAX      Counter32
    MAX-ACCESS  read-write
    STATUS      obsolete
    DESCRIPTION 
        "Counts the number of database delete operations performed while recording data reported by the call center service.   There is one instance of this counter per group defined in the system."
    ::= { bwCallCenterReportingQueueGroupEntry 39 }

  bwCallCenterReportingQueueEventsReported OBJECT-TYPE
    SYNTAX      Counter32
    MAX-ACCESS  read-write
    STATUS      current
    DESCRIPTION 
        "This counter represents the number of Enhanced Reporting events reported by the Call Center service regardless of type.  Note that more specific counters can also be incremented."
    ::= { callCenterReportingQueue 3 }

  bwCallCenterReportingQueueEventsIgnored OBJECT-TYPE
    SYNTAX      Counter32
    MAX-ACCESS  read-write
    STATUS      current
    DESCRIPTION 
        "This counter represents the number of Enhanced Reporting events reported by the Call Center service, which are ignored.  While events are not generally ignored, certain situations cause this to occur.  One example is when Enhanced Reporting is enabled for a call center, but no database has been configured to receive the reported data."
    ::= { callCenterReportingQueue 4 }

  bwCallCenterReportingQueueEventsFailed OBJECT-TYPE
    SYNTAX      Counter32
    MAX-ACCESS  read-write
    STATUS      current
    DESCRIPTION 
        "This counter represents the number of Enhanced Reporting events reported by the Call Center service, which failed to be recorded in the database.  One example of a failure is when events are reported while the database connection is down."
    ::= { callCenterReportingQueue 5 }

  bwCallCenterReportingQueueAgentStartEventsReported OBJECT-TYPE
    SYNTAX      Counter32
    MAX-ACCESS  read-write
    STATUS      obsolete
    DESCRIPTION 
        "This counter represents the number of agent start events reported by the call center service."
    ::= { callCenterReportingQueue 6 }

   bwCallCenterReportingQueueAgentBounceEventsReported OBJECT-TYPE
    SYNTAX      Counter32
    MAX-ACCESS  read-write
    STATUS      obsolete
    DESCRIPTION 
        "This counter represents the number of agent bounce events reported by the call center service."
    ::= { callCenterReportingQueue 7 }

  bwCallCenterReportingQueueAgentAnswerEventsReported OBJECT-TYPE
    SYNTAX      Counter32
    MAX-ACCESS  read-write
    STATUS      obsolete
    DESCRIPTION 
        "This counter represents the number of agent answer events reported by the call center service."
    ::= { callCenterReportingQueue 8 }

  bwCallCenterReportingQueueAgentHoldEventsReported OBJECT-TYPE
    SYNTAX      Counter32
    MAX-ACCESS  read-write
    STATUS      obsolete
    DESCRIPTION 
        "This counter represents the number of agent hold events reported by the call center service."
    ::= { callCenterReportingQueue 9 }

  bwCallCenterReportingQueueAgentRetrieveEventsReported OBJECT-TYPE
    SYNTAX      Counter32
    MAX-ACCESS  read-write
    STATUS      obsolete
    DESCRIPTION 
        "This counter represents the number of agent retrieve events reported by the call center service."
    ::= { callCenterReportingQueue 10 }

  bwCallCenterReportingQueueAgentRedirectEventsReported OBJECT-TYPE
    SYNTAX      Counter32
    MAX-ACCESS  read-write
    STATUS      obsolete
    DESCRIPTION 
        "This counter represents the number of agent redirect events reported by the call center service."
    ::= { callCenterReportingQueue 11 }

  bwCallCenterReportingQueueAgentReleaseEventsReported OBJECT-TYPE
    SYNTAX      Counter32
    MAX-ACCESS  read-write
    STATUS      obsolete
    DESCRIPTION 
        "This counter represents the number of agent release events reported by the call center service."
    ::= { callCenterReportingQueue 12 }

  bwCallCenterReportingQueueAgentStateEventsReported OBJECT-TYPE
    SYNTAX      Counter32
    MAX-ACCESS  read-write
    STATUS      obsolete
    DESCRIPTION 
        "This counter represents the number of agent state events reported by the call center service."
    ::= { callCenterReportingQueue 13 }

  bwCallCenterReportingQueueAgentDispCodeEventsReported OBJECT-TYPE
    SYNTAX      Counter32
    MAX-ACCESS  read-write
    STATUS      obsolete
    DESCRIPTION 
        "This counter represents the number of agent disposition code events reported by the call center service."
    ::= { callCenterReportingQueue 14 }

  bwCallCenterReportingQueueAgentConfigEventsReported OBJECT-TYPE
    SYNTAX      Counter32
    MAX-ACCESS  read-write
    STATUS      obsolete
    DESCRIPTION 
        "This counter represents the number of agent configuration events reported by the call center service."
    ::= { callCenterReportingQueue 15 }

  bwCallCenterReportingQueueAcdOverflowSizeEventsReported OBJECT-TYPE
    SYNTAX      Counter32
    MAX-ACCESS  read-write
    STATUS      obsolete
    DESCRIPTION 
        "This counter represents the number of ACD size overflow events reported by the call center service."
    ::= { callCenterReportingQueue 16 }

  bwCallCenterReportingQueueAcdOverflowTimeEventsReported OBJECT-TYPE
    SYNTAX      Counter32
    MAX-ACCESS  read-write
    STATUS      obsolete
    DESCRIPTION 
        "This counter represents the number of ACD time overflow events reported by the call center service."
    ::= { callCenterReportingQueue 17 }

  bwCallCenterReportingQueueAcdForwardEventsReported OBJECT-TYPE
    SYNTAX      Counter32
    MAX-ACCESS  read-write
    STATUS      obsolete
    DESCRIPTION 
        "This counter represents the number of ACD forward events reported by the call center service."
    ::= { callCenterReportingQueue 18 }

  bwCallCenterReportingQueueAcdHolidayServiceEventsReported OBJECT-TYPE
    SYNTAX      Counter32
    MAX-ACCESS  read-write
    STATUS      obsolete
    DESCRIPTION 
        "This counter represents the number of ACD holiday service events reported by the call center service."
    ::= { callCenterReportingQueue 19 }

  bwCallCenterReportingQueueAcdNightServiceEventsReported OBJECT-TYPE
    SYNTAX      Counter32
    MAX-ACCESS  read-write
    STATUS      obsolete
    DESCRIPTION 
        "This counter represents the number of ACD night service events reported by the call center service."
    ::= { callCenterReportingQueue 20 }

  bwCallCenterReportingQueueAcdAddEventsReported OBJECT-TYPE
    SYNTAX      Counter32
    MAX-ACCESS  read-write
    STATUS      obsolete
    DESCRIPTION 
        "This counter represents the number of ACD add events reported by the call center service."
    ::= { callCenterReportingQueue 21 }

  bwCallCenterReportingQueueAcdOfferEventsReported OBJECT-TYPE
    SYNTAX      Counter32
    MAX-ACCESS  read-write
    STATUS      obsolete
    DESCRIPTION 
        "This counter represents the number of ACD offer events reported by the call center service."
    ::= { callCenterReportingQueue 22 }

  bwCallCenterReportingQueueAcdBounceEventsReported OBJECT-TYPE
    SYNTAX      Counter32
    MAX-ACCESS  read-write
    STATUS      obsolete
    DESCRIPTION 
        "This counter represents the number of ACD bounce events reported by the call center service."
    ::= { callCenterReportingQueue 23 }

  bwCallCenterReportingQueueAcdAnswerEventsReported OBJECT-TYPE
    SYNTAX      Counter32
    MAX-ACCESS  read-write
    STATUS      obsolete
    DESCRIPTION 
        "This counter represents the number of ACD answer events reported by the call center service."
    ::= { callCenterReportingQueue 24 }

  bwCallCenterReportingQueueAcdTransferEventsReported OBJECT-TYPE
    SYNTAX      Counter32
    MAX-ACCESS  read-write
    STATUS      obsolete
    DESCRIPTION 
        "This counter represents the number of ACD transfer events reported by the call center service."
    ::= { callCenterReportingQueue 25 }

  bwCallCenterReportingQueueAcdReleaseEventsReported OBJECT-TYPE
    SYNTAX      Counter32
    MAX-ACCESS  read-write
    STATUS      obsolete
    DESCRIPTION 
        "This counter represents the number of ACD release events reported by the call center service."
    ::= { callCenterReportingQueue 26 }

  bwCallCenterReportingQueueAcdAbandonedEventsReported OBJECT-TYPE
    SYNTAX      Counter32
    MAX-ACCESS  read-write
    STATUS      obsolete
    DESCRIPTION 
        "This counter represents the number of ACD abandoned events reported by the call center service."
    ::= { callCenterReportingQueue 27 }

  bwCallCenterReportingQueueAcdStrandedEventsReported OBJECT-TYPE
    SYNTAX      Counter32
    MAX-ACCESS  read-write
    STATUS      obsolete
    DESCRIPTION 
        "This counter represents the number of ACD stranded events reported by the call center service."
    ::= { callCenterReportingQueue 28 }

  bwCallCenterReportingQueueAcdEscapedEventsReported OBJECT-TYPE
    SYNTAX      Counter32
    MAX-ACCESS  read-write
    STATUS      obsolete
    DESCRIPTION 
        "This counter represents the number of ACD escaped events reported by the call center service."
    ::= { callCenterReportingQueue 29 }

  bwCallCenterReportingQueueAcdConfigEventsReported OBJECT-TYPE
    SYNTAX      Counter32
    MAX-ACCESS  read-write
    STATUS      obsolete
    DESCRIPTION 
        "This counter represents the number of ACD configuration events reported by the call center service."
    ::= { callCenterReportingQueue 30 }

  bwCallCenterReportingQueueAcdDnisConfigEventsReported OBJECT-TYPE
    SYNTAX      Counter32
    MAX-ACCESS  read-write
    STATUS      obsolete
    DESCRIPTION 
        "This counter represents the number of ACD DNIS configuration events reported by the call center service."
    ::= { callCenterReportingQueue 31 }

  bwCallCenterReportingQueueAcdSupervisorConfigEventsReported OBJECT-TYPE
    SYNTAX      Counter32
    MAX-ACCESS  read-write
    STATUS      obsolete
    DESCRIPTION 
        "This counter represents the number of ACD supervisor configuration events reported by the call center service."
    ::= { callCenterReportingQueue 32 }

  bwCallCenterReportingQueueAcdAgentJoinEventsReported OBJECT-TYPE
    SYNTAX      Counter32
    MAX-ACCESS  read-write
    STATUS      obsolete
    DESCRIPTION 
        "This counter represents the number of ACD agent join events reported by the call center service."
    ::= { callCenterReportingQueue 33 }

  bwCallCenterReportingQueueAcdAgentAssignmentEventsReported OBJECT-TYPE
    SYNTAX      Counter32
    MAX-ACCESS  read-write
    STATUS      obsolete
    DESCRIPTION 
        "This counter represents the number of ACD agent assignment events reported by the call center service."
    ::= { callCenterReportingQueue 34 }

  bwCallCenterReportingQueueDatabaseFailures OBJECT-TYPE
    SYNTAX      Counter32
    MAX-ACCESS  read-write
    STATUS      current
    DESCRIPTION 
        "This counter represents the number of database failures incurred while recording data reported by the call center service."
    ::= { callCenterReportingQueue 35 }

  bwCallCenterReportingQueueDatabaseInserts OBJECT-TYPE
    SYNTAX      Counter32
    MAX-ACCESS  read-write
    STATUS      current
    DESCRIPTION 
        "This counter represents the number of database insert operations performed while recording data reported by the call center service."
    ::= { callCenterReportingQueue 36 }

  bwCallCenterReportingQueueDatabaseUpdates OBJECT-TYPE
    SYNTAX      Counter32
    MAX-ACCESS  read-write
    STATUS      current
    DESCRIPTION 
        "This counter represents the number of database update operations performed while recording data reported by the call center service."
    ::= { callCenterReportingQueue 37 }

  bwCallCenterReportingQueueDatabaseQueries OBJECT-TYPE
    SYNTAX      Counter32
    MAX-ACCESS  read-write
    STATUS      current
    DESCRIPTION 
        "This counter represents the number of database select operations performed while recording data reported by the call center service."
    ::= { callCenterReportingQueue 38 }

  bwCallCenterReportingQueueDatabaseDeletes OBJECT-TYPE
    SYNTAX      Counter32
    MAX-ACCESS  read-write
    STATUS      current
    DESCRIPTION 
        "This counter represents the number of database delete operations performed while recording data reported by the call center service."
    ::= { callCenterReportingQueue 39 }

  bwCallCenterReportingQueueEventResets OBJECT-TYPE
    SYNTAX      Counter32
    MAX-ACCESS  read-write
    STATUS      current
    DESCRIPTION 
        "When set to a value other than '0', all event statistics stored in the callCenterReportingQueueEventTable are reset to '0'."
    ::= { callCenterReportingQueue 40 }

  bwCallCenterReportingQueueEventTable OBJECT-TYPE
    SYNTAX      SEQUENCE OF BwCallCenterReportingQueueEventEntry
    MAX-ACCESS  not-accessible
    STATUS      current
    DESCRIPTION 
        "Counters for Call Center Reporting Queue measurements"
    ::= { callCenterReportingQueue 41 }

  bwCallCenterReportingQueueEventEntry OBJECT-TYPE
    SYNTAX      BwCallCenterReportingQueueEventEntry
    MAX-ACCESS  not-accessible
    STATUS      current
    DESCRIPTION 
        "Each row contains the service counters for the Call Center Reporting Queue service"
    INDEX       { bwCallCenterReportingQueueEventIndex }
    ::= { bwCallCenterReportingQueueEventTable 1 }

  BwCallCenterReportingQueueEventEntry ::= SEQUENCE {
    bwCallCenterReportingQueueEventIndex      Unsigned32,
    bwCallCenterReportingQueueEventName       DisplayString,
    bwCallCenterReportingQueueEventCount      Counter32 }

  bwCallCenterReportingQueueEventIndex OBJECT-TYPE
    SYNTAX      Unsigned32
    MAX-ACCESS  read-write
    STATUS      current
    DESCRIPTION 
        "This is the index of the queue event table entry."
    ::= { bwCallCenterReportingQueueEventEntry 1 }

  bwCallCenterReportingQueueEventName OBJECT-TYPE
    SYNTAX      DisplayString
    MAX-ACCESS  read-write
    STATUS      current
    DESCRIPTION 
        "This displays the name of the queue event table entry."
    ::= { bwCallCenterReportingQueueEventEntry 2 }

  bwCallCenterReportingQueueEventCount OBJECT-TYPE
    SYNTAX      Counter32
    MAX-ACCESS  read-write
    STATUS      current
    DESCRIPTION 
        "This displays the number of events reported for the specific event table entry."
    ::= { bwCallCenterReportingQueueEventEntry 3 }

-- Services :: CFGNA  ...........................................

  bwCFGNAForward OBJECT-TYPE
    SYNTAX      Counter32
    MAX-ACCESS  read-write
    STATUS      current
    DESCRIPTION 
        "This is the number of times Call Forwarding Group No Answer (CFGNA) has forwarded from one Hunt Group agent to another."
    ::= { callForwardGroupNoAnswer 1 }

  bwCFGNAOverflowForward OBJECT-TYPE
    SYNTAX      Counter32
    MAX-ACCESS  read-write
    STATUS      current
    DESCRIPTION 
        "This is the number of times Call Forwarding Group No Answer rolls over to the first visited Hunt Group agent and the call forwards to the external destination."
    ::= { callForwardGroupNoAnswer 2 }

  bwCFGNAOverflowNoForward OBJECT-TYPE
    SYNTAX      Counter32
    MAX-ACCESS  read-write
    STATUS      current
    DESCRIPTION 
        "This is the number of times Call Forwarding Group No Answer rolls over to the first visited Hunt Group agent and the call is given temporarily unavailable treatment."
    ::= { callForwardGroupNoAnswer 3 }

  bwCFGNASPTable OBJECT-TYPE
    SYNTAX      SEQUENCE OF BwCFGNASPEntry
    MAX-ACCESS  not-accessible
    STATUS      current
    DESCRIPTION 
        "Counters for Call Center service measurements for service providers"
    ::= { callForwardGroupNoAnswer 4 }

  bwCFGNASPEntry OBJECT-TYPE
    SYNTAX      BwCFGNASPEntry
    MAX-ACCESS  not-accessible
    STATUS      current
    DESCRIPTION 
        "Each row contains the service counters for the Call Forward Group No Answer service for each service provider in the system"
    INDEX       { bwCFGNASPIndex }
    ::= { bwCFGNASPTable 1 }

  BwCFGNASPEntry ::= SEQUENCE {
    bwCFGNASPIndex              Unsigned32,
    bwCFGNASPID                 DisplayString,
    bwCFGNASPForward            Counter32,
    bwCFGNASPOverflowForward    Counter32,
    bwCFGNASPOverflowNoForward  Counter32,
    bwCFGNASPExternalForward    Counter32,
    bwCFGNASPExternalNoForward  Counter32
  }

  bwCFGNASPIndex OBJECT-TYPE
    SYNTAX      Unsigned32
    MAX-ACCESS  read-only
    STATUS      current
    DESCRIPTION 
        "This column represents the index of the service provider in the system"
    ::= { bwCFGNASPEntry 1 }

  bwCFGNASPID OBJECT-TYPE
    SYNTAX      DisplayString
    MAX-ACCESS  read-only
    STATUS      current
    DESCRIPTION 
        "This string represents a service provider ID"
    ::= { bwCFGNASPEntry 2 }

  bwCFGNASPForward OBJECT-TYPE
    SYNTAX      Counter32
    MAX-ACCESS  read-write
    STATUS      current
    DESCRIPTION 
        "This is the number of times Call Forwarding Group No Answer has forwarded from one Hunt Group agent to another."
    ::= { bwCFGNASPEntry 3 }

  bwCFGNASPOverflowForward OBJECT-TYPE
    SYNTAX      Counter32
    MAX-ACCESS  read-write
    STATUS      current
    DESCRIPTION 
        "This is the number of times Call Forwarding Group No Answer rolls over to the first visited Hunt Group agent and the call forwards to the external destination."
    ::= { bwCFGNASPEntry 4 }

  bwCFGNASPOverflowNoForward OBJECT-TYPE
    SYNTAX      Counter32
    MAX-ACCESS  read-write
    STATUS      current
    DESCRIPTION 
        "This is the number of times Call Forwarding Group No Answer rolls over to the first visited Hunt Group agent and the call is given temporarily unavailable treatment."
    ::= { bwCFGNASPEntry 5 }

  bwCFGNASPExternalForward OBJECT-TYPE
    SYNTAX      Counter32
    MAX-ACCESS  read-write
    STATUS      current
    DESCRIPTION 
        "This is the number of times Call Forwarding Group No Answer External has forwarded a Hunt Group call under the service provider."
    ::= { bwCFGNASPEntry 6 }

  bwCFGNASPExternalNoForward OBJECT-TYPE
    SYNTAX      Counter32
    MAX-ACCESS  read-write
    STATUS      current
    DESCRIPTION 
        "This is the number of times Call Forwarding Group No Answer External has given Temporarily Unavailable treatment to a Hunt Group call under the service provider."
    ::= { bwCFGNASPEntry 7 }

  bwCFGNAGroupTable OBJECT-TYPE
    SYNTAX      SEQUENCE OF BwCFGNAGroupEntry
    MAX-ACCESS  not-accessible
    STATUS      current
    DESCRIPTION 
        "Counters for Call Center service measurements for groups"
    ::= { callForwardGroupNoAnswer 5 }

  bwCFGNAGroupEntry OBJECT-TYPE
    SYNTAX      BwCFGNAGroupEntry
    MAX-ACCESS  not-accessible
    STATUS      current
    DESCRIPTION 
        "Each row contains the service counters for the Call Forward Group No Answer service for each group in the system"
    INDEX       { bwCFGNAGroupIndex }
    ::= { bwCFGNAGroupTable 1 }

  BwCFGNAGroupEntry ::= SEQUENCE {
    bwCFGNAGroupIndex               Unsigned32,
    bwCFGNAGroupID                  DisplayString,
    bwCFGNAGroupForward             Counter32,
    bwCFGNAGroupOverflowForward     Counter32,
    bwCFGNAGroupOverflowNoForward   Counter32,
    bwCFGNAGroupExternalForward     Counter32,
    bwCFGNAGroupExternalNoForward   Counter32
  }

  bwCFGNAGroupIndex OBJECT-TYPE
    SYNTAX      Unsigned32
    MAX-ACCESS  read-only
    STATUS      current
    DESCRIPTION 
        "This column represents the index of the group in the system"
    ::= { bwCFGNAGroupEntry 1 }

  bwCFGNAGroupID OBJECT-TYPE
    SYNTAX      DisplayString
    MAX-ACCESS  read-only
    STATUS      current
    DESCRIPTION 
        "This string represents a group ID"
    ::= { bwCFGNAGroupEntry 2 }

  bwCFGNAGroupForward OBJECT-TYPE
    SYNTAX      Counter32
    MAX-ACCESS  read-write
    STATUS      current
    DESCRIPTION 
        "This is the number of times Call Forwarding Group No Answer has forwarded from one Hunt Group agent to another."
    ::= { bwCFGNAGroupEntry 3 }

  bwCFGNAGroupOverflowForward OBJECT-TYPE
    SYNTAX      Counter32
    MAX-ACCESS  read-write
    STATUS      current
    DESCRIPTION 
        "This is the number of times Call Forwarding Group No Answer rolls over to the first visited Hunt Group agent and the call forwards to the external destination."
    ::= { bwCFGNAGroupEntry 4 }

  bwCFGNAGroupOverflowNoForward OBJECT-TYPE
    SYNTAX      Counter32
    MAX-ACCESS  read-write
    STATUS      current
    DESCRIPTION 
        "This is the number of times Call Forwarding Group No Answer rolls over to the first visited Hunt Group agent and the call is given temporarily unavailable treatment."
    ::= { bwCFGNAGroupEntry 5 }

  bwCFGNAGroupExternalForward OBJECT-TYPE
    SYNTAX      Counter32
    MAX-ACCESS  read-write
    STATUS      current
    DESCRIPTION 
        "This is the number of times Call Forwarding Group No Answer External has forwarded a Hunt Group call in the group."
    ::= { bwCFGNAGroupEntry 6 }

  bwCFGNAGroupExternalNoForward OBJECT-TYPE
    SYNTAX      Counter32
    MAX-ACCESS  read-write
    STATUS      current
    DESCRIPTION 
        "This is the number of times Call Forwarding Group No Answer External has given Temporarily Unavailable treatment to a Hunt Group/Call Center call in the group."
    ::= { bwCFGNAGroupEntry 7 }

  bwCFGNAExternalForward OBJECT-TYPE
    SYNTAX      Counter32
    MAX-ACCESS  read-write
    STATUS      current
    DESCRIPTION 
        "This is the number of times Call Forwarding Group No Answer External has forwarded a Hunt Group call."
    ::= { callForwardGroupNoAnswer 6 }

  bwCFGNAExternalNoForward OBJECT-TYPE
    SYNTAX      Counter32
    MAX-ACCESS  read-write
    STATUS      current
    DESCRIPTION 
        "This is the number of times Call Forwarding Group No Answer External has given Temporarily Unavailable treatment to a Hunt Group call."
    ::= { callForwardGroupNoAnswer 7 }

  bwSD100Program OBJECT-TYPE
    SYNTAX      Counter32
    MAX-ACCESS  read-write
    STATUS      current
    DESCRIPTION 
        "This counter is incremented each time a new SD100 call is programmed via FAC method on BroadWorks"
    ::= { sd100 1 }

  bwSD100Call OBJECT-TYPE
    SYNTAX      Counter32
    MAX-ACCESS  read-write
    STATUS      current
    DESCRIPTION 
        "This counter is incremented each time SD100 code is used to originate a call on BroadWorks"
    ::= { sd100 2 }

  bwSD100SPTable OBJECT-TYPE
    SYNTAX      SEQUENCE OF BwSD100SPEntry
    MAX-ACCESS  not-accessible
    STATUS      current
    DESCRIPTION 
        "Counters for sd100 service measurements for service providers"
    ::= { sd100 3 }

  bwSD100SPEntry OBJECT-TYPE
    SYNTAX      BwSD100SPEntry
    MAX-ACCESS  not-accessible
    STATUS      current
    DESCRIPTION 
        "Each row contains the service counters for the sd100 service for each service provider in the system"
    INDEX       { bwSD100SPIndex }
    ::= { bwSD100SPTable 1 }

  BwSD100SPEntry ::= SEQUENCE {
    bwSD100SPIndex      Unsigned32,
    bwSD100SPID         DisplayString,
    bwSD100SPProgram    Counter32,
    bwSD100SPCall       Counter32
  }

  bwSD100SPIndex OBJECT-TYPE
    SYNTAX      Unsigned32
    MAX-ACCESS  read-only
    STATUS      current
    DESCRIPTION 
        "This column represents the index of the service provider in the system"
    ::= { bwSD100SPEntry 1 }

  bwSD100SPID OBJECT-TYPE
    SYNTAX      DisplayString
    MAX-ACCESS  read-only
    STATUS      current
    DESCRIPTION 
        "This string represents a service provider ID"
    ::= { bwSD100SPEntry 2 }

  bwSD100SPProgram OBJECT-TYPE
    SYNTAX      Counter32
    MAX-ACCESS  read-write
    STATUS      current
    DESCRIPTION 
        "This counter is incremented each time a new SD100 call is programmed via the FAC method for a particular service provider"
    ::= { bwSD100SPEntry 3 }

  bwSD100SPCall OBJECT-TYPE
    SYNTAX      Counter32
    MAX-ACCESS  read-write
    STATUS      current
    DESCRIPTION 
        "This counter is incremented each time SD100 code is used to originate a call for a particular service provider"
    ::= { bwSD100SPEntry 4 }

  bwSD100GroupTable OBJECT-TYPE
    SYNTAX      SEQUENCE OF BwSD100GroupEntry
    MAX-ACCESS  not-accessible
    STATUS      current
    DESCRIPTION 
        "Counters for sd100 service measurements for groups"
    ::= { sd100 4 }

  bwSD100GroupEntry OBJECT-TYPE
    SYNTAX      BwSD100GroupEntry
    MAX-ACCESS  not-accessible
    STATUS      current
    DESCRIPTION 
        "Each row contains the service counters for the sd100 service for each group in the system"
    INDEX       { bwSD100GroupIndex }
    ::= { bwSD100GroupTable 1 }

  BwSD100GroupEntry ::= SEQUENCE {
    bwSD100GroupIndex       Unsigned32,
    bwSD100GroupID          DisplayString,
    bwSD100GroupProgram     Counter32,
    bwSD100GroupCall        Counter32
  }

  bwSD100GroupIndex OBJECT-TYPE
    SYNTAX      Unsigned32
    MAX-ACCESS  read-only
    STATUS      current
    DESCRIPTION 
        "This column represents the index of the group in the system"
    ::= { bwSD100GroupEntry 1 }

  bwSD100GroupID OBJECT-TYPE
    SYNTAX      DisplayString
    MAX-ACCESS  read-only
    STATUS      current
    DESCRIPTION 
        "This string represents a group ID"
    ::= { bwSD100GroupEntry 2 }

  bwSD100GroupProgram OBJECT-TYPE
    SYNTAX      Counter32
    MAX-ACCESS  read-write
    STATUS      current
    DESCRIPTION 
        "This counter is incremented each time a new SD100 call is programmed via the FAC method for a particular group"
    ::= { bwSD100GroupEntry 3 }

  bwSD100GroupCall OBJECT-TYPE
    SYNTAX      Counter32
    MAX-ACCESS  read-write
    STATUS      current
    DESCRIPTION 
        "This counter is incremented each time SD100 code is used to originate a call for a particular group"
    ::= { bwSD100GroupEntry 4 }

  bwThirdPartyVoiceMailNbOfCFWBusy OBJECT-TYPE
    SYNTAX      Counter32
    MAX-ACCESS  read-write
    STATUS      current
    DESCRIPTION 
        "Incremented each time a call is forwarded to an external VM (by the Third-Party Voice Mail Support User service) on busy condition"
    ::= { thirdPartyVMail 1 }

  bwThirdPartyVoiceMailNbOfCFWNoAnswer OBJECT-TYPE
    SYNTAX      Counter32
    MAX-ACCESS  read-write
    STATUS      current
    DESCRIPTION 
        "Incremented each time a call is forwarded to an external VM (by the Third-Party Voice Mail Support User service) on no-answer condition, at the group level"
    ::= { thirdPartyVMail 2 }

  bwThirdPartyVMailSPTable OBJECT-TYPE
    SYNTAX      SEQUENCE OF BwThirdPartyVMailSPEntry
    MAX-ACCESS  not-accessible
    STATUS      current
    DESCRIPTION 
        "Counters for the Third Party Voice Mail service measurements for service providers"
    ::= { thirdPartyVMail 3 }

  bwThirdPartyVMailSPEntry OBJECT-TYPE
    SYNTAX      BwThirdPartyVMailSPEntry
    MAX-ACCESS  not-accessible
    STATUS      current
    DESCRIPTION 
        "Each row contains the service counters for the sd100 service for each service provider in the system"
    INDEX       { bwThirdPartyVMailSPIndex }
    ::= { bwThirdPartyVMailSPTable 1 }

  BwThirdPartyVMailSPEntry ::= SEQUENCE {
    bwThirdPartyVMailSPIndex                Unsigned32,
    bwThirdPartyVMailSPID                   DisplayString,
    bwThirdPartyVoiceMailSPNbOfCFWBusy      Counter32,
    bwThirdPartyVoiceMailSPNbOfCFWNoAnswer  Counter32
  }

  bwThirdPartyVMailSPIndex OBJECT-TYPE
    SYNTAX      Unsigned32
    MAX-ACCESS  read-only
    STATUS      current
    DESCRIPTION 
        "This column represents the index of the service provider in the system"
    ::= { bwThirdPartyVMailSPEntry 1 }

  bwThirdPartyVMailSPID OBJECT-TYPE
    SYNTAX      DisplayString
    MAX-ACCESS  read-only
    STATUS      current
    DESCRIPTION 
        "This string represents a service provider ID"
    ::= { bwThirdPartyVMailSPEntry 2 }

  bwThirdPartyVoiceMailSPNbOfCFWBusy OBJECT-TYPE
    SYNTAX      Counter32
    MAX-ACCESS  read-write
    STATUS      current
    DESCRIPTION 
        "Incremented each time a call is forwarded to an external VM (by the Third-Party Voice Mail Support User service) on busy condition for a particular service provider"
    ::= { bwThirdPartyVMailSPEntry 3 }

  bwThirdPartyVoiceMailSPNbOfCFWNoAnswer OBJECT-TYPE
    SYNTAX      Counter32
    MAX-ACCESS  read-write
    STATUS      current
    DESCRIPTION 
        "Incremented each time a call is forwarded to an external VM (by the Third-Party Voice Mail Support User service) on no-answer condition, at the group level"
    ::= { bwThirdPartyVMailSPEntry 4 }

  bwThirdPartyVMailGroupTable OBJECT-TYPE
    SYNTAX      SEQUENCE OF BwThirdPartyVMailGroupEntry
    MAX-ACCESS  not-accessible
    STATUS      current
    DESCRIPTION 
        "Counters for the Third Party Voice Mail service measurements for groups"
    ::= { thirdPartyVMail 4 }

  bwThirdPartyVMailGroupEntry OBJECT-TYPE
    SYNTAX      BwThirdPartyVMailGroupEntry
    MAX-ACCESS  not-accessible
    STATUS      current
    DESCRIPTION 
        "Each row contains the service counters for the sd100 service for each group in the system"
    INDEX       { bwThirdPartyVMailGroupIndex }
    ::= { bwThirdPartyVMailGroupTable 1 }

  BwThirdPartyVMailGroupEntry ::= SEQUENCE {
    bwThirdPartyVMailGroupIndex                 Unsigned32,
    bwThirdPartyVMailGroupID                    DisplayString,
    bwThirdPartyVoiceMailGroupNbOfCFWBusy       Counter32,
    bwThirdPartyVoiceMailGroupNbOfCFWNoAnswer   Counter32
  }

  bwThirdPartyVMailGroupIndex OBJECT-TYPE
    SYNTAX      Unsigned32
    MAX-ACCESS  read-only
    STATUS      current
    DESCRIPTION 
        "This column represents the index of the group in the system"
    ::= { bwThirdPartyVMailGroupEntry 1 }

  bwThirdPartyVMailGroupID OBJECT-TYPE
    SYNTAX      DisplayString
    MAX-ACCESS  read-only
    STATUS      current
    DESCRIPTION 
        "This string represents a group ID"
    ::= { bwThirdPartyVMailGroupEntry 2 }

  bwThirdPartyVoiceMailGroupNbOfCFWBusy OBJECT-TYPE
    SYNTAX      Counter32
    MAX-ACCESS  read-write
    STATUS      current
    DESCRIPTION 
        "Incremented each time a call is forwarded to an external VM (by the Third-Party Voice Mail Support User service) on busy condition for a particular group"
    ::= { bwThirdPartyVMailGroupEntry 3 }

  bwThirdPartyVoiceMailGroupNbOfCFWNoAnswer OBJECT-TYPE
    SYNTAX      Counter32
    MAX-ACCESS  read-write
    STATUS      current
    DESCRIPTION 
        "Incremented each time a call is forwarded to an external VM (by the Third-Party Voice Mail Support User service) on no-answer condition, at the group level for a particular group"
    ::= { bwThirdPartyVMailGroupEntry 4 }

  bwDirectedCallPickupNumAttempts OBJECT-TYPE
    SYNTAX      Counter32
    MAX-ACCESS  read-write
    STATUS      current
    DESCRIPTION 
        "This counter shall be incremented each time a user attempts to pick up a call using the Directed Call Pickup FAC"
    ::= { directedCallPickup 1 }

  bwDirectedCallPickupNumFailures OBJECT-TYPE
    SYNTAX      Counter32
    MAX-ACCESS  read-write
    STATUS      current
    DESCRIPTION 
        "This counter shall be incremented each time a user is unsuccessful at picking up a call using the Directed Call Pickup FAC"
    ::= { directedCallPickup 2 }

  bwDirectedCallPickupSPTable OBJECT-TYPE
    SYNTAX      SEQUENCE OF BwDirectedCallPickupSPEntry
    MAX-ACCESS  not-accessible
    STATUS      current
    DESCRIPTION 
        "Counters for the Directed Call Pick Up service measurements for service providers"
    ::= { directedCallPickup 3 }

  bwDirectedCallPickupSPEntry OBJECT-TYPE
    SYNTAX      BwDirectedCallPickupSPEntry
    MAX-ACCESS  not-accessible
    STATUS      current
    DESCRIPTION 
        "Each row contains the service counters for the directed call pick-up service for each service provider in the system"
    INDEX       { bwDirectedCallPickupSPIndex }
    ::= { bwDirectedCallPickupSPTable 1 }

  BwDirectedCallPickupSPEntry ::= SEQUENCE {
    bwDirectedCallPickupSPIndex         Unsigned32,
    bwDirectedCallPickupSPID            DisplayString,
    bwDirectedCallPickupSPNumAttempts   Counter32,
    bwDirectedCallPickupSPNumFailures   Counter32
  }

  bwDirectedCallPickupSPIndex OBJECT-TYPE
    SYNTAX      Unsigned32
    MAX-ACCESS  read-only
    STATUS      current
    DESCRIPTION 
        "This column represents the index of the service provider in the system"
    ::= { bwDirectedCallPickupSPEntry 1 }

  bwDirectedCallPickupSPID OBJECT-TYPE
    SYNTAX      DisplayString
    MAX-ACCESS  read-only
    STATUS      current
    DESCRIPTION 
        "This string represents a service provider ID"
    ::= { bwDirectedCallPickupSPEntry 2 }

  bwDirectedCallPickupSPNumAttempts OBJECT-TYPE
    SYNTAX      Counter32
    MAX-ACCESS  read-write
    STATUS      current
    DESCRIPTION 
        "This counter shall be incremented each time a user attempts to pick up a call using the Directed Call Pickup FAC for a particular service provider"
    ::= { bwDirectedCallPickupSPEntry 3 }

  bwDirectedCallPickupSPNumFailures OBJECT-TYPE
    SYNTAX      Counter32
    MAX-ACCESS  read-write
    STATUS      current
    DESCRIPTION 
        "This counter shall be incremented each time a user is unsuccessful at picking up a call using the Directed Call Pickup FAC for a particular service provider"
    ::= { bwDirectedCallPickupSPEntry 4 }

  bwDirectedCallPickupGroupTable OBJECT-TYPE
    SYNTAX      SEQUENCE OF BwDirectedCallPickupGroupEntry
    MAX-ACCESS  not-accessible
    STATUS      current
    DESCRIPTION 
        "Counters for the Directed Call Pick Up service measurements for groups"
    ::= { directedCallPickup 4 }

  bwDirectedCallPickupGroupEntry OBJECT-TYPE
    SYNTAX      BwDirectedCallPickupGroupEntry
    MAX-ACCESS  not-accessible
    STATUS      current
    DESCRIPTION 
        "Each row contains the service counters for the directed call pick-up service for each service provider in the system"
    INDEX       { bwDirectedCallPickupGroupIndex }
    ::= { bwDirectedCallPickupGroupTable 1 }

  BwDirectedCallPickupGroupEntry ::= SEQUENCE {
    bwDirectedCallPickupGroupIndex          Unsigned32,
    bwDirectedCallPickupGroupID             DisplayString,
    bwDirectedCallPickupGroupNumAttempts    Counter32,
    bwDirectedCallPickupGroupNumFailures    Counter32
  }

  bwDirectedCallPickupGroupIndex OBJECT-TYPE
    SYNTAX      Unsigned32
    MAX-ACCESS  read-only
    STATUS      current
    DESCRIPTION 
        "This column represents the index of the service provider in the system"
    ::= { bwDirectedCallPickupGroupEntry 1 }

  bwDirectedCallPickupGroupID OBJECT-TYPE
    SYNTAX      DisplayString
    MAX-ACCESS  read-only
    STATUS      current
    DESCRIPTION 
        "This string represents a service provider ID"
    ::= { bwDirectedCallPickupGroupEntry 2 }

  bwDirectedCallPickupGroupNumAttempts OBJECT-TYPE
    SYNTAX      Counter32
    MAX-ACCESS  read-write
    STATUS      current
    DESCRIPTION 
        "This counter shall be incremented each time a user attempts to pick up a call using the Directed Call Pickup FAC for a particular group"
    ::= { bwDirectedCallPickupGroupEntry 3 }

  bwDirectedCallPickupGroupNumFailures OBJECT-TYPE
    SYNTAX      Counter32
    MAX-ACCESS  read-write
    STATUS      current
    DESCRIPTION 
        "This counter shall be incremented each time a user is unsuccessful at picking up a call using the Directed Call Pickup FAC for a particular group"
    ::= { bwDirectedCallPickupGroupEntry 4 }

  bwFlashCallHoldNumActivations OBJECT-TYPE
    SYNTAX      Counter32
    MAX-ACCESS  read-write
    STATUS      current
    DESCRIPTION 
        "This counter shall be incremented each time a user successfully holds a call via the Flash Call Hold FAC"
    ::= { flashCallHold 1 }

  bwFlashCallHoldSPTable OBJECT-TYPE
    SYNTAX      SEQUENCE OF BwFlashCallHoldSPEntry
    MAX-ACCESS  not-accessible
    STATUS      current
    DESCRIPTION 
        "Counters for the Flash Call Hold service measurements for service providers"
    ::= { flashCallHold 2 }

  bwFlashCallHoldSPEntry OBJECT-TYPE
    SYNTAX      BwFlashCallHoldSPEntry
    MAX-ACCESS  not-accessible
    STATUS      current
    DESCRIPTION 
        "Each row contains the service counters for the directed call pick-up service for each service provider in the system"
    INDEX       { bwFlashCallHoldSPIndex }
    ::= { bwFlashCallHoldSPTable 1 }

  BwFlashCallHoldSPEntry ::= SEQUENCE {
    bwFlashCallHoldSPIndex              Unsigned32,
    bwFlashCallHoldSPID                 DisplayString,
    bwFlashCallHoldSPNumActivations     Counter32
  }

  bwFlashCallHoldSPIndex OBJECT-TYPE
    SYNTAX      Unsigned32
    MAX-ACCESS  read-only
    STATUS      current
    DESCRIPTION 
        "This column represents the index of the service provider in the system"
    ::= { bwFlashCallHoldSPEntry 1 }

  bwFlashCallHoldSPID OBJECT-TYPE
    SYNTAX      DisplayString
    MAX-ACCESS  read-only
    STATUS      current
    DESCRIPTION 
        "This string represents a service provider ID"
    ::= { bwFlashCallHoldSPEntry 2 }

  bwFlashCallHoldSPNumActivations OBJECT-TYPE
    SYNTAX      Counter32
    MAX-ACCESS  read-write
    STATUS      current
    DESCRIPTION 
        "This counter shall be incremented each time a user successfully holds a call via the Flash Call Hold FAC for a specigic service provider"
    ::= { bwFlashCallHoldSPEntry 3 }

  bwFlashCallHoldGroupTable OBJECT-TYPE
    SYNTAX      SEQUENCE OF BwFlashCallHoldGroupEntry
    MAX-ACCESS  not-accessible
    STATUS      current
    DESCRIPTION 
        "Counters for the Flash Call Hold service measurements for groups"
    ::= { flashCallHold 3 }

  bwFlashCallHoldGroupEntry OBJECT-TYPE
    SYNTAX      BwFlashCallHoldGroupEntry
    MAX-ACCESS  not-accessible
    STATUS      current
    DESCRIPTION 
        "Each row contains the service counters for the directed call pick-up service for each group in the system"
    INDEX       { bwFlashCallHoldGroupIndex }
    ::= { bwFlashCallHoldGroupTable 1 }

  BwFlashCallHoldGroupEntry ::= SEQUENCE {
    bwFlashCallHoldGroupIndex           Unsigned32,
    bwFlashCallHoldGroupID              DisplayString,
    bwFlashCallHoldGroupNumActivations  Counter32
  }

  bwFlashCallHoldGroupIndex OBJECT-TYPE
    SYNTAX      Unsigned32
    MAX-ACCESS  read-only
    STATUS      current
    DESCRIPTION 
        "This column represents the index of the service provider in the system"
    ::= { bwFlashCallHoldGroupEntry 1 }

  bwFlashCallHoldGroupID OBJECT-TYPE
    SYNTAX      DisplayString
    MAX-ACCESS  read-only
    STATUS      current
    DESCRIPTION 
        "This string represents a service provider ID"
    ::= { bwFlashCallHoldGroupEntry 2 }

  bwFlashCallHoldGroupNumActivations OBJECT-TYPE
    SYNTAX      Counter32
    MAX-ACCESS  read-write
    STATUS      current
    DESCRIPTION 
        "This counter shall be incremented each time a user successfully holds a call via the Flash Call Hold FAC for a specigic group"
    ::= { bwFlashCallHoldGroupEntry 3 }

  bwEZRegistrationsRejected OBJECT-TYPE
    SYNTAX      Counter32
    MAX-ACCESS  read-write
    STATUS      current
    DESCRIPTION 
        "This counter is incremented whenever a SIP device registration is rejected because of the Emergency Zone service setting for a group"
    ::= { emergencyZones 1 }

  bwEZEmergencyCallsRejected OBJECT-TYPE
    SYNTAX      Counter32
    MAX-ACCESS  read-write
    STATUS      current
    DESCRIPTION 
        "This counter is incremented whenever an emergency call is rejected because of the emergency zone service setting for a group"
    ::= { emergencyZones 2 }

  bwEZNormalCallsRejected OBJECT-TYPE
    SYNTAX      Counter32
    MAX-ACCESS  read-write
    STATUS      current
    DESCRIPTION 
        "This counter is incremented whenever a non-emergency call is rejected because of the Emergency Zone serivce setting for a group"
    ::= { emergencyZones 3 }

  bwEZSPTable OBJECT-TYPE
    SYNTAX      SEQUENCE OF BwEZSPEntry
    MAX-ACCESS  not-accessible
    STATUS      current
    DESCRIPTION 
        "Counters for the Emergency Zones service measurements for service providers"
    ::= { emergencyZones 4 }

  bwEZSPEntry OBJECT-TYPE
    SYNTAX      BwEZSPEntry
    MAX-ACCESS  not-accessible
    STATUS      current
    DESCRIPTION 
        "Each row contains the service counters for the emergency zone service for each service provider in the system"
    INDEX       { bwEZSPIndex }
    ::= { bwEZSPTable 1 }

  BwEZSPEntry ::= SEQUENCE {
    bwEZSPIndex                     Unsigned32,
    bwEZSPID                        DisplayString,
    bwEZSPRegistrationsRejected     Counter32,
    bwEZSPEmergencyCallsRejected    Counter32,
    bwEZSPNormalCallsRejected       Counter32
  }

  bwEZSPIndex OBJECT-TYPE
    SYNTAX      Unsigned32
    MAX-ACCESS  read-only
    STATUS      current
    DESCRIPTION 
        "This column represents the index of the service provider in the system"
    ::= { bwEZSPEntry 1 }

  bwEZSPID OBJECT-TYPE
    SYNTAX      DisplayString
    MAX-ACCESS  read-only
    STATUS      current
    DESCRIPTION 
        "This string represents a service provider ID"
    ::= { bwEZSPEntry 2 }

  bwEZSPRegistrationsRejected OBJECT-TYPE
    SYNTAX      Counter32
    MAX-ACCESS  read-write
    STATUS      current
    DESCRIPTION 
        "This counter is incremented whenever a SIP device registration is rejected because of the Emergency Zone service setting for a group for a specific service provider"
    ::= { bwEZSPEntry 3 }

  bwEZSPEmergencyCallsRejected OBJECT-TYPE
    SYNTAX      Counter32
    MAX-ACCESS  read-write
    STATUS      current
    DESCRIPTION 
        "This counter is incremented whenever an emergency call is rejected because of the emergency zone service setting for a group for a specific service provider"
    ::= { bwEZSPEntry 4 }

  bwEZSPNormalCallsRejected OBJECT-TYPE
    SYNTAX      Counter32
    MAX-ACCESS  read-write
    STATUS      current
    DESCRIPTION 
        "This counter is incremented whenever a non-emergency call is rejected because of the Emergency Zone serivce setting for a group for a specific service provider"
    ::= { bwEZSPEntry 5 }

  bwEZGroupTable OBJECT-TYPE
    SYNTAX      SEQUENCE OF BwEZGroupEntry
    MAX-ACCESS  not-accessible
    STATUS      current
    DESCRIPTION 
        "Counters for the Emergency Zones service measurements for groups"
    ::= { emergencyZones 5 }

  bwEZGroupEntry OBJECT-TYPE
    SYNTAX      BwEZGroupEntry
    MAX-ACCESS  not-accessible
    STATUS      current
    DESCRIPTION 
        "Each row contains the service counters for the emergency zone service for each group in the system"
    INDEX       { bwEZGroupIndex }
    ::= { bwEZGroupTable 1 }

  BwEZGroupEntry ::= SEQUENCE {
    bwEZGroupIndex                      Unsigned32,
    bwEZGroupID                         DisplayString,
    bwEZGroupRegistrationsRejected      Counter32,
    bwEZGroupEmergencyCallsRejected     Counter32,
    bwEZGroupNormalCallsRejected        Counter32
  }

  bwEZGroupIndex OBJECT-TYPE
    SYNTAX      Unsigned32
    MAX-ACCESS  read-only
    STATUS      current
    DESCRIPTION 
        "This column represents the index of the service provider in the system"
    ::= { bwEZGroupEntry 1 }

  bwEZGroupID OBJECT-TYPE
    SYNTAX      DisplayString
    MAX-ACCESS  read-only
    STATUS      current
    DESCRIPTION 
        "This string represents a service provider ID"
    ::= { bwEZGroupEntry 2 }

  bwEZGroupRegistrationsRejected OBJECT-TYPE
    SYNTAX      Counter32
    MAX-ACCESS  read-write
    STATUS      current
    DESCRIPTION 
        "This counter is incremented whenever a SIP device registration is rejected because of the Emergency Zone service setting for a group for a specific group"
    ::= { bwEZGroupEntry 3 }

  bwEZGroupEmergencyCallsRejected OBJECT-TYPE
    SYNTAX      Counter32
    MAX-ACCESS  read-write
    STATUS      current
    DESCRIPTION 
        "This counter is incremented whenever an emergency call is rejected because of the emergency zone service setting for a group for a specific group"
    ::= { bwEZGroupEntry 4 }

  bwEZGroupNormalCallsRejected OBJECT-TYPE
    SYNTAX      Counter32
    MAX-ACCESS  read-write
    STATUS      current
    DESCRIPTION 
        "This counter is incremented whenever a non-emergency call is rejected because of the Emergency Zone serivce setting for a group for a specific group"
    ::= { bwEZGroupEntry 5 }

  bwDPUBIAttempt OBJECT-TYPE
    SYNTAX      Counter32
    MAX-ACCESS  read-write
    STATUS      current
    DESCRIPTION 
        "This counter is incremented each time a user attempts Directed Call Pickup with Barge-in"
    ::= { dpubi 1 }

  bwDPUBIFailure OBJECT-TYPE
    SYNTAX      Counter32
    MAX-ACCESS  read-write
    STATUS      current
    DESCRIPTION 
        "This counter is incremented each time a user fails to pickup a call with Directed Call Pickup with Barge-in"
    ::= { dpubi 2 }

  bwDPUBIBargeIn OBJECT-TYPE
    SYNTAX      Counter32
    MAX-ACCESS  read-write
    STATUS      current
    DESCRIPTION 
        "This counter is incremented each time a user successfully barges into a call with Directed Call Pickup with Barge-in"
    ::= { dpubi 3 }

  bwDPUBIBargeInFailure OBJECT-TYPE
    SYNTAX      Counter32
    MAX-ACCESS  read-write
    STATUS      current
    DESCRIPTION 
        "This counter is incremented each time a user fails to barge into a call with Directed Call Pickup with Barge-in"
    ::= { dpubi 4 }

  bwDPUBISPTable OBJECT-TYPE
    SYNTAX      SEQUENCE OF BwDPUBISPEntry
    MAX-ACCESS  not-accessible
    STATUS      current
    DESCRIPTION 
        "Counters for the Directed Call Pickup with Barge In service measurements for service providers"
    ::= { dpubi 5 }

  bwDPUBISPEntry OBJECT-TYPE
    SYNTAX      BwDPUBISPEntry
    MAX-ACCESS  not-accessible
    STATUS      current
    DESCRIPTION 
        "Each row contains the service counters for the Directed Call Pickup with Barge In service for each service provider in the system"
    INDEX       { bwDPUBISPIndex }
    ::= { bwDPUBISPTable 1 }

  BwDPUBISPEntry ::= SEQUENCE {
    bwDPUBISPIndex                            Unsigned32,
    bwDPUBISPID                               DisplayString,
    bwDPUBISPAttempt                          Counter32,
    bwDPUBISPFailure                          Counter32,
    bwDPUBISPBargeIn                          Counter32,
    bwDPUBISPBargeInFailure                   Counter32,
    bwDPUBISPExempt                           Counter32,
    bwDPUBISPNumSilentlyMonitoredCalls        Counter32,
    bwDPUBISPNumSilentlyMonitoredCallsFailure Counter32,
    bwDPUBISPNumMonitorNextCallRequest        Counter32,
    bwDPUBISPNumMonitorNextCallRequestFailure Counter32
  }

  bwDPUBISPIndex OBJECT-TYPE
    SYNTAX      Unsigned32
    MAX-ACCESS  read-only
    STATUS      current
    DESCRIPTION 
        "This column represents the index of the service provider in the system"
    ::= { bwDPUBISPEntry 1 }

  bwDPUBISPID OBJECT-TYPE
    SYNTAX      DisplayString
    MAX-ACCESS  read-only
    STATUS      current
    DESCRIPTION 
        "This string represents a service provider ID"
    ::= { bwDPUBISPEntry 2 }

  bwDPUBISPAttempt OBJECT-TYPE
    SYNTAX      Counter32
    MAX-ACCESS  read-write
    STATUS      current
    DESCRIPTION 
        "This counter is incremented each time a user under the Service Provider attempts Directed Call Pickup with Barge-in"
    ::= { bwDPUBISPEntry 3 }

  bwDPUBISPFailure OBJECT-TYPE
    SYNTAX      Counter32
    MAX-ACCESS  read-write
    STATUS      current
    DESCRIPTION 
        "This counter is incremented each time a user under the Service Provider fails to pickup a call with Directed Call Pickup with Barge-in"
    ::= { bwDPUBISPEntry 4 }

  bwDPUBISPBargeIn OBJECT-TYPE
    SYNTAX      Counter32
    MAX-ACCESS  read-write
    STATUS      current
    DESCRIPTION 
        "This counter is incremented each time a user under the Service Provider successfully barges into a call with Directed Call Pickup with Barge-in"
    ::= { bwDPUBISPEntry 5 }

  bwDPUBISPBargeInFailure OBJECT-TYPE
    SYNTAX      Counter32
    MAX-ACCESS  read-write
    STATUS      current
    DESCRIPTION 
        "This counter is incremented each time a user under the Service Provider fails to barge into a call with Directed Call Pickup with Barge-in"
    ::= { bwDPUBISPEntry 6 }

  bwDPUBISPExempt OBJECT-TYPE
    SYNTAX      Counter32
    MAX-ACCESS  read-write
    STATUS      current
    DESCRIPTION 
        "This counter is incremented each time a DPUBI attempt is blocked by the picked up user's Barge-in Exempt service for a given service provider."
    ::= { bwDPUBISPEntry 7 }

  bwDPUBISPNumSilentlyMonitoredCalls OBJECT-TYPE
    SYNTAX      Counter32
    MAX-ACCESS  read-write
    STATUS      current
    DESCRIPTION 
        "This is the number of times that a supervisor silently monitored a call successfully. There is one instance of this counter for each service provider defined in the system."
    ::= { bwDPUBISPEntry 8 }

  bwDPUBISPNumSilentlyMonitoredCallsFailure OBJECT-TYPE
    SYNTAX      Counter32
    MAX-ACCESS  read-write
    STATUS      current
    DESCRIPTION 
        "This is the number of times that a supervisor failed to silently monitor a call. There is one instance of this counter for each service provider defined in the system."
    ::= { bwDPUBISPEntry 9 }

  bwDPUBISPNumMonitorNextCallRequest OBJECT-TYPE
    SYNTAX      Counter32
    MAX-ACCESS  read-write
    STATUS      current
    DESCRIPTION 
        "This is the number of times that a request to Monitor Next Call is invoked successfully.  There is one instance of this counter for each service provider defined in the system."
    ::= { bwDPUBISPEntry 10 }

  bwDPUBISPNumMonitorNextCallRequestFailure OBJECT-TYPE
    SYNTAX      Counter32
    MAX-ACCESS  read-write
    STATUS      current
    DESCRIPTION 
        "This is the number of times that a request to Monitor Next Call failed.  There is one instance of this counter for each service provider defined in the system."
    ::= { bwDPUBISPEntry 11 }

  bwDPUBIGroupTable OBJECT-TYPE
    SYNTAX      SEQUENCE OF BwDPUBIGroupEntry
    MAX-ACCESS  not-accessible
    STATUS      current
    DESCRIPTION 
        "Counters for the Directed Call Pickup with Barge In service measurements for groups"
    ::= { dpubi 6 }

  bwDPUBIGroupEntry OBJECT-TYPE
    SYNTAX      BwDPUBIGroupEntry
    MAX-ACCESS  not-accessible
    STATUS      current
    DESCRIPTION 
        "Each row contains the service counters for the Directed Call Pickup with Barge In service for each group in the system"
    INDEX       { bwDPUBIGroupIndex }
    ::= { bwDPUBIGroupTable 1 }

  BwDPUBIGroupEntry ::= SEQUENCE {
    bwDPUBIGroupIndex                            Unsigned32,
    bwDPUBIGroupID                               DisplayString,
    bwDPUBIGroupAttempt                          Counter32,
    bwDPUBIGroupFailure                          Counter32,
    bwDPUBIGroupBargeIn                          Counter32,
    bwDPUBIGroupBargeInFailure                   Counter32,
    bwDPUBIGroupExempt                           Counter32,
    bwDPUBIGroupNumSilentlyMonitoredCalls        Counter32,
    bwDPUBIGroupNumSilentlyMonitoredCallsFailure Counter32,
    bwDPUBIGroupNumMonitorNextCallRequest        Counter32,
    bwDPUBIGroupNumMonitorNextCallRequestFailure Counter32
  }

  bwDPUBIGroupIndex OBJECT-TYPE
    SYNTAX      Unsigned32
    MAX-ACCESS  read-only
    STATUS      current
    DESCRIPTION 
        "This column represents the index of the group in the system"
    ::= { bwDPUBIGroupEntry 1 }

  bwDPUBIGroupID OBJECT-TYPE
    SYNTAX      DisplayString
    MAX-ACCESS  read-only
    STATUS      current
    DESCRIPTION 
        "This string represents a group ID"
    ::= { bwDPUBIGroupEntry 2 }

  bwDPUBIGroupAttempt OBJECT-TYPE
    SYNTAX      Counter32
    MAX-ACCESS  read-write
    STATUS      current
    DESCRIPTION 
        "This counter is incremented each time a user under the group attempts Directed Call Pickup with Barge-in"
    ::= { bwDPUBIGroupEntry 3 }

  bwDPUBIGroupFailure OBJECT-TYPE
    SYNTAX      Counter32
    MAX-ACCESS  read-write
    STATUS      current
    DESCRIPTION 
        "This counter is incremented each time a user under the group fails to pickup a call with Directed Call Pickup with Barge-in"
    ::= { bwDPUBIGroupEntry 4 }

  bwDPUBIGroupBargeIn OBJECT-TYPE
    SYNTAX      Counter32
    MAX-ACCESS  read-write
    STATUS      current
    DESCRIPTION 
        "This counter is incremented each time a user under the group successfully barges into a call with Directed Call Pickup with Barge-in"
    ::= { bwDPUBIGroupEntry 5 }

  bwDPUBIGroupBargeInFailure OBJECT-TYPE
    SYNTAX      Counter32
    MAX-ACCESS  read-write
    STATUS      current
    DESCRIPTION 
        "This counter is incremented each time a user under the group fails to barge into a call with Directed Call Pickup with Barge-in"
    ::= { bwDPUBIGroupEntry 6 }

  bwDPUBIGroupExempt OBJECT-TYPE
    SYNTAX      Counter32
    MAX-ACCESS  read-write
    STATUS      current
    DESCRIPTION 
        "This counter is incremented each time a DPUBI attempt is blocked by the picked up user's Barge-in Exempt service for a given group."
    ::= { bwDPUBIGroupEntry 7 }

  bwDPUBIGroupNumSilentlyMonitoredCalls OBJECT-TYPE
    SYNTAX      Counter32
    MAX-ACCESS  read-write
    STATUS      current
    DESCRIPTION 
        "This is the number of times that a supervisor silently monitored a call successfully. There is one instance of this counter for each group defined in the system."
    ::= { bwDPUBIGroupEntry 8 }

  bwDPUBIGroupNumSilentlyMonitoredCallsFailure OBJECT-TYPE
    SYNTAX      Counter32
    MAX-ACCESS  read-write
    STATUS      current
    DESCRIPTION 
        "This is the number of times that a supervisor failed to silently monitor a call.There is one instance of this counter for each group defined in the system."
    ::= { bwDPUBIGroupEntry 9 }

  bwDPUBIGroupNumMonitorNextCallRequest OBJECT-TYPE
    SYNTAX      Counter32
    MAX-ACCESS  read-write
    STATUS      current
    DESCRIPTION 
        "This is the number of times that a request to Monitor Next Call is invoked successfully.  There is one instance of this counter for each group defined in the system."
    ::= { bwDPUBIGroupEntry 10 }

  bwDPUBIGroupNumMonitorNextCallRequestFailure OBJECT-TYPE
    SYNTAX      Counter32
    MAX-ACCESS  read-write
    STATUS      current
    DESCRIPTION 
        "This is the number of times that a request to Monitor Next Call failed.  There is one instance of this counter for each group defined in the system."
    ::= { bwDPUBIGroupEntry 11 }

  bwDPUBIExempt OBJECT-TYPE
    SYNTAX      Counter32
    MAX-ACCESS  read-write
    STATUS      current
    DESCRIPTION 
        "This counter is incremented each time a DPUBI attempt is blocked by the picked up user's Barge-in Exempt service."
    ::= { dpubi 7 }

  bwDPUBINumSilentlyMonitoredCalls OBJECT-TYPE
    SYNTAX      Counter32
    MAX-ACCESS  read-write
    STATUS      current
    DESCRIPTION 
        "This is the number of times that a supervisor silently monitored a call successfully."
    ::= { dpubi 8 }

  bwDPUBINumSilentlyMonitoredCallsFailure OBJECT-TYPE
    SYNTAX      Counter32
    MAX-ACCESS  read-write
    STATUS      current
    DESCRIPTION 
        "This is the number of times that a supervisor failed to silently monitor a call."
    ::= { dpubi 9 }

  bwDPUBINumMonitorNextCallRequest OBJECT-TYPE
    SYNTAX      Counter32
    MAX-ACCESS  read-write
    STATUS      current
    DESCRIPTION 
        "This is the number of times that a request to Monitor Next Call is invoked successfully."
    ::= { dpubi 10 }

  bwDPUBINumMonitorNextCallRequestFailure OBJECT-TYPE
    SYNTAX      Counter32
    MAX-ACCESS  read-write
    STATUS      current
    DESCRIPTION 
        "This is the number of times that a request to Monitor Next Call failed."
    ::= { dpubi 11 }

-- Service : ACB ...........................................

  bwACBStarted OBJECT-TYPE
    SYNTAX      Counter32
    MAX-ACCESS  read-write
    STATUS      current
    DESCRIPTION 
        "System wide, number of times Automatic Callback has been activated"
    ::= { acb 1 }

  bwACBExpired OBJECT-TYPE
    SYNTAX      Counter32
    MAX-ACCESS  read-write
    STATUS      current
    DESCRIPTION 
        "System wide, number of times Automatic Callback's time to wait for an idle line has expired. The default time to wait is 30 minutes"
    ::= { acb 2 }

  bwACBSPTable OBJECT-TYPE
    SYNTAX      SEQUENCE OF BwACBSPEntry
    MAX-ACCESS  not-accessible
    STATUS      current
    DESCRIPTION 
        "Counters for the Automatic Call Back service measurements for service providers"
    ::= { acb 4 }

  bwACBSPEntry OBJECT-TYPE
    SYNTAX      BwACBSPEntry
    MAX-ACCESS  not-accessible
    STATUS      current
    DESCRIPTION 
        "Each row contains the service counters for the Automatic Call Back service for each service provider in the system"
    INDEX       { bwACBSPIndex }
    ::= { bwACBSPTable 1 }

  BwACBSPEntry ::= SEQUENCE {
    bwACBSPIndex                    Unsigned32,
    bwACBSPID                       DisplayString,
    bwACBSPStarted                  Counter32,
    bwACBSPExpired                  Counter32,
    bwACBSPMaxOrigSession           Counter32,
    bwACBSPMaxTermSession           Counter32,
    bwLegacyACBSPOrigSession        Counter32,
    bwLegacyACBSPOrigSuccessSession Counter32,
    bwLegacyACBSPOrigFailedSession  Counter32,
    bwLegacyACBSPTermSession        Counter32,
    bwLegacyACBSPTermSuccessSession Counter32,
    bwLegacyACBSPTermFailedSession  Counter32
  }

  bwACBSPIndex OBJECT-TYPE
    SYNTAX      Unsigned32
    MAX-ACCESS  read-only
    STATUS      current
    DESCRIPTION 
        "This column represents the index of the service provider in the system"
    ::= { bwACBSPEntry 1 }

  bwACBSPID OBJECT-TYPE
    SYNTAX      DisplayString
    MAX-ACCESS  read-only
    STATUS      current
    DESCRIPTION 
        "This string represents a service provider ID"
    ::= { bwACBSPEntry 2 }

  bwACBSPStarted OBJECT-TYPE
    SYNTAX      Counter32
    MAX-ACCESS  read-write
    STATUS      current
    DESCRIPTION 
        "Number of times Automatic Callback has been activated for a given service provider"
    ::= { bwACBSPEntry 3 }

  bwACBSPExpired OBJECT-TYPE
    SYNTAX      Counter32
    MAX-ACCESS  read-write
    STATUS      current
    DESCRIPTION 
        "Number of times Automatic Callback's time to wait for an idle line has expired for a given service provider. The default time to wait is 30 minutes."
    ::= { bwACBSPEntry 4 }

  bwACBSPMaxOrigSession OBJECT-TYPE
    SYNTAX      Counter32
    MAX-ACCESS  read-write
    STATUS      current
    DESCRIPTION 
        "Service Provider level, number of times the max number of Automatic Callback sessions has been reached for the originator."
    ::= { bwACBSPEntry 6 }

  bwACBSPMaxTermSession OBJECT-TYPE
    SYNTAX      Counter32
    MAX-ACCESS  read-write
    STATUS      current
    DESCRIPTION 
        "Service Provider level, number of times the max number of Automatic Callback sessions has been reached for the terminator."
    ::= { bwACBSPEntry 7 }

  bwLegacyACBSPOrigSession OBJECT-TYPE
    SYNTAX      Counter32
    MAX-ACCESS  read-write
    STATUS      current
    DESCRIPTION 
        "This is the number of times the Automatic Callback session has been initiated. There is one instance of this counter for each service provider defined in the system."
    ::= { bwACBSPEntry 8 }

  bwLegacyACBSPOrigSuccessSession OBJECT-TYPE
    SYNTAX      Counter32
    MAX-ACCESS  read-write
    STATUS      current
    DESCRIPTION 
        "This is the number of times the Automatic Callback session has been initiated successfully.  There is one instance of this counter for each service provider defined in the system."
    ::= { bwACBSPEntry 9 }

  bwLegacyACBSPOrigFailedSession OBJECT-TYPE
    SYNTAX      Counter32
    MAX-ACCESS  read-write
    STATUS      current
    DESCRIPTION 
        "This is the number of times the Automatic Callback session has failed.  There is one instance of this counter for each service provider defined in the system."
    ::= { bwACBSPEntry 10 }

  bwLegacyACBSPTermSession OBJECT-TYPE
    SYNTAX      Counter32
    MAX-ACCESS  read-write
    STATUS      current
    DESCRIPTION 
        "This is the number of times an Automatic Callback session request has been received on this switch.  There is one instance of this counter for each service provider defined in the system."
    ::= { bwACBSPEntry 11 }

  bwLegacyACBSPTermSuccessSession OBJECT-TYPE
    SYNTAX      Counter32
    MAX-ACCESS  read-write
    STATUS      current
    DESCRIPTION 
        "This is the number of times an Automatic Callback session request has been received on this switch successfully.  There is one instance of this counter for each service provider defined in the system."
    ::= { bwACBSPEntry 12 }

  bwLegacyACBSPTermFailedSession OBJECT-TYPE
    SYNTAX      Counter32
    MAX-ACCESS  read-write
    STATUS      current
    DESCRIPTION 
        "This is the number of times an Automatic Callback session request has failed on this switch.  There is one instance of this counter for each service provider defined in the system."
    ::= { bwACBSPEntry 13 }

  bwACBGroupTable OBJECT-TYPE
    SYNTAX      SEQUENCE OF BwACBGroupEntry
    MAX-ACCESS  not-accessible
    STATUS      current
    DESCRIPTION 
        "Counters for the Automatic Call Back service measurements for groups"
    ::= { acb 5 }

  bwACBGroupEntry OBJECT-TYPE
    SYNTAX      BwACBGroupEntry
    MAX-ACCESS  not-accessible
    STATUS      current
    DESCRIPTION 
        "Each row contains the service counters for the Automatic Call Back service for each group in the system"
    INDEX       { bwACBGroupIndex }
    ::= { bwACBGroupTable 1 }

  BwACBGroupEntry ::= SEQUENCE {
    bwACBGroupIndex                    Unsigned32,
    bwACBGroupID                       DisplayString,
    bwACBGroupStarted                  Counter32,
    bwACBGroupExpired                  Counter32,
    bwACBGroupMaxOrigSession           Counter32,
    bwACBGroupMaxTermSession           Counter32,
    bwLegacyACBGroupOrigSession        Counter32,
    bwLegacyACBGroupOrigSuccessSession Counter32,
    bwLegacyACBGroupOrigFailedSession  Counter32,
    bwLegacyACBGroupTermSession        Counter32,
    bwLegacyACBGroupTermSuccessSession Counter32,
    bwLegacyACBGroupTermFailedSession  Counter32
  }

  bwACBGroupIndex OBJECT-TYPE
    SYNTAX      Unsigned32
    MAX-ACCESS  read-only
    STATUS      current
    DESCRIPTION 
        "This column represents the index of the group in the system"
    ::= { bwACBGroupEntry 1 }

  bwACBGroupID OBJECT-TYPE
    SYNTAX      DisplayString
    MAX-ACCESS  read-only
    STATUS      current
    DESCRIPTION 
        "This string represents a group ID"
    ::= { bwACBGroupEntry 2 }

  bwACBGroupStarted OBJECT-TYPE
    SYNTAX      Counter32
    MAX-ACCESS  read-write
    STATUS      current
    DESCRIPTION 
        "Number of times Automatic Callback has been activated for a given group"
    ::= { bwACBGroupEntry 3 }

  bwACBGroupExpired OBJECT-TYPE
    SYNTAX      Counter32
    MAX-ACCESS  read-write
    STATUS      current
    DESCRIPTION 
        "Number of times Automatic Callback's time to wait for an idle line has expired for a given group. The default time to wait is 30 minutes."
    ::= { bwACBGroupEntry 4 }

  bwACBGroupMaxOrigSession OBJECT-TYPE
    SYNTAX      Counter32
    MAX-ACCESS  read-write
    STATUS      current
    DESCRIPTION 
        "Group level, number of times the max number of Automatic Callback sessions has been reached for the originator."
    ::= { bwACBGroupEntry 6 }

  bwACBGroupMaxTermSession OBJECT-TYPE
    SYNTAX      Counter32
    MAX-ACCESS  read-write
    STATUS      current
    DESCRIPTION 
        "Group level, number of times the max number of Automatic Callback sessions has been reached for the terminator."
    ::= { bwACBGroupEntry 7 }

  bwLegacyACBGroupOrigSession OBJECT-TYPE
    SYNTAX      Counter32
    MAX-ACCESS  read-write
    STATUS      current
    DESCRIPTION 
        "This is the number of times the Automatic Callback session has been initiated.  There is one instance of this counter for each group defined in the system."
    ::= { bwACBGroupEntry 8 }

  bwLegacyACBGroupOrigSuccessSession OBJECT-TYPE
    SYNTAX      Counter32
    MAX-ACCESS  read-write
    STATUS      current
    DESCRIPTION 
        "This is the number of times the Automatic Callback session has been initiated successfully.  There is one instance of this counter for each group defined in the system."
    ::= { bwACBGroupEntry 9 }

  bwLegacyACBGroupOrigFailedSession OBJECT-TYPE
    SYNTAX      Counter32
    MAX-ACCESS  read-write
    STATUS      current
    DESCRIPTION 
        "This is the number of times the Automatic Callback session has failed.  There is one instance of this counter for each group defined in the system."
    ::= { bwACBGroupEntry 10 }

  bwLegacyACBGroupTermSession OBJECT-TYPE
    SYNTAX      Counter32
    MAX-ACCESS  read-write
    STATUS      current
    DESCRIPTION 
        "This is the number of times an Automatic Callback session request has been received on this switch.  There is one instance of this counter for each group defined in the system."
    ::= { bwACBGroupEntry 11 }

  bwLegacyACBGroupTermSuccessSession OBJECT-TYPE
    SYNTAX      Counter32
    MAX-ACCESS  read-write
    STATUS      current
    DESCRIPTION 
        "This is the number of times an Automatic Callback session request has been received on this switch successfully.  There is one instance of this counter for each group defined in the system."
    ::= { bwACBGroupEntry 12 }

  bwLegacyACBGroupTermFailedSession OBJECT-TYPE
    SYNTAX      Counter32
    MAX-ACCESS  read-write
    STATUS      current
    DESCRIPTION 
        "This is the number of times an Automatic Callback session request has failed on this switch.  There is one instance of this counter for each group defined in the system."
    ::= { bwACBGroupEntry 13 }

  bwACBMaxOrigSession OBJECT-TYPE
    SYNTAX      Counter32
    MAX-ACCESS  read-write
    STATUS      current
    DESCRIPTION 
        "System wide, number of times the max number of Automatic Callback sessions has been reached for the originator."
    ::= { acb 6 }

  bwACBMaxTermSession OBJECT-TYPE
    SYNTAX      Counter32
    MAX-ACCESS  read-write
    STATUS      current
    DESCRIPTION 
        "System wide, number of times the max number of Automatic Callback sessions has been reached for the terminator."
    ::= { acb 7 }

  bwLegacyACBOrigSession OBJECT-TYPE
    SYNTAX      Counter32
    MAX-ACCESS  read-write
    STATUS      current
    DESCRIPTION 
        "This is the number of times the Automatic Callback session has been initiated."
    ::= { acb 8 }

  bwLegacyACBOrigSuccessSession OBJECT-TYPE
    SYNTAX      Counter32
    MAX-ACCESS  read-write
    STATUS      current
    DESCRIPTION 
        "This is the number of times the Automatic Callback session has been initiated successfully."
    ::= { acb 9 }

  bwLegacyACBOrigFailedSession OBJECT-TYPE
    SYNTAX      Counter32
    MAX-ACCESS  read-write
    STATUS      current
    DESCRIPTION 
        "This is the number of times the Automatic Callback session has failed."
    ::= { acb 10 }

  bwLegacyACBTermSession OBJECT-TYPE
    SYNTAX      Counter32
    MAX-ACCESS  read-write
    STATUS      current
    DESCRIPTION 
        "This is the number of times an Automatic Callback session request has been received on this switch."
    ::= { acb 11 }

  bwLegacyACBTermSuccessSession OBJECT-TYPE
    SYNTAX      Counter32
    MAX-ACCESS  read-write
    STATUS      current
    DESCRIPTION 
        "This is the number of times an Automatic Callback session request has been received on this switch successfully."
    ::= { acb 12 }

  bwLegacyACBTermFailedSession OBJECT-TYPE
    SYNTAX      Counter32
    MAX-ACCESS  read-write
    STATUS      current
    DESCRIPTION 
        "This is the number of times an Automatic Callback session request has failed on this switch."
    ::= { acb 13 }

-- Service : Sequential Ring ...........................................

  bwSequentialRingNumAttempts OBJECT-TYPE
    SYNTAX      Counter32
    MAX-ACCESS  read-write
    STATUS      current
    DESCRIPTION 
        "This counter is incremented whenever the sequential ring service forwards a call to the next in the list. The counter is not incremented for an attempt to alert the base location, unless it appears in the sequential ring list."
    ::= { sequentialRing 1 }

  bwSequentialRingNumNoAnswer OBJECT-TYPE
    SYNTAX      Counter32
    MAX-ACCESS  read-write
    STATUS      current
    DESCRIPTION 
        "This counter is incremented whenever the sequential ring service reaches the end of the list, and no users are available"
    ::= { sequentialRing 2 }

  bwSequentialRingSPTable OBJECT-TYPE
    SYNTAX      SEQUENCE OF BwSequentialRingSPEntry
    MAX-ACCESS  not-accessible
    STATUS      current
    DESCRIPTION 
        "This table tracks sequential ring measurements per service provider"
    ::= { sequentialRing 3 }

  bwSequentialRingSPEntry OBJECT-TYPE
    SYNTAX      BwSequentialRingSPEntry
    MAX-ACCESS  not-accessible
    STATUS      current
    DESCRIPTION 
        "Each row contains the service counters for the sequentialRing service for each service provider in the system"
    INDEX       { bwSequentialRingSPIndex }
    ::= { bwSequentialRingSPTable 1 }

  BwSequentialRingSPEntry ::= SEQUENCE {
    bwSequentialRingSPIndex         Unsigned32,
    bwSequentialRingSPID            DisplayString,
    bwSequentialRingSPNumAttempts   Counter32,
    bwSequentialRingSPNumNoAnswer   Counter32,
    bwSequentialRingSPActivations   Counter32,
    bwSequentialRingSPAnswered      Counter32,
    bwSequentialRingSPAbandoned     Counter32
  }

  bwSequentialRingSPIndex OBJECT-TYPE
    SYNTAX      Unsigned32
    MAX-ACCESS  read-only
    STATUS      current
    DESCRIPTION 
        "This column represents the index of the service provider in the system"
    ::= { bwSequentialRingSPEntry 1 }

  bwSequentialRingSPID OBJECT-TYPE
    SYNTAX      DisplayString
    MAX-ACCESS  read-only
    STATUS      current
    DESCRIPTION 
        "This string represents a service provider ID"
    ::= { bwSequentialRingSPEntry 2 }

  bwSequentialRingSPNumAttempts OBJECT-TYPE
    SYNTAX      Counter32
    MAX-ACCESS  read-write
    STATUS      current
    DESCRIPTION 
        "This counter is incremented whenever the sequential ring service forwards a call to the next user in the list for a given service provider. The counter is not incremented for an attempt to alert the base location, unless it appears in the sequential ring list."
    ::= { bwSequentialRingSPEntry 3 }

  bwSequentialRingSPNumNoAnswer OBJECT-TYPE
    SYNTAX      Counter32
    MAX-ACCESS  read-write
    STATUS      current
    DESCRIPTION 
        "This counter is incremented whenever the sequential ring service reaches the end of the list, and no users are available for a given service provider"
    ::= { bwSequentialRingSPEntry 4 }

  bwSequentialRingSPActivations OBJECT-TYPE
    SYNTAX      Counter32
    MAX-ACCESS  read-write
    STATUS      current
    DESCRIPTION 
        "This counter is incremented every time the Sequential Ring service is activated by an incoming call (service is active and screening is successful) for a given Service Provider."
    ::= { bwSequentialRingSPEntry 5 }

  bwSequentialRingSPAnswered OBJECT-TYPE
    SYNTAX      Counter32
    MAX-ACCESS  read-write
    STATUS      current
    DESCRIPTION 
        "This counter is incremented every time a caller gets connected to a location as a result of Sequential Ring for a given Service Provider"
    ::= { bwSequentialRingSPEntry 6 }

  bwSequentialRingSPAbandoned OBJECT-TYPE
    SYNTAX      Counter32
    MAX-ACCESS  read-write
    STATUS      current
    DESCRIPTION 
        "This counter is incremented every time a caller hangs up before Sequential Ring completes for a given Service Provider"
    ::= { bwSequentialRingSPEntry 7 }

  bwSequentialRingGroupTable OBJECT-TYPE
    SYNTAX      SEQUENCE OF BwSequentialRingGroupEntry
    MAX-ACCESS  not-accessible
    STATUS      current
    DESCRIPTION 
        "This table tracks sequential ring measurements per groups"
    ::= { sequentialRing 4 }

  bwSequentialRingGroupEntry OBJECT-TYPE
    SYNTAX      BwSequentialRingGroupEntry
    MAX-ACCESS  not-accessible
    STATUS      current
    DESCRIPTION 
        "Each row contains the service counters for the sequentialRing service for each group in the system"
    INDEX       { bwSequentialRingGroupIndex }
    ::= { bwSequentialRingGroupTable 1 }

  BwSequentialRingGroupEntry ::= SEQUENCE {
    bwSequentialRingGroupIndex          Unsigned32,
    bwSequentialRingGroupID             DisplayString,
    bwSequentialRingGroupNumAttempts    Counter32,
    bwSequentialRingGroupNumNoAnswer    Counter32,
    bwSequentialRingGroupActivations    Counter32,
    bwSequentialRingGroupAnswered       Counter32,
    bwSequentialRingGroupAbandoned      Counter32
  }

  bwSequentialRingGroupIndex OBJECT-TYPE
    SYNTAX      Unsigned32
    MAX-ACCESS  read-only
    STATUS      current
    DESCRIPTION 
        "This column represents the index of the group in the system"
    ::= { bwSequentialRingGroupEntry 1 }

  bwSequentialRingGroupID OBJECT-TYPE
    SYNTAX      DisplayString
    MAX-ACCESS  read-only
    STATUS      current
    DESCRIPTION 
        "This string represents a group ID"
    ::= { bwSequentialRingGroupEntry 2 }

  bwSequentialRingGroupNumAttempts OBJECT-TYPE
    SYNTAX      Counter32
    MAX-ACCESS  read-write
    STATUS      current
    DESCRIPTION 
        "This counter is incremented whenever the sequential ring service forwards a call to the next user in the list for a given group. The counter is not incremented for an attempt to alert the base location, unless it appears in the sequential ring list."
    ::= { bwSequentialRingGroupEntry 3 }

  bwSequentialRingGroupNumNoAnswer OBJECT-TYPE
    SYNTAX      Counter32
    MAX-ACCESS  read-write
    STATUS      current
    DESCRIPTION 
        "This counter is incremented whenever the sequential ring service reaches the end of the list, and no users are available for a given group"
    ::= { bwSequentialRingGroupEntry 4 }

  bwSequentialRingGroupActivations OBJECT-TYPE
    SYNTAX      Counter32
    MAX-ACCESS  read-write
    STATUS      current
    DESCRIPTION 
        "This counter is incremented every time the Sequential Ring service is activated by an incoming call (service is active and screening is successful) for a given Group"
    ::= { bwSequentialRingGroupEntry 5 }

  bwSequentialRingGroupAnswered OBJECT-TYPE
    SYNTAX      Counter32
    MAX-ACCESS  read-write
    STATUS      current
    DESCRIPTION 
        "This counter is incremented every time a caller gets connected to a location as a result of Sequential Ring for a given Group"
    ::= { bwSequentialRingGroupEntry 6 }

  bwSequentialRingGroupAbandoned OBJECT-TYPE
    SYNTAX      Counter32
    MAX-ACCESS  read-write
    STATUS      current
    DESCRIPTION 
        "This counter is incremented every time a caller hangs up before Sequential Ring completes for a given Group"
    ::= { bwSequentialRingGroupEntry 7 }

  bwSequentialRingActivations OBJECT-TYPE
    SYNTAX      Counter32
    MAX-ACCESS  read-write
    STATUS      current
    DESCRIPTION 
        "This counter is incremented every time the Sequential Ring service is activated by an incoming call (service is active and screening is successful)."
    ::= { sequentialRing 5 }

  bwSequentialRingAnswered OBJECT-TYPE
    SYNTAX      Counter32
    MAX-ACCESS  read-write
    STATUS      current
    DESCRIPTION 
        "This counter is incremented every time a caller gets connected to a location as a result of Sequential Ring"
    ::= { sequentialRing 6 }

  bwSequentialRingAbandoned OBJECT-TYPE
    SYNTAX      Counter32
    MAX-ACCESS  read-write
    STATUS      current
    DESCRIPTION 
        "This counter is incremented every time a caller hangs up before Sequential Ring completes"
    ::= { sequentialRing 7 }

-- Service : Ring Timeout ...........................................

  bwRingTimeoutNumExpires OBJECT-TYPE
    SYNTAX      Counter32
    MAX-ACCESS  read-write
    STATUS      current
    DESCRIPTION 
        "Number of times the ring timeout timer expires for the entire system."
    ::= { ringTimeout 1 }

  bwRingTimeoutSPTable OBJECT-TYPE
    SYNTAX      SEQUENCE OF BwRingTimeoutSPEntry
    MAX-ACCESS  not-accessible
    STATUS      current
    DESCRIPTION 
        "Counters for the Ring Timeout service measurements for service providers"
    ::= { ringTimeout 2 }

  bwRingTimeoutSPEntry OBJECT-TYPE
    SYNTAX      BwRingTimeoutSPEntry
    MAX-ACCESS  not-accessible
    STATUS      current
    DESCRIPTION 
        "Each row contains the service counters for the Ring Timeout service for each service provider in the system"
    INDEX       { bwRingTimeoutSPIndex }
    ::= { bwRingTimeoutSPTable 1 }

  BwRingTimeoutSPEntry ::= SEQUENCE {
    bwRingTimeoutSPIndex        Unsigned32,
    bwRingTimeoutSPID           DisplayString,
    bwRingTimeoutSPNumExpires   Counter32
  }

  bwRingTimeoutSPIndex OBJECT-TYPE
    SYNTAX      Unsigned32
    MAX-ACCESS  read-only
    STATUS      current
    DESCRIPTION 
        "This column represents the index of the service provider in the system"
    ::= { bwRingTimeoutSPEntry 1 }

  bwRingTimeoutSPID OBJECT-TYPE
    SYNTAX      DisplayString
    MAX-ACCESS  read-only
    STATUS      current
    DESCRIPTION 
        "This string represents a service provider ID"
    ::= { bwRingTimeoutSPEntry 2 }

  bwRingTimeoutSPNumExpires OBJECT-TYPE
    SYNTAX      Counter32
    MAX-ACCESS  read-write
    STATUS      current
    DESCRIPTION 
        "Number of times the ring timeout timer expires for a given service provider"
    ::= { bwRingTimeoutSPEntry 3 }

  bwRingTimeoutGroupTable OBJECT-TYPE
    SYNTAX      SEQUENCE OF BwRingTimeoutGroupEntry
    MAX-ACCESS  not-accessible
    STATUS      current
    DESCRIPTION 
        "Counters for the Ring Timeout service measurements for groups"
    ::= { ringTimeout 3 }

  bwRingTimeoutGroupEntry OBJECT-TYPE
    SYNTAX      BwRingTimeoutGroupEntry
    MAX-ACCESS  not-accessible
    STATUS      current
    DESCRIPTION 
        "Each row contains the service counters for the Ring Timeout service for each group in the system"
    INDEX       { bwRingTimeoutGroupIndex }
    ::= { bwRingTimeoutGroupTable 1 }

  BwRingTimeoutGroupEntry ::= SEQUENCE {
    bwRingTimeoutGroupIndex         Unsigned32,
    bwRingTimeoutGroupID            DisplayString,
    bwRingTimeoutGroupNumExpires    Counter32
  }

  bwRingTimeoutGroupIndex OBJECT-TYPE
    SYNTAX      Unsigned32
    MAX-ACCESS  read-only
    STATUS      current
    DESCRIPTION 
        "This column represents the index of the group in the system"
    ::= { bwRingTimeoutGroupEntry 1 }

  bwRingTimeoutGroupID OBJECT-TYPE
    SYNTAX      DisplayString
    MAX-ACCESS  read-only
    STATUS      current
    DESCRIPTION 
        "This string represents a group ID"
    ::= { bwRingTimeoutGroupEntry 2 }

  bwRingTimeoutGroupNumExpires OBJECT-TYPE
    SYNTAX      Counter32
    MAX-ACCESS  read-write
    STATUS      current
    DESCRIPTION 
        "Number of times the ring timeout timer expires for a given group"
    ::= { bwRingTimeoutGroupEntry 3 }

-- Service : video Add On ...........................................

  bwVAOOutgoingAttempts OBJECT-TYPE
    SYNTAX      Counter32
    MAX-ACCESS  read-write
    STATUS      current
    DESCRIPTION 
        "This counter is incremented each time a video add on call is attempted for an outgoing call."
    ::= { videoAddOn 1 }

  bwVAOOutgoingSuccess OBJECT-TYPE
    SYNTAX      Counter32
    MAX-ACCESS  read-write
    STATUS      current
    DESCRIPTION 
        "This counter is incremented each time a video add on call attempt is successful for an outgoing call."
    ::= { videoAddOn 2 }

  bwVAOIncomingAttempts OBJECT-TYPE
    SYNTAX      Counter32
    MAX-ACCESS  read-write
    STATUS      current
    DESCRIPTION 
        "This counter is incremented each time a video add on call is attempted for an incoming call."
    ::= { videoAddOn 3 }

  bwVAOIncomingSuccess OBJECT-TYPE
    SYNTAX      Counter32
    MAX-ACCESS  read-write
    STATUS      current
    DESCRIPTION 
        "This counter is incremented each time a video add on call attempt is successful for an incoming call."
    ::= { videoAddOn 4 }

  bwVAOSPTable OBJECT-TYPE
    SYNTAX      SEQUENCE OF BwVAOSPEntry
    MAX-ACCESS  not-accessible
    STATUS      current
    DESCRIPTION 
        "Counters for the Ring Timeout service measurements for service providers"
    ::= { videoAddOn 5 }

  bwVAOSPEntry OBJECT-TYPE
    SYNTAX      BwVAOSPEntry
    MAX-ACCESS  not-accessible
    STATUS      current
    DESCRIPTION 
        "Each row contains the service counters for the Video Add-On service for each service provider in the system"
    INDEX       { bwVAOSPIndex }
    ::= { bwVAOSPTable 1 }

  BwVAOSPEntry ::= SEQUENCE {
    bwVAOSPIndex                Unsigned32,
    bwVAOSPID                   DisplayString,
    bwVAOSPOutgoingAttempts     Counter32,
    bwVAOSPOutgoingSuccess      Counter32,
    bwVAOSPIncomingAttempts     Counter32,
    bwVAOSPIncomingSuccess      Counter32
  }

  bwVAOSPIndex OBJECT-TYPE
    SYNTAX      Unsigned32
    MAX-ACCESS  read-only
    STATUS      current
    DESCRIPTION 
        "This column represents the index of the service provider in the system"
    ::= { bwVAOSPEntry 1 }

  bwVAOSPID OBJECT-TYPE
    SYNTAX      DisplayString
    MAX-ACCESS  read-only
    STATUS      current
    DESCRIPTION 
        "This string represents a service provider ID"
    ::= { bwVAOSPEntry 2 }

  bwVAOSPOutgoingAttempts OBJECT-TYPE
    SYNTAX      Counter32
    MAX-ACCESS  read-write
    STATUS      current
    DESCRIPTION 
        "This counter is incremented each time a video add on call is attempted for an outgoing call for the given service provider."
    ::= { bwVAOSPEntry 3 }

  bwVAOSPOutgoingSuccess OBJECT-TYPE
    SYNTAX      Counter32
    MAX-ACCESS  read-write
    STATUS      current
    DESCRIPTION 
        "This counter is incremented each time a video add on call attempt is successful for an outgoing call for the given service provider."
    ::= { bwVAOSPEntry 4 }

  bwVAOSPIncomingAttempts OBJECT-TYPE
    SYNTAX      Counter32
    MAX-ACCESS  read-write
    STATUS      current
    DESCRIPTION 
        "This counter is incremented each time a video add on call is attempted for an incoming call for the given service provider."
    ::= { bwVAOSPEntry 5 }

  bwVAOSPIncomingSuccess OBJECT-TYPE
    SYNTAX      Counter32
    MAX-ACCESS  read-write
    STATUS      current
    DESCRIPTION 
        "This counter is incremented each time a video add on call attempt is successful for an incoming call for the given service provider."
    ::= { bwVAOSPEntry 6 }

  bwVAOGroupTable OBJECT-TYPE
    SYNTAX      SEQUENCE OF BwVAOGroupEntry
    MAX-ACCESS  not-accessible
    STATUS      current
    DESCRIPTION 
        "Counters for the Ring Timeout service measurements for groups"
    ::= { videoAddOn 6 }

  bwVAOGroupEntry OBJECT-TYPE
    SYNTAX      BwVAOGroupEntry
    MAX-ACCESS  not-accessible
    STATUS      current
    DESCRIPTION 
        "Each row contains the service counters for the Video Add-On service for each group in the system"
    INDEX       { bwVAOGroupIndex }
    ::= { bwVAOGroupTable 1 }

  BwVAOGroupEntry ::= SEQUENCE {
    bwVAOGroupIndex             Unsigned32,
    bwVAOGroupID                DisplayString,
    bwVAOGroupOutgoingAttempts  Counter32,
    bwVAOGroupOutgoingSuccess   Counter32,
    bwVAOGroupIncomingAttempts  Counter32,
    bwVAOGroupIncomingSuccess   Counter32
  }

  bwVAOGroupIndex OBJECT-TYPE
    SYNTAX      Unsigned32
    MAX-ACCESS  read-only
    STATUS      current
    DESCRIPTION 
        "This column represents the index of the group in the system"
    ::= { bwVAOGroupEntry 1 }

  bwVAOGroupID OBJECT-TYPE
    SYNTAX      DisplayString
    MAX-ACCESS  read-only
    STATUS      current
    DESCRIPTION 
        "This string represents a group ID"
    ::= { bwVAOGroupEntry 2 }

  bwVAOGroupOutgoingAttempts OBJECT-TYPE
    SYNTAX      Counter32
    MAX-ACCESS  read-write
    STATUS      current
    DESCRIPTION 
        "This counter is incremented each time a video add on call is attempted for an outgoing call for the given group."
    ::= { bwVAOGroupEntry 3 }

  bwVAOGroupOutgoingSuccess OBJECT-TYPE
    SYNTAX      Counter32
    MAX-ACCESS  read-write
    STATUS      current
    DESCRIPTION 
        "This counter is incremented each time a video add on call attempt is successful for an outgoing call for the given group."
    ::= { bwVAOGroupEntry 4 }

  bwVAOGroupIncomingAttempts OBJECT-TYPE
    SYNTAX      Counter32
    MAX-ACCESS  read-write
    STATUS      current
    DESCRIPTION 
        "This counter is incremented each time a video add on call is attempted for an incoming call for the given group."
    ::= { bwVAOGroupEntry 5 }

  bwVAOGroupIncomingSuccess OBJECT-TYPE
    SYNTAX      Counter32
    MAX-ACCESS  read-write
    STATUS      current
    DESCRIPTION 
        "This counter is incremented each time a video add on call attempt is successful for an incoming call for the given group."
    ::= { bwVAOGroupEntry 6 }

-- Service : Malicious Call Trace ...........................................

  bwMaliciousCallTraceApplied OBJECT-TYPE
    SYNTAX      Counter32
    MAX-ACCESS  read-write
    STATUS      current
    DESCRIPTION 
        "This counter is incremented each time a the Malicious Call Trace serevice is activated."
    ::= { mct 1 }

  bwMaliciousCallTraceAnnouncement OBJECT-TYPE
    SYNTAX      Counter32
    MAX-ACCESS  read-write
    STATUS      current
    DESCRIPTION
       "Number of Malicious Call Trace Announcements attempted."
    ::= { mct 4 }

  bwMaliciousCallTraceSPTable OBJECT-TYPE
    SYNTAX      SEQUENCE OF BwMaliciousCallTraceSPEntry
    MAX-ACCESS  not-accessible
    STATUS      current
    DESCRIPTION 
        "Counters for the Malicious Call Trace service measurements for service providers"
    ::= { mct 2 }

  bwMaliciousCallTraceSPEntry OBJECT-TYPE
    SYNTAX      BwMaliciousCallTraceSPEntry
    MAX-ACCESS  not-accessible
    STATUS      current
    DESCRIPTION 
        "Each row contains the service counters for the Malicious Call Trace service for each service provider in the system"
    INDEX       { bwMaliciousCallTraceSPIndex }
    ::= { bwMaliciousCallTraceSPTable 1 }

  BwMaliciousCallTraceSPEntry ::= SEQUENCE {
    bwMaliciousCallTraceSPIndex        Unsigned32,
    bwMaliciousCallTraceSPID           DisplayString,
    bwMaliciousCallTraceSPApplied      Counter32,
    bwMaliciousCallTraceSPAnnouncement Counter32
  }

  bwMaliciousCallTraceSPIndex OBJECT-TYPE
    SYNTAX      Unsigned32
    MAX-ACCESS  read-only
    STATUS      current
    DESCRIPTION 
        "This column represents the index of the service provider in the system"
    ::= { bwMaliciousCallTraceSPEntry 1 }

  bwMaliciousCallTraceSPID OBJECT-TYPE
    SYNTAX      DisplayString
    MAX-ACCESS  read-only
    STATUS      current
    DESCRIPTION 
        "This string represents a service provider ID"
    ::= { bwMaliciousCallTraceSPEntry 2 }

  bwMaliciousCallTraceSPApplied OBJECT-TYPE
    SYNTAX      Counter32
    MAX-ACCESS  read-write
    STATUS      current
    DESCRIPTION 
        "This counter is incremented each time a the Malicious Call Trace serevice is activated for the given service provider."
    ::= { bwMaliciousCallTraceSPEntry 3 }

  bwMaliciousCallTraceSPAnnouncement OBJECT-TYPE
    SYNTAX      Counter32
    MAX-ACCESS  read-write
    STATUS      current
    DESCRIPTION
        "Number of Malicious Call Trace Announcements attempted for users in a given service provider."
    ::= { bwMaliciousCallTraceSPEntry 4 }

  bwMaliciousCallTraceGroupTable OBJECT-TYPE
    SYNTAX      SEQUENCE OF BwMaliciousCallTraceGroupEntry
    MAX-ACCESS  not-accessible
    STATUS      current
    DESCRIPTION 
        "Counters for the Malicious Call Trace service measurements for groups"
    ::= { mct 3 }

  bwMaliciousCallTraceGroupEntry OBJECT-TYPE
    SYNTAX      BwMaliciousCallTraceGroupEntry
    MAX-ACCESS  not-accessible
    STATUS      current
    DESCRIPTION 
        "Each row contains the service counters for the Malicious Call Trace service for each group in the system"
    INDEX       { bwMaliciousCallTraceGroupIndex }
    ::= { bwMaliciousCallTraceGroupTable 1 }

  BwMaliciousCallTraceGroupEntry ::= SEQUENCE {
    bwMaliciousCallTraceGroupIndex        Unsigned32,
    bwMaliciousCallTraceGroupID           DisplayString,
    bwMaliciousCallTraceGroupApplied      Counter32,
    bwMaliciousCallTraceGroupAnnouncement Counter32
  }

  bwMaliciousCallTraceGroupIndex OBJECT-TYPE
    SYNTAX      Unsigned32
    MAX-ACCESS  read-only
    STATUS      current
    DESCRIPTION 
        "This column represents the index of the service provider in the system"
    ::= { bwMaliciousCallTraceGroupEntry 1 }

  bwMaliciousCallTraceGroupID OBJECT-TYPE
    SYNTAX      DisplayString
    MAX-ACCESS  read-only
    STATUS      current
    DESCRIPTION 
        "This string represents a service provider ID"
    ::= { bwMaliciousCallTraceGroupEntry 2 }

  bwMaliciousCallTraceGroupApplied OBJECT-TYPE
    SYNTAX      Counter32
    MAX-ACCESS  read-write
    STATUS      current
    DESCRIPTION 
        "This counter is incremented each time a the Malicious Call Trace serevice is activated for the given group."
    ::= { bwMaliciousCallTraceGroupEntry 3 }

  bwMaliciousCallTraceGroupAnnouncement  OBJECT-TYPE
    SYNTAX      Counter32
    MAX-ACCESS  read-write
    STATUS      current
    DESCRIPTION
        "Number of Malicious Call Trace Announcements attempted for user in a given group."
    ::=  {  bwMaliciousCallTraceGroupEntry  4  }

-- Service : Push To Talk ...........................................

  bwPTTInvoke OBJECT-TYPE
    SYNTAX      Counter32
    MAX-ACCESS  read-write
    STATUS      current
    DESCRIPTION 
        "Counts the number of times a user has originated a Push to Talk call."
    ::= { pushToTalk 1 }

  bwPTTReject OBJECT-TYPE
    SYNTAX      Counter32
    MAX-ACCESS  read-write
    STATUS      current
    DESCRIPTION 
        "Counts the number of times a user has rejected a Push to Talk call because of their access list."
    ::= { pushToTalk 2 }

  bwPTTSPTable OBJECT-TYPE
    SYNTAX      SEQUENCE OF BwPTTSPEntry
    MAX-ACCESS  not-accessible
    STATUS      current
    DESCRIPTION 
        "Counters for the Push To Talk service measurements for service providers"
    ::= { pushToTalk 3 }

  bwPTTSPEntry OBJECT-TYPE
    SYNTAX      BwPTTSPEntry
    MAX-ACCESS  not-accessible
    STATUS      current
    DESCRIPTION 
        "Each row contains the service counters for the Push To Talk service for each service provider in the system"
    INDEX       { bwPTTSPIndex }
    ::= { bwPTTSPTable 1 }

  BwPTTSPEntry ::= SEQUENCE {
    bwPTTSPIndex    Unsigned32,
    bwPTTSPID       DisplayString,
    bwPTTSPInvoke   Counter32,
    bwPTTSPReject   Counter32
  }

  bwPTTSPIndex OBJECT-TYPE
    SYNTAX      Unsigned32
    MAX-ACCESS  read-only
    STATUS      current
    DESCRIPTION 
        "This column represents the index of the service provider in the system"
    ::= { bwPTTSPEntry 1 }

  bwPTTSPID OBJECT-TYPE
    SYNTAX      DisplayString
    MAX-ACCESS  read-only
    STATUS      current
    DESCRIPTION 
        "This string represents a service provider ID"
    ::= { bwPTTSPEntry 2 }

  bwPTTSPInvoke OBJECT-TYPE
    SYNTAX      Counter32
    MAX-ACCESS  read-write
    STATUS      current
    DESCRIPTION 
        "Counts the number of times a user has originated a Push to Talk call for a given service provider."
    ::= { bwPTTSPEntry 3 }

  bwPTTSPReject OBJECT-TYPE
    SYNTAX      Counter32
    MAX-ACCESS  read-write
    STATUS      current
    DESCRIPTION 
        "Counts the number of times a user has rejected a Push to Talk call because of their access list for a given service provider."
    ::= { bwPTTSPEntry 4 }

  bwPTTGroupTable OBJECT-TYPE
    SYNTAX      SEQUENCE OF BwPTTGroupEntry
    MAX-ACCESS  not-accessible
    STATUS      current
    DESCRIPTION 
        "Counters for the Push To Talk service measurements for groups"
    ::= { pushToTalk 4 }

  bwPTTGroupEntry OBJECT-TYPE
    SYNTAX      BwPTTGroupEntry
    MAX-ACCESS  not-accessible
    STATUS      current
    DESCRIPTION 
        "Each row contains the service counters for the Push To Talk service for each group in the system"
    INDEX       { bwPTTGroupIndex }
    ::= { bwPTTGroupTable 1 }

  BwPTTGroupEntry ::= SEQUENCE {
    bwPTTGroupIndex     Unsigned32,
    bwPTTGroupID        DisplayString,
    bwPTTGroupInvoke    Counter32,
    bwPTTGroupReject    Counter32
  }

  bwPTTGroupIndex OBJECT-TYPE
    SYNTAX      Unsigned32
    MAX-ACCESS  read-only
    STATUS      current
    DESCRIPTION 
        "This column represents the index of the group in the system"
    ::= { bwPTTGroupEntry 1 }

  bwPTTGroupID OBJECT-TYPE
    SYNTAX      DisplayString
    MAX-ACCESS  read-only
    STATUS      current
    DESCRIPTION 
        "This string represents a group ID"
    ::= { bwPTTGroupEntry 2 }

  bwPTTGroupInvoke OBJECT-TYPE
    SYNTAX      Counter32
    MAX-ACCESS  read-write
    STATUS      current
    DESCRIPTION 
        "Counts the number of times a user has originated a Push to Talk call for a given group."
    ::= { bwPTTGroupEntry 3 }

  bwPTTGroupReject OBJECT-TYPE
    SYNTAX      Counter32
    MAX-ACCESS  read-write
    STATUS      current
    DESCRIPTION 
        "Counts the number of times a user has rejected a Push to Talk call because of their access list for agiven group."
    ::= { bwPTTGroupEntry 4 }

-- Service : Hoteling ...........................................

  bwHotelingAssociate OBJECT-TYPE
    SYNTAX      Counter32
    MAX-ACCESS  read-write
    STATUS      current
    DESCRIPTION 
        "This counter is incremented each time a guest - host association is created."
    ::= { hoteling 1 }

  bwHotelingDisassociate OBJECT-TYPE
    SYNTAX      Counter32
    MAX-ACCESS  read-write
    STATUS      current
    DESCRIPTION 
        "This counter is incremented each time a guest - host association is removed."
    ::= { hoteling 2 }

  bwHotelingTimeout OBJECT-TYPE
    SYNTAX      Counter32
    MAX-ACCESS  read-write
    STATUS      current
    DESCRIPTION 
        "This counter is incremented each time a guest - host association is removed due to a timeout."
    ::= { hoteling 3 }

  bwHotelingSPTable OBJECT-TYPE
    SYNTAX      SEQUENCE OF BwHotelingSPEntry
    MAX-ACCESS  not-accessible
    STATUS      current
    DESCRIPTION 
        "Counters for the Hoteling service measurements for service providers"
    ::= { hoteling 4 }

  bwHotelingSPEntry OBJECT-TYPE
    SYNTAX      BwHotelingSPEntry
    MAX-ACCESS  not-accessible
    STATUS      current
    DESCRIPTION 
        "Each row contains the service counters for the Hoteling service for each service provider in the system"
    INDEX       { bwHotelingSPIndex }
    ::= { bwHotelingSPTable 1 }

  BwHotelingSPEntry ::= SEQUENCE {
    bwHotelingSPIndex           Unsigned32,
    bwHotelingSPID              DisplayString,
    bwHotelingSPAssociate       Counter32,
    bwHotelingSPDisassociate    Counter32,
    bwHotelingSPTimeout         Counter32
  }

  bwHotelingSPIndex OBJECT-TYPE
    SYNTAX      Unsigned32
    MAX-ACCESS  read-only
    STATUS      current
    DESCRIPTION 
        "This column represents the index of the service provider in the system"
    ::= { bwHotelingSPEntry 1 }

  bwHotelingSPID OBJECT-TYPE
    SYNTAX      DisplayString
    MAX-ACCESS  read-only
    STATUS      current
    DESCRIPTION 
        "This string represents a service provider ID"
    ::= { bwHotelingSPEntry 2 }

  bwHotelingSPAssociate OBJECT-TYPE
    SYNTAX      Counter32
    MAX-ACCESS  read-write
    STATUS      current
    DESCRIPTION 
        "This counter is incremented each time a guest - host association is created for a given service provider."
    ::= { bwHotelingSPEntry 3 }

  bwHotelingSPDisassociate OBJECT-TYPE
    SYNTAX      Counter32
    MAX-ACCESS  read-write
    STATUS      current
    DESCRIPTION 
        "This counter is incremented each time a guest - host association is removed for a given service provider."
    ::= { bwHotelingSPEntry 4 }

  bwHotelingSPTimeout OBJECT-TYPE
    SYNTAX      Counter32
    MAX-ACCESS  read-write
    STATUS      current
    DESCRIPTION 
        "This counter is incremented each time a guest - host association is removed due to a timeout for a given service provider."
    ::= { bwHotelingSPEntry 5 }

  bwHotelingGroupTable OBJECT-TYPE
    SYNTAX      SEQUENCE OF BwHotelingGroupEntry
    MAX-ACCESS  not-accessible
    STATUS      current
    DESCRIPTION 
        "Counters for the Hoteling service measurements for groups"
    ::= { hoteling 5 }

  bwHotelingGroupEntry OBJECT-TYPE
    SYNTAX      BwHotelingGroupEntry
    MAX-ACCESS  not-accessible
    STATUS      current
    DESCRIPTION 
        "Each row contains the service counters for the Hoteling service for each group in the system"
    INDEX       { bwHotelingGroupIndex }
    ::= { bwHotelingGroupTable 1 }

  BwHotelingGroupEntry ::= SEQUENCE {
    bwHotelingGroupIndex            Unsigned32,
    bwHotelingGroupID               DisplayString,
    bwHotelingGroupAssociate        Counter32,
    bwHotelingGroupDisassociate     Counter32,
    bwHotelingGroupTimeout          Counter32
  }

  bwHotelingGroupIndex OBJECT-TYPE
    SYNTAX      Unsigned32
    MAX-ACCESS  read-only
    STATUS      current
    DESCRIPTION 
        "This column represents the index of the group in the system"
    ::= { bwHotelingGroupEntry 1 }

  bwHotelingGroupID OBJECT-TYPE
    SYNTAX      DisplayString
    MAX-ACCESS  read-only
    STATUS      current
    DESCRIPTION 
        "This string represents a group ID"
    ::= { bwHotelingGroupEntry 2 }

  bwHotelingGroupAssociate OBJECT-TYPE
    SYNTAX      Counter32
    MAX-ACCESS  read-write
    STATUS      current
    DESCRIPTION 
        "This counter is incremented each time a guest - host association is created for a given group."
    ::= { bwHotelingGroupEntry 3 }

  bwHotelingGroupDisassociate OBJECT-TYPE
    SYNTAX      Counter32
    MAX-ACCESS  read-write
    STATUS      current
    DESCRIPTION 
        "This counter is incremented each time a guest - host association is removed for a given group."
    ::= { bwHotelingGroupEntry 4 }

  bwHotelingGroupTimeout OBJECT-TYPE
    SYNTAX      Counter32
    MAX-ACCESS  read-write
    STATUS      current
    DESCRIPTION 
        "This counter is incremented each time a guest - host association is removed due to a timeout for a given group."
    ::= { bwHotelingGroupEntry 5 }

-- Service : Preferred Carrier ...........................................

  bwSubscriptionUserPIC OBJECT-TYPE
    SYNTAX      Counter32
    MAX-ACCESS  read-write
    STATUS      current
    DESCRIPTION 
        "This counter shall be incremented each time the user PICs are used, but not explicitly dialed."
    ::= { preferredCarrier 1 }

  bwSubscriptionGroupPIC OBJECT-TYPE
    SYNTAX      Counter32
    MAX-ACCESS  read-write
    STATUS      current
    DESCRIPTION 
        "This counter shall be incremented each time the group PICs are used, but not explicitly dialed."
    ::= { preferredCarrier 2 }

  bwSubscriptionServiceProviderPIC OBJECT-TYPE
    SYNTAX      Counter32
    MAX-ACCESS  read-write
    STATUS      current
    DESCRIPTION 
        "This counter shall be incremented each time the service provider PICs are used, but not explicitly dialed."
    ::= { preferredCarrier 3 }

  bwSubscriptionDialedUserPIC OBJECT-TYPE
    SYNTAX      Counter32
    MAX-ACCESS  read-write
    STATUS      current
    DESCRIPTION 
        "This counter shall be incremented each time the user PICs are used and explicitly dialed."
    ::= { preferredCarrier 4 }

  bwSubscriptionDialedGroupPIC OBJECT-TYPE
    SYNTAX      Counter32
    MAX-ACCESS  read-write
    STATUS      current
    DESCRIPTION 
        "This counter shall be incremented each time the group PICs are used and explicitly dialed."
    ::= { preferredCarrier 5 }

  bwSubscriptionDialedServiceProviderPIC OBJECT-TYPE
    SYNTAX      Counter32
    MAX-ACCESS  read-write
    STATUS      current
    DESCRIPTION 
        "This counter shall be incremented each time the service provider PICs are used and explicitly dialed."
    ::= { preferredCarrier 6 }

  bwNonSubscriptionDialedUserPIC OBJECT-TYPE
    SYNTAX      Counter32
    MAX-ACCESS  read-write
    STATUS      current
    DESCRIPTION 
        "This counter shall be incremented each time a casual dialed carrier is used instead of the user subscribed PIC."
    ::= { preferredCarrier 7 }

  bwNonSubscriptionDialedGroupPIC OBJECT-TYPE
    SYNTAX      Counter32
    MAX-ACCESS  read-write
    STATUS      current
    DESCRIPTION 
        "This counter shall be incremented each time a casual dialed carrier is used instead of the group subscribed PIC."
    ::= { preferredCarrier 8 }

  bwNonSubscriptionDialedServiceProviderPIC OBJECT-TYPE
    SYNTAX      Counter32
    MAX-ACCESS  read-write
    STATUS      current
    DESCRIPTION 
        "This counter shall be incremented each time a casual dialed carrier is used instead of the service provider subscribed PIC."
    ::= { preferredCarrier 9 }

  bwNoIndicationUserPIC OBJECT-TYPE
    SYNTAX      Counter32
    MAX-ACCESS  read-write
    STATUS      current
    DESCRIPTION 
        "This counter shall be incremented each time the user subscribed PIC is used, but with no indication on how this PIC was specified."
    ::= { preferredCarrier 10 }

  bwNoIndicationGroupPIC OBJECT-TYPE
    SYNTAX      Counter32
    MAX-ACCESS  read-write
    STATUS      current
    DESCRIPTION 
        "This counter shall be incremented each time the group subscribed PIC is used, but with no indication on how this PIC was specified."
    ::= { preferredCarrier 11 }

  bwNoIndicationServiceProviderPIC OBJECT-TYPE
    SYNTAX      Counter32
    MAX-ACCESS  read-write
    STATUS      current
    DESCRIPTION 
        "This counter shall be incremented each time the service provider subscribed PIC is used, but with no indication on how this PIC was specified."
    ::= { preferredCarrier 12 }

  bwPreferredCarrierSPTable OBJECT-TYPE
    SYNTAX      SEQUENCE OF BwPreferredCarrierSPEntry
    MAX-ACCESS  not-accessible
    STATUS      current
    DESCRIPTION 
        "Counters for the Preferred Carrier service measurements for service providers"
    ::= { preferredCarrier 13 }

  bwPreferredCarrierSPEntry OBJECT-TYPE
    SYNTAX      BwPreferredCarrierSPEntry
    MAX-ACCESS  not-accessible
    STATUS      current
    DESCRIPTION 
        "Each row contains the service counters for the Preferred Carrier service for each service provider in the system"
    INDEX       { bwPreferredCarrierSPIndex }
    ::= { bwPreferredCarrierSPTable 1 }

  BwPreferredCarrierSPEntry ::= SEQUENCE {
    bwPreferredCarrierSPIndex                       Unsigned32,
    bwPreferredCarrierSPID                          DisplayString,
    bwSPSubscriptionUserPIC                         Counter32,
    bwSPSubscriptionGroupPIC                        Counter32,
    bwSPSubscriptionServiceProviderPIC              Counter32,
    bwSPSubscriptionDialedUserPIC                   Counter32,
    bwSPSubscriptionDialedGroupPIC                  Counter32,
    bwSPSubscriptionDialedServiceProviderPIC        Counter32,
    bwSPNonSubscriptionDialedUserPIC                Counter32,
    bwSPNonSubscriptionDialedGroupPIC               Counter32,
    bwSPNonSubscriptionDialedServiceProviderPIC     Counter32,
    bwSPNoIndicationUserPIC                         Counter32,
    bwSPNoIndicationGroupPIC                        Counter32,
    bwSPNoIndicationServiceProviderPIC              Counter32
  }

  bwPreferredCarrierSPIndex OBJECT-TYPE
    SYNTAX      Unsigned32
    MAX-ACCESS  read-only
    STATUS      current
    DESCRIPTION 
        "This column represents the index of the service provider in the system"
    ::= { bwPreferredCarrierSPEntry 1 }

  bwPreferredCarrierSPID OBJECT-TYPE
    SYNTAX      DisplayString
    MAX-ACCESS  read-only
    STATUS      current
    DESCRIPTION 
        "This string represents a service provider ID"
    ::= { bwPreferredCarrierSPEntry 2 }

  bwSPSubscriptionUserPIC OBJECT-TYPE
    SYNTAX      Counter32
    MAX-ACCESS  read-write
    STATUS      current
    DESCRIPTION 
        "This counter shall be incremented each time the user PICs are used, but not explicitly dialed, on a per-service provider basis.."
    ::= { bwPreferredCarrierSPEntry 3 }

  bwSPSubscriptionGroupPIC OBJECT-TYPE
    SYNTAX      Counter32
    MAX-ACCESS  read-write
    STATUS      current
    DESCRIPTION 
        "This counter shall be incremented each time the group PICs are used, but not explicitly dialed, on a per-service provider basis.."
    ::= { bwPreferredCarrierSPEntry 4 }

  bwSPSubscriptionServiceProviderPIC OBJECT-TYPE
    SYNTAX      Counter32
    MAX-ACCESS  read-write
    STATUS      current
    DESCRIPTION 
        "This counter shall be incremented each time the service provider PICs are used, but not explicitly dialed, on a per-service provider basis.."
    ::= { bwPreferredCarrierSPEntry 5 }

  bwSPSubscriptionDialedUserPIC OBJECT-TYPE
    SYNTAX      Counter32
    MAX-ACCESS  read-write
    STATUS      current
    DESCRIPTION 
        "This counter shall be incremented each time the user PICs are used and explicitly dialed, on a per-service provider basis.."
    ::= { bwPreferredCarrierSPEntry 6 }

  bwSPSubscriptionDialedGroupPIC OBJECT-TYPE
    SYNTAX      Counter32
    MAX-ACCESS  read-write
    STATUS      current
    DESCRIPTION 
        "This counter shall be incremented each time the group PICs are used and explicitly dialed, on a per-service provider basis.."
    ::= { bwPreferredCarrierSPEntry 7 }

  bwSPSubscriptionDialedServiceProviderPIC OBJECT-TYPE
    SYNTAX      Counter32
    MAX-ACCESS  read-write
    STATUS      current
    DESCRIPTION 
        "This counter shall be incremented each time the service provider PICs are used and explicitly dialed, on a per-service provider basis.."
    ::= { bwPreferredCarrierSPEntry 8 }

  bwSPNonSubscriptionDialedUserPIC OBJECT-TYPE
    SYNTAX      Counter32
    MAX-ACCESS  read-write
    STATUS      current
    DESCRIPTION 
        "This counter shall be incremented each time a casual dialed carrier is used instead of the user subscribed PIC, on a per-service provider basis.."
    ::= { bwPreferredCarrierSPEntry 9 }

  bwSPNonSubscriptionDialedGroupPIC OBJECT-TYPE
    SYNTAX      Counter32
    MAX-ACCESS  read-write
    STATUS      current
    DESCRIPTION 
        "This counter shall be incremented each time a casual dialed carrier is used instead of the group subscribed PIC, on a per-service provider basis.."
    ::= { bwPreferredCarrierSPEntry 10 }

  bwSPNonSubscriptionDialedServiceProviderPIC OBJECT-TYPE
    SYNTAX      Counter32
    MAX-ACCESS  read-write
    STATUS      current
    DESCRIPTION 
        "This counter shall be incremented each time a casual dialed carrier is used instead of the service provider subscribed PIC, on a per-service provider basis.."
    ::= { bwPreferredCarrierSPEntry 11 }

  bwSPNoIndicationUserPIC OBJECT-TYPE
    SYNTAX      Counter32
    MAX-ACCESS  read-write
    STATUS      current
    DESCRIPTION 
        "This counter shall be incremented each time the user subscribed PIC is used, but with no indication on how this PIC was specified, on a per-service provider basis.."
    ::= { bwPreferredCarrierSPEntry 12 }

  bwSPNoIndicationGroupPIC OBJECT-TYPE
    SYNTAX      Counter32
    MAX-ACCESS  read-write
    STATUS      current
    DESCRIPTION 
        "This counter shall be incremented each time the group subscribed PIC is used, but with no indication on how this PIC was specified, on a per-service provider basis.."
    ::= { bwPreferredCarrierSPEntry 13 }

  bwSPNoIndicationServiceProviderPIC OBJECT-TYPE
    SYNTAX      Counter32
    MAX-ACCESS  read-write
    STATUS      current
    DESCRIPTION 
        "This counter shall be incremented each time the service provider subscribed PIC is used, but with no indication on how this PIC was specified, on a per-service provider basis.."
    ::= { bwPreferredCarrierSPEntry 14 }

  bwPreferredCarrierGroupTable OBJECT-TYPE
    SYNTAX      SEQUENCE OF BwPreferredCarrierGroupEntry
    MAX-ACCESS  not-accessible
    STATUS      current
    DESCRIPTION 
        "Counters for the Preferred Carrier service measurements for groups"
    ::= { preferredCarrier 14 }

  bwPreferredCarrierGroupEntry OBJECT-TYPE
    SYNTAX      BwPreferredCarrierGroupEntry
    MAX-ACCESS  not-accessible
    STATUS      current
    DESCRIPTION 
        "Each row contains the service counters for the Preferred Carrier service for each group in the system"
    INDEX       { bwPreferredCarrierGroupIndex }
    ::= { bwPreferredCarrierGroupTable 1 }

  BwPreferredCarrierGroupEntry ::= SEQUENCE {
    bwPreferredCarrierGroupIndex                    Unsigned32,
    bwPreferredCarrierGroupID                       DisplayString,
    bwGroupSubscriptionUserPIC                      Counter32,
    bwGroupSubscriptionGroupPIC                     Counter32,
    bwGroupSubscriptionServiceProviderPIC           Counter32,
    bwGroupSubscriptionDialedUserPIC                Counter32,
    bwGroupSubscriptionDialedGroupPIC               Counter32,
    bwGroupSubscriptionDialedServiceProviderPIC     Counter32,
    bwGroupNonSubscriptionDialedUserPIC             Counter32,
    bwGroupNonSubscriptionDialedGroupPIC            Counter32,
    bwGroupNonSubscriptionDialedServiceProviderPIC  Counter32,
    bwGroupNoIndicationUserPIC                      Counter32,
    bwGroupNoIndicationGroupPIC                     Counter32,
    bwGroupNoIndicationServiceProviderPIC           Counter32
  }

  bwPreferredCarrierGroupIndex OBJECT-TYPE
    SYNTAX      Unsigned32
    MAX-ACCESS  read-only
    STATUS      current
    DESCRIPTION 
        "This column represents the index of the group in the system"
    ::= { bwPreferredCarrierGroupEntry 1 }

  bwPreferredCarrierGroupID OBJECT-TYPE
    SYNTAX      DisplayString
    MAX-ACCESS  read-only
    STATUS      current
    DESCRIPTION 
        "This string represents a group ID"
    ::= { bwPreferredCarrierGroupEntry 2 }

  bwGroupSubscriptionUserPIC OBJECT-TYPE
    SYNTAX      Counter32
    MAX-ACCESS  read-write
    STATUS      current
    DESCRIPTION 
        "This counter shall be incremented each time the user PICs are used, but not explicitly dialed, on a per-group basis.."
    ::= { bwPreferredCarrierGroupEntry 3 }

  bwGroupSubscriptionGroupPIC OBJECT-TYPE
    SYNTAX      Counter32
    MAX-ACCESS  read-write
    STATUS      current
    DESCRIPTION 
        "This counter shall be incremented each time the group PICs are used, but not explicitly dialed, on a per-group basis.."
    ::= { bwPreferredCarrierGroupEntry 4 }

  bwGroupSubscriptionServiceProviderPIC OBJECT-TYPE
    SYNTAX      Counter32
    MAX-ACCESS  read-write
    STATUS      current
    DESCRIPTION 
        "This counter shall be incremented each time the service provider PICs are used, but not explicitly dialed, on a per-group basis.."
    ::= { bwPreferredCarrierGroupEntry 5 }

  bwGroupSubscriptionDialedUserPIC OBJECT-TYPE
    SYNTAX      Counter32
    MAX-ACCESS  read-write
    STATUS      current
    DESCRIPTION 
        "This counter shall be incremented each time the user PICs are used and explicitly dialed, on a per-group basis.."
    ::= { bwPreferredCarrierGroupEntry 6 }

  bwGroupSubscriptionDialedGroupPIC OBJECT-TYPE
    SYNTAX      Counter32
    MAX-ACCESS  read-write
    STATUS      current
    DESCRIPTION 
        "This counter shall be incremented each time the group PICs are used and explicitly dialed, on a per-group basis.."
    ::= { bwPreferredCarrierGroupEntry 7 }

  bwGroupSubscriptionDialedServiceProviderPIC OBJECT-TYPE
    SYNTAX      Counter32
    MAX-ACCESS  read-write
    STATUS      current
    DESCRIPTION 
        "This counter shall be incremented each time the service provider PICs are used and explicitly dialed, on a per-group basis.."
    ::= { bwPreferredCarrierGroupEntry 8 }

  bwGroupNonSubscriptionDialedUserPIC OBJECT-TYPE
    SYNTAX      Counter32
    MAX-ACCESS  read-write
    STATUS      current
    DESCRIPTION 
        "This counter shall be incremented each time a casual dialed carrier is used instead of the user subscribed PIC, on a per-group basis.."
    ::= { bwPreferredCarrierGroupEntry 9 }

  bwGroupNonSubscriptionDialedGroupPIC OBJECT-TYPE
    SYNTAX      Counter32
    MAX-ACCESS  read-write
    STATUS      current
    DESCRIPTION 
        "This counter shall be incremented each time a casual dialed carrier is used instead of the group subscribed PIC, on a per-group basis.."
    ::= { bwPreferredCarrierGroupEntry 10 }

  bwGroupNonSubscriptionDialedServiceProviderPIC OBJECT-TYPE
    SYNTAX      Counter32
    MAX-ACCESS  read-write
    STATUS      current
    DESCRIPTION 
        "This counter shall be incremented each time a casual dialed carrier is used instead of the service provider subscribed PIC, on a per-group basis.."
    ::= { bwPreferredCarrierGroupEntry 11 }

  bwGroupNoIndicationUserPIC OBJECT-TYPE
    SYNTAX      Counter32
    MAX-ACCESS  read-write
    STATUS      current
    DESCRIPTION 
        "This counter shall be incremented each time the user subscribed PIC is used, but with no indication on how this PIC was specified, on a per-group basis.."
    ::= { bwPreferredCarrierGroupEntry 12 }

  bwGroupNoIndicationGroupPIC OBJECT-TYPE
    SYNTAX      Counter32
    MAX-ACCESS  read-write
    STATUS      current
    DESCRIPTION 
        "This counter shall be incremented each time the group subscribed PIC is used, but with no indication on how this PIC was specified, on a per-group basis.."
    ::= { bwPreferredCarrierGroupEntry 13 }

  bwGroupNoIndicationServiceProviderPIC OBJECT-TYPE
    SYNTAX      Counter32
    MAX-ACCESS  read-write
    STATUS      current
    DESCRIPTION 
        "This counter shall be incremented each time the service provider subscribed PIC is used, but with no indication on how this PIC was specified, on a per-group basis.."
    ::= { bwPreferredCarrierGroupEntry 14 }

-- Service : Family SimRing ...........................................

  bwFamilySimRingNumAttempts OBJECT-TYPE
    SYNTAX      Counter32
    MAX-ACCESS  read-write
    STATUS      current
    DESCRIPTION 
        "System wide counter for number of times family sim ring has been executed."
    ::= { familySimRing 1 }

  bwFamilySimRingNumBusy OBJECT-TYPE
    SYNTAX      Counter32
    MAX-ACCESS  read-write
    STATUS      current
    DESCRIPTION 
        "System wide counter for number of times all sim ring numbers have failed."
    ::= { familySimRing 2 }

  bwFamilySimRingSPTable OBJECT-TYPE
    SYNTAX      SEQUENCE OF BwFamilySimRingSPEntry
    MAX-ACCESS  not-accessible
    STATUS      current
    DESCRIPTION 
        "Counters for the Family Simring service measurements for service providers"
    ::= { familySimRing 3 }

  bwFamilySimRingSPEntry OBJECT-TYPE
    SYNTAX      BwFamilySimRingSPEntry
    MAX-ACCESS  not-accessible
    STATUS      current
    DESCRIPTION 
        "Each row contains the service counters for the Family Simring service for each service provider in the system"
    INDEX       { bwFamilySimRingSPIndex }
    ::= { bwFamilySimRingSPTable 1 }

  BwFamilySimRingSPEntry ::= SEQUENCE {
    bwFamilySimRingSPIndex          Unsigned32,
    bwFamilySimRingSPID             DisplayString,
    bwFamilySimRingSPNumAttempts    Counter32,
    bwFamilySimRingSPNumBusy        Counter32
  }

  bwFamilySimRingSPIndex OBJECT-TYPE
    SYNTAX      Unsigned32
    MAX-ACCESS  read-only
    STATUS      current
    DESCRIPTION 
        "This column represents the index of the service provider in the system"
    ::= { bwFamilySimRingSPEntry 1 }

  bwFamilySimRingSPID OBJECT-TYPE
    SYNTAX      DisplayString
    MAX-ACCESS  read-only
    STATUS      current
    DESCRIPTION 
        "This string represents a service provider ID"
    ::= { bwFamilySimRingSPEntry 2 }

  bwFamilySimRingSPNumAttempts OBJECT-TYPE
    SYNTAX      Counter32
    MAX-ACCESS  read-write
    STATUS      current
    DESCRIPTION 
        "System wide counter for number of times family sim ring has been executed for a given service provider."
    ::= { bwFamilySimRingSPEntry 3 }

  bwFamilySimRingSPNumBusy OBJECT-TYPE
    SYNTAX      Counter32
    MAX-ACCESS  read-write
    STATUS      current
    DESCRIPTION 
        "System wide counter for number of times all sim ring numbers have failed for a given service provider."
    ::= { bwFamilySimRingSPEntry 4 }

  bwFamilySimRingGroupTable OBJECT-TYPE
    SYNTAX      SEQUENCE OF BwFamilySimRingGroupEntry
    MAX-ACCESS  not-accessible
    STATUS      current
    DESCRIPTION 
        "Counters for the Family Simring service measurements for groups"
    ::= { familySimRing 4 }

  bwFamilySimRingGroupEntry OBJECT-TYPE
    SYNTAX      BwFamilySimRingGroupEntry
    MAX-ACCESS  not-accessible
    STATUS      current
    DESCRIPTION 
        "Each row contains the service counters for the Family Simring service for each group in the system"
    INDEX       { bwFamilySimRingGroupIndex }
    ::= { bwFamilySimRingGroupTable 1 }

  BwFamilySimRingGroupEntry ::= SEQUENCE {
    bwFamilySimRingGroupIndex           Unsigned32,
    bwFamilySimRingGroupID              DisplayString,
    bwFamilySimRingGroupNumAttempts     Counter32,
    bwFamilySimRingGroupNumBusy         Counter32
  }

  bwFamilySimRingGroupIndex OBJECT-TYPE
    SYNTAX      Unsigned32
    MAX-ACCESS  read-only
    STATUS      current
    DESCRIPTION 
        "This column represents the index of the group in the system"
    ::= { bwFamilySimRingGroupEntry 1 }

  bwFamilySimRingGroupID OBJECT-TYPE
    SYNTAX      DisplayString
    MAX-ACCESS  read-only
    STATUS      current
    DESCRIPTION 
        "This string represents a group ID"
    ::= { bwFamilySimRingGroupEntry 2 }

  bwFamilySimRingGroupNumAttempts OBJECT-TYPE
    SYNTAX      Counter32
    MAX-ACCESS  read-write
    STATUS      current
    DESCRIPTION 
        "System wide counter for number of times family sim ring has been executed for a given group."
    ::= { bwFamilySimRingGroupEntry 3 }

  bwFamilySimRingGroupNumBusy OBJECT-TYPE
    SYNTAX      Counter32
    MAX-ACCESS  read-write
    STATUS      current
    DESCRIPTION 
        "System wide counter for number of times all sim ring numbers have failed for a given group."
    ::= { bwFamilySimRingGroupEntry 4 }

-- Service : Diversion Inhibitor ...........................................

  bwDiversionInhibited OBJECT-TYPE
    SYNTAX      Counter32
    MAX-ACCESS  read-write
    STATUS      current
    DESCRIPTION 
        "This counter is incremented each time Diversion Inhibitor FAC is invoked for a call, directly or via service configuration."
    ::= { diversionInhibitor 1 }

  bwDiversionInhibitorSPTable OBJECT-TYPE
    SYNTAX      SEQUENCE OF BwDiversionInhibitorSPEntry
    MAX-ACCESS  not-accessible
    STATUS      current
    DESCRIPTION 
        "Counters for the Diversion Inhibitor service measurements for service providers"
    ::= { diversionInhibitor 2 }

  bwDiversionInhibitorSPEntry OBJECT-TYPE
    SYNTAX      BwDiversionInhibitorSPEntry
    MAX-ACCESS  not-accessible
    STATUS      current
    DESCRIPTION 
        "Each row contains the service counters for the Diversion Inhibitor service for each service provider in the system"
    INDEX       { bwDiversionInhibitorSPIndex }
    ::= { bwDiversionInhibitorSPTable 1 }

  BwDiversionInhibitorSPEntry ::= SEQUENCE {
    bwDiversionInhibitorSPIndex     Unsigned32,
    bwDiversionInhibitorSPID        DisplayString,
    bwSPDiversionInhibited          Counter32
  }

  bwDiversionInhibitorSPIndex OBJECT-TYPE
    SYNTAX      Unsigned32
    MAX-ACCESS  read-only
    STATUS      current
    DESCRIPTION 
        "This column represents the index of the service provider in the system"
    ::= { bwDiversionInhibitorSPEntry 1 }

  bwDiversionInhibitorSPID OBJECT-TYPE
    SYNTAX      DisplayString
    MAX-ACCESS  read-only
    STATUS      current
    DESCRIPTION 
        "This string represents a service provider ID"
    ::= { bwDiversionInhibitorSPEntry 2 }

  bwSPDiversionInhibited OBJECT-TYPE
    SYNTAX      Counter32
    MAX-ACCESS  read-write
    STATUS      current
    DESCRIPTION 
        "This counter is incremented each time Diversion Inhibitor FAC is invoked for a call, directly or via service configuration for a service provider."
    ::= { bwDiversionInhibitorSPEntry 3 }

  bwDiversionInhibitorGroupTable OBJECT-TYPE
    SYNTAX      SEQUENCE OF BwDiversionInhibitorGroupEntry
    MAX-ACCESS  not-accessible
    STATUS      current
    DESCRIPTION 
        "Counters for the Diversion Inhibitor service measurements for groups"
    ::= { diversionInhibitor 3 }

  bwDiversionInhibitorGroupEntry OBJECT-TYPE
    SYNTAX      BwDiversionInhibitorGroupEntry
    MAX-ACCESS  not-accessible
    STATUS      current
    DESCRIPTION 
        "Each row contains the service counters for the Diversion Inhibitor service for each group in the system"
    INDEX       { bwDiversionInhibitorGroupIndex }
    ::= { bwDiversionInhibitorGroupTable 1 }

  BwDiversionInhibitorGroupEntry ::= SEQUENCE {
    bwDiversionInhibitorGroupIndex  Unsigned32,
    bwDiversionInhibitorGroupID     DisplayString,
    bwGroupDiversionInhibited       Counter32
  }

  bwDiversionInhibitorGroupIndex OBJECT-TYPE
    SYNTAX      Unsigned32
    MAX-ACCESS  read-only
    STATUS      current
    DESCRIPTION 
        "This column represents the index of the group in the system"
    ::= { bwDiversionInhibitorGroupEntry 1 }

  bwDiversionInhibitorGroupID OBJECT-TYPE
    SYNTAX      DisplayString
    MAX-ACCESS  read-only
    STATUS      current
    DESCRIPTION 
        "This string represents a group ID"
    ::= { bwDiversionInhibitorGroupEntry 2 }

  bwGroupDiversionInhibited OBJECT-TYPE
    SYNTAX      Counter32
    MAX-ACCESS  read-write
    STATUS      current
    DESCRIPTION 
        "This counter is incremented each time Diversion Inhibitor FAC is invoked for a call, directly or via service configuration for a group."
    ::= { bwDiversionInhibitorGroupEntry 3 }

-- Service : Instant Group Call ...........................................

  bwIGCPushToTalkInvoke OBJECT-TYPE
    SYNTAX      Counter32
    MAX-ACCESS  read-write
    STATUS      current
    DESCRIPTION 
        "This counter is incremented each time a Instant Group Call virtual user is called and the Push-To-Talk feature access code was dialed."
    ::= { instantGroupCall 1 }

  bwIGCNormalInvoke OBJECT-TYPE
    SYNTAX      Counter32
    MAX-ACCESS  read-write
    STATUS      current
    DESCRIPTION 
        "This counter is incremented each time a Instant Group Call virtual user is called and the Push-To-Talk feature access code was not dialed."
    ::= { instantGroupCall 2 }

  bwIGCSPTable OBJECT-TYPE
    SYNTAX      SEQUENCE OF BwIGCSPEntry
    MAX-ACCESS  not-accessible
    STATUS      current
    DESCRIPTION 
        "Counters for the Instant Group Call service measurements for service providers"
    ::= { instantGroupCall 3 }

  bwIGCSPEntry OBJECT-TYPE
    SYNTAX      BwIGCSPEntry
    MAX-ACCESS  not-accessible
    STATUS      current
    DESCRIPTION 
        "Each row contains the service counters for the Instant Group Call service for each service provider in the system"
    INDEX       { bwIGCSPIndex }
    ::= { bwIGCSPTable 1 }

  BwIGCSPEntry ::= SEQUENCE {
    bwIGCSPIndex                Unsigned32,
    bwIGCSPID                   DisplayString,
    bwIGCSPPushToTalkInvoke     Counter32,
    bwIGCSPNormalInvoke         Counter32
  }

  bwIGCSPIndex OBJECT-TYPE
    SYNTAX      Unsigned32
    MAX-ACCESS  read-only
    STATUS      current
    DESCRIPTION 
        "This column represents the index of the service provider in the system"
    ::= { bwIGCSPEntry 1 }

  bwIGCSPID OBJECT-TYPE
    SYNTAX      DisplayString
    MAX-ACCESS  read-only
    STATUS      current
    DESCRIPTION 
        "This string represents a service provider ID"
    ::= { bwIGCSPEntry 2 }

  bwIGCSPPushToTalkInvoke OBJECT-TYPE
    SYNTAX      Counter32
    MAX-ACCESS  read-write
    STATUS      current
    DESCRIPTION 
        "This counter is incremented, per service provider ID, each time a Instant Group Call virtual user is called and the Push-To-Talk feature access code was dialed."
    ::= { bwIGCSPEntry 3 }

  bwIGCSPNormalInvoke OBJECT-TYPE
    SYNTAX      Counter32
    MAX-ACCESS  read-write
    STATUS      current
    DESCRIPTION 
        "This counter is incremented, per service provider ID, each time a Instant Group Call virtual user is called and the Push-To-Talk feature access code was not dialed."
    ::= { bwIGCSPEntry 4 }

  bwIGCGroupTable OBJECT-TYPE
    SYNTAX      SEQUENCE OF BwIGCGroupEntry
    MAX-ACCESS  not-accessible
    STATUS      current
    DESCRIPTION 
        "Counters for the Instant Group Call service measurements for groups"
    ::= { instantGroupCall 4 }

  bwIGCGroupEntry OBJECT-TYPE
    SYNTAX      BwIGCGroupEntry
    MAX-ACCESS  not-accessible
    STATUS      current
    DESCRIPTION 
        "Each row contains the service counters for the Instant Group Call service for each group in the system"
    INDEX       { bwIGCGroupIndex }
    ::= { bwIGCGroupTable 1 }

  BwIGCGroupEntry ::= SEQUENCE {
    bwIGCGroupIndex             Unsigned32,
    bwIGCGroupID                DisplayString,
    bwIGCGroupPushToTalkInvoke  Counter32,
    bwIGCGroupNormalInvoke      Counter32
  }

  bwIGCGroupIndex OBJECT-TYPE
    SYNTAX      Unsigned32
    MAX-ACCESS  read-only
    STATUS      current
    DESCRIPTION 
        "This column represents the index of the group in the system"
    ::= { bwIGCGroupEntry 1 }

  bwIGCGroupID OBJECT-TYPE
    SYNTAX      DisplayString
    MAX-ACCESS  read-only
    STATUS      current
    DESCRIPTION 
        "This string represents a group ID"
    ::= { bwIGCGroupEntry 2 }

  bwIGCGroupPushToTalkInvoke OBJECT-TYPE
    SYNTAX      Counter32
    MAX-ACCESS  read-write
    STATUS      current
    DESCRIPTION 
        "This counter is incremented, per group ID, each time a Instant Group Call virtual user is called and the Push-To-Talk feature access code was dialed."
    ::= { bwIGCGroupEntry 3 }

  bwIGCGroupNormalInvoke OBJECT-TYPE
    SYNTAX      Counter32
    MAX-ACCESS  read-write
    STATUS      current
    DESCRIPTION 
        "This counter is incremented, per group ID, each time a Instant Group Call virtual user is called and the Push-To-Talk feature access code was not dialed."
    ::= { bwIGCGroupEntry 4 }

-- Service : Automatic Hold Retrieve ...........................................

  bwAHRHold OBJECT-TYPE
    SYNTAX      Counter32
    MAX-ACCESS  read-write
    STATUS      current
    DESCRIPTION 
        "Number of times a call is put on hold via the AHR service."
    ::= { automaticHoldRetrieve 1 }

  bwAHRRetrieve OBJECT-TYPE
    SYNTAX      Counter32
    MAX-ACCESS  read-write
    STATUS      current
    DESCRIPTION 
        "Number of times a call is retrieved via the AHR service."
    ::= { automaticHoldRetrieve 2 }

  bwAHRSPTable OBJECT-TYPE
    SYNTAX      SEQUENCE OF BwAHRSPEntry
    MAX-ACCESS  not-accessible
    STATUS      current
    DESCRIPTION 
        "Counters for the Automatic Hold Retrieve service measurements for service providers."
    ::= { automaticHoldRetrieve 3 }

  bwAHRSPEntry OBJECT-TYPE
    SYNTAX      BwAHRSPEntry
    MAX-ACCESS  not-accessible
    STATUS      current
    DESCRIPTION 
        "Each row contains the service counters for the Automatic Hold Retrieve service for each service provider in the system"
    INDEX       { bwAHRSPIndex }
    ::= { bwAHRSPTable 1 }

  BwAHRSPEntry ::= SEQUENCE {
    bwAHRSPIndex        Unsigned32,
    bwAHRSPID           DisplayString,
    bwAHRSPHold         Counter32,
    bwAHRSPRetrieve     Counter32
  }

  bwAHRSPIndex OBJECT-TYPE
    SYNTAX      Unsigned32
    MAX-ACCESS  read-only
    STATUS      current
    DESCRIPTION 
        "This column represents the index of the service provider in the system."
    ::= { bwAHRSPEntry 1 }

  bwAHRSPID OBJECT-TYPE
    SYNTAX      DisplayString
    MAX-ACCESS  read-only
    STATUS      current
    DESCRIPTION 
        "This string represents a service provider ID."
    ::= { bwAHRSPEntry 2 }

  bwAHRSPHold OBJECT-TYPE
    SYNTAX      Counter32
    MAX-ACCESS  read-write
    STATUS      current
    DESCRIPTION 
        "Number of calls within a service provider that are put on hold via the AHR service."
    ::= { bwAHRSPEntry 3 }

  bwAHRSPRetrieve OBJECT-TYPE
    SYNTAX      Counter32
    MAX-ACCESS  read-write
    STATUS      current
    DESCRIPTION 
        "Number of calls within a service provider that are retrieved via the AHR service."
    ::= { bwAHRSPEntry 4 }

  bwAHRGroupTable OBJECT-TYPE
    SYNTAX      SEQUENCE OF BwAHRGroupEntry
    MAX-ACCESS  not-accessible
    STATUS      current
    DESCRIPTION 
        "Counters for the Automatic Hold Retrieve service measurements for groups."
    ::= { automaticHoldRetrieve 4 }

  bwAHRGroupEntry OBJECT-TYPE
    SYNTAX      BwAHRGroupEntry
    MAX-ACCESS  not-accessible
    STATUS      current
    DESCRIPTION 
        "Each row contains the service counters for the Automatic Hold Retrieve service for each group in the system"
    INDEX       { bwAHRGroupIndex }
    ::= { bwAHRGroupTable 1 }

  BwAHRGroupEntry ::= SEQUENCE {
    bwAHRGroupIndex     Unsigned32,
    bwAHRGroupID        DisplayString,
    bwAHRGroupHold      Counter32,
    bwAHRGroupRetrieve  Counter32
  }

  bwAHRGroupIndex OBJECT-TYPE
    SYNTAX      Unsigned32
    MAX-ACCESS  read-only
    STATUS      current
    DESCRIPTION 
        "This column represents the index of the group in the system."
    ::= { bwAHRGroupEntry 1 }

  bwAHRGroupID OBJECT-TYPE
    SYNTAX      DisplayString
    MAX-ACCESS  read-only
    STATUS      current
    DESCRIPTION 
        "This string represents a group ID."
    ::= { bwAHRGroupEntry 2 }

  bwAHRGroupHold OBJECT-TYPE
    SYNTAX      Counter32
    MAX-ACCESS  read-write
    STATUS      current
    DESCRIPTION 
        "Number of calls within a group that are put on hold via the AHR service."
    ::= { bwAHRGroupEntry 3 }

  bwAHRGroupRetrieve OBJECT-TYPE
    SYNTAX      Counter32
    MAX-ACCESS  read-write
    STATUS      current
    DESCRIPTION 
        "Number of calls within a group that are retrieved via the AHR service."
    ::= { bwAHRGroupEntry 4 }

-- Service : Trunk Group ...........................................

  bwTrunkOriginationAttempt OBJECT-TYPE
    SYNTAX      Counter32
    MAX-ACCESS  read-write
    STATUS      current
    DESCRIPTION 
        "This counter is incremented when a call is originated by a trunk user, whether it goes through or not."
    ::= { trunkGroup 1 }

  bwTrunkOriginationBlocked OBJECT-TYPE
    SYNTAX      Counter32
    MAX-ACCESS  read-write
    STATUS      current
    DESCRIPTION 
        "This counter is incremented when a call originated by a trunk user is blocked because the trunk call capacity is reached."
    ::= { trunkGroup 2 }

  bwTrunkTerminationAttempt OBJECT-TYPE
    SYNTAX      Counter32
    MAX-ACCESS  read-write
    STATUS      current
    DESCRIPTION 
        "This counter is incremented when a call from an outside party attempts to terminate on a trunk user, whether it goes through or not."
    ::= { trunkGroup 3 }

  bwTrunkTerminationBlocked OBJECT-TYPE
    SYNTAX      Counter32
    MAX-ACCESS  read-write
    STATUS      current
    DESCRIPTION 
        "This counter is incremented when a call destined to a trunk user is blocked because the trunk call capacity is reached."
    ::= { trunkGroup 4 }

  bwTrunkSPTable OBJECT-TYPE
    SYNTAX      SEQUENCE OF BwTrunkSPEntry
    MAX-ACCESS  not-accessible
    STATUS      current
    DESCRIPTION 
        "Counters for the Business Trunk Group service measurements for service providers."
    ::= { trunkGroup 5 }

  bwTrunkSPEntry OBJECT-TYPE
    SYNTAX      BwTrunkSPEntry
    MAX-ACCESS  not-accessible
    STATUS      current
    DESCRIPTION 
        "Each row contains the service counters for the Business Trunk Group service for each service provider in the system"
    INDEX       { bwTrunkSPIndex }
    ::= { bwTrunkSPTable 1 }

  BwTrunkSPEntry ::= SEQUENCE {
    bwTrunkSPIndex                    Unsigned32,
    bwTrunkSPID                       DisplayString,
    bwTrunkSPOriginationAttempt       Counter32,
    bwTrunkSPOriginationBlocked       Counter32,
    bwTrunkSPTerminationAttempt       Counter32,
    bwTrunkSPTerminationBlocked       Counter32,
    bwTrunkSPOodPbxRedirectionAttempt Counter32,
    bwTrunkSPOodPbxRedirectionBlocked Counter32
  }

  bwTrunkSPIndex OBJECT-TYPE
    SYNTAX      Unsigned32
    MAX-ACCESS  read-only
    STATUS      current
    DESCRIPTION 
        "This column represents the index of the service provider in the system."
    ::= { bwTrunkSPEntry 1 }

  bwTrunkSPID OBJECT-TYPE
    SYNTAX      DisplayString
    MAX-ACCESS  read-only
    STATUS      current
    DESCRIPTION 
        "This string represents a service provider ID."
    ::= { bwTrunkSPEntry 2 }

  bwTrunkSPOriginationAttempt OBJECT-TYPE
    SYNTAX      Counter32
    MAX-ACCESS  read-write
    STATUS      current
    DESCRIPTION 
        "This counter is incremented when a call is originated by a trunk user in the service provider, whether it goes through or not."
    ::= { bwTrunkSPEntry 3 }

  bwTrunkSPOriginationBlocked OBJECT-TYPE
    SYNTAX      Counter32
    MAX-ACCESS  read-write
    STATUS      current
    DESCRIPTION 
        "This counter is incremented when a call originated by a trunk user within the service provider is blocked because the trunk call capacity is reached."
    ::= { bwTrunkSPEntry 4 }

  bwTrunkSPTerminationAttempt OBJECT-TYPE
    SYNTAX      Counter32
    MAX-ACCESS  read-write
    STATUS      current
    DESCRIPTION 
        "This counter is incremented when a call from an outside party attempts to terminate on a trunk user within the service provider, whether it goes through or not."
    ::= { bwTrunkSPEntry 5 }

  bwTrunkSPTerminationBlocked OBJECT-TYPE
    SYNTAX      Counter32
    MAX-ACCESS  read-write
    STATUS      current
    DESCRIPTION 
        "This counter is incremented when a call destined to a trunk user within the service provider is blocked because the trunk call capacity is reached."
    ::= { bwTrunkSPEntry 6 }

  bwTrunkSPOodPbxRedirectionAttempt OBJECT-TYPE
    SYNTAX      Counter32
    MAX-ACCESS  read-write
    STATUS      current
    DESCRIPTION 
        "This count reflects the total number of  trunking Out-Of-Dialog (OOD) Private Branch Exchange (PBX) redirections that have been attempted for a service provider or enterprise."
-- @feature:208093
    ::= { bwTrunkSPEntry 7 }

  bwTrunkSPOodPbxRedirectionBlocked OBJECT-TYPE
    SYNTAX      Counter32
    MAX-ACCESS  read-write
    STATUS      current
    DESCRIPTION 
        "This count reflects the total number of trunking Out-Of-Dialog (OOD) Private Branch Exchange (PBX) redirections that are blocked because the trunk group call capacity has been reached for a service provider or enterprise."
-- @feature:208093
    ::= { bwTrunkSPEntry 8 }

  bwTrunkGroupTable OBJECT-TYPE
    SYNTAX      SEQUENCE OF BwTrunkGroupEntry
    MAX-ACCESS  not-accessible
    STATUS      current
    DESCRIPTION 
        "Counters for the Business Trunk Group service measurements for groups."
    ::= { trunkGroup 6 }

  bwTrunkGroupEntry OBJECT-TYPE
    SYNTAX      BwTrunkGroupEntry
    MAX-ACCESS  not-accessible
    STATUS      current
    DESCRIPTION 
        "Each row contains the service counters for the Business Trunk Group service for each group in the system"
    INDEX       { bwTrunkGroupIndex }
    ::= { bwTrunkGroupTable 1 }

  BwTrunkGroupEntry ::= SEQUENCE {
    bwTrunkGroupIndex                    Unsigned32,
    bwTrunkGroupID                       DisplayString,
    bwTrunkGroupOriginationAttempt       Counter32,
    bwTrunkGroupOriginationBlocked       Counter32,
    bwTrunkGroupTerminationAttempt       Counter32,
    bwTrunkGroupTerminationBlocked       Counter32,
    bwTrunkGroupOodPbxRedirectionAttempt Counter32,
    bwTrunkGroupOodPbxRedirectionBlocked Counter32
  }

  bwTrunkGroupIndex OBJECT-TYPE
    SYNTAX      Unsigned32
    MAX-ACCESS  read-only
    STATUS      current
    DESCRIPTION 
        "This column represents the index of the group in the system."
    ::= { bwTrunkGroupEntry 1 }

  bwTrunkGroupID OBJECT-TYPE
    SYNTAX      DisplayString
    MAX-ACCESS  read-only
    STATUS      current
    DESCRIPTION 
        "This string represents a group ID."
    ::= { bwTrunkGroupEntry 2 }

  bwTrunkGroupOriginationAttempt OBJECT-TYPE
    SYNTAX      Counter32
    MAX-ACCESS  read-write
    STATUS      current
    DESCRIPTION 
        "This counter is incremented when a call is originated by a trunk user in the group, whether it goes through or not."
    ::= { bwTrunkGroupEntry 3 }

  bwTrunkGroupOriginationBlocked OBJECT-TYPE
    SYNTAX      Counter32
    MAX-ACCESS  read-write
    STATUS      current
    DESCRIPTION 
        "This counter is incremented when a call originated by a trunk user within the group is blocked because the trunk call capacity is reached."
    ::= { bwTrunkGroupEntry 4 }

  bwTrunkGroupTerminationAttempt OBJECT-TYPE
    SYNTAX      Counter32
    MAX-ACCESS  read-write
    STATUS      current
    DESCRIPTION 
        "This counter is incremented when a call from an outside party attempts to terminate on a trunk user within the group, whether it goes through or not."
    ::= { bwTrunkGroupEntry 5 }

  bwTrunkGroupTerminationBlocked OBJECT-TYPE
    SYNTAX      Counter32
    MAX-ACCESS  read-write
    STATUS      current
    DESCRIPTION 
        "This counter is incremented when a call destined to a trunk user within the group is blocked because the trunk call capacity is reached."
    ::= { bwTrunkGroupEntry 6 }

  bwTrunkGroupOodPbxRedirectionAttempt OBJECT-TYPE
    SYNTAX      Counter32
    MAX-ACCESS  read-write
    STATUS      current
    DESCRIPTION 
        "This count reflects the total number of  trunking Out-Of-Dialog (OOD) Private Branch Exchange (PBX) redirections that have been attempted for a group."
-- @feature:208093
    ::= { bwTrunkGroupEntry 7 }

  bwTrunkGroupOodPbxRedirectionBlocked OBJECT-TYPE
    SYNTAX      Counter32
    MAX-ACCESS  read-write
    STATUS      current
    DESCRIPTION 
        "This count reflects the total number of trunking Out-Of-Dialog (OOD) Private Branch Exchange (PBX) redirections that are blocked because the trunk group call capacity has been reached for a group."
-- @feature:208093
    ::= { bwTrunkGroupEntry 8 }

  bwTrunkGroupPerTGTable OBJECT-TYPE
    SYNTAX      SEQUENCE OF BwTrunkGroupPerTGEntry
    MAX-ACCESS  not-accessible
    STATUS      current
    DESCRIPTION 
        "Counters for the Business Trunk Group service measurements on a per trunk group basis."
    ::= { trunkGroup 7 }

  bwTrunkGroupPerTGEntry OBJECT-TYPE
    SYNTAX      BwTrunkGroupPerTGEntry
    MAX-ACCESS  not-accessible
    STATUS      current
    DESCRIPTION 
        "Each row contains the service counters for the Business Trunk Group service for each service provider in the system"
    INDEX       { bwTrunkGroupPerTGIndex }
    ::= { bwTrunkGroupPerTGTable 1 }

  BwTrunkGroupPerTGEntry ::= SEQUENCE {
    bwTrunkGroupPerTGIndex                                          Unsigned32,
    bwTrunkGroupPerTGName                                           DisplayString,
    bwTrunkGroupPerTGCapacityExceeded                               Counter32,
    bwTrunkGroupPerTGUnreachableDestination                         Counter32,
    bwTrunkGroupPerTGMaxActiveCalls                                 Gauge32,
    bwTrunkGroupPerTGMaxOutgoingActiveCalls                         Gauge32,
    bwTrunkGroupPerTGMaxIncomingActiveCalls                         Gauge32,
    bwTrunkGroupPerTGCapacityExceededInitialValue                   Gauge32,
    bwTrunkGroupPerTGCapacityExceededOffsetValue                    Gauge32,
    bwTrunkGroupPerTGBursting                                       DisplayString,
    bwTrunkGroupPerTGBurstingMaxActiveCalls                         Gauge32,
    bwTrunkGroupPerTGBurstingMaxOutgoingActiveCalls                 Gauge32,
    bwTrunkGroupPerTGBurstingMaxIncomingActiveCalls                 Gauge32,
    bwTrunkGroupPerTGGroupID                                        DisplayString,
    bwTrunkGroupPerTGTotalActiveCalls                               Gauge32,
    bwTrunkGroupPerTGOutgoingActiveCalls                            Gauge32,
    bwTrunkGroupPerTGIncomingActiveCalls                            Gauge32,
    bwTrunkGroupPerTGTotalCallHighWaterMark                         Gauge32,
    bwTrunkGroupPerTGOutgoingCallHighWaterMark                      Gauge32,
    bwTrunkGroupPerTGIncomingCallHighWaterMark                      Gauge32,
    bwTrunkGroupPerTGCallHighWaterMarkReset                         Counter32,
    bwTrunkGroupPerTGHoldingTotalCallHighWaterMark                  Gauge32,
    bwTrunkGroupPerTGHoldingOutgoingCallHighWaterMark               Gauge32,
    bwTrunkGroupPerTGHoldingIncomingCallHighWaterMark               Gauge32,
    bwTrunkGroupPerTGOriginationAttempt                             Counter32,
    bwTrunkGroupPerTGOriginationBlocked                             Counter32,
    bwTrunkGroupPerTGTerminationAttempt                             Counter32,
    bwTrunkGroupPerTGTerminationBlocked                             Counter32,
    bwTrunkGroupPerTGTerminationFailure                             Counter32,
    bwTrunkGroupPerTGOodPbxRedirectionAttempt                       Counter32,
    bwTrunkGroupPerTGOodPbxRedirectionBlocked                       Counter32
  }

  bwTrunkGroupPerTGIndex OBJECT-TYPE
    SYNTAX      Unsigned32
    MAX-ACCESS  read-only
    STATUS      current
    DESCRIPTION 
        "This column represents the index of the trunk group in the system."
    ::= { bwTrunkGroupPerTGEntry 1 }

  bwTrunkGroupPerTGName OBJECT-TYPE
    SYNTAX      DisplayString
    MAX-ACCESS  read-only
    STATUS      current
    DESCRIPTION 
        "This string represents the name of a trunk group."
    ::= { bwTrunkGroupPerTGEntry 2 }

  bwTrunkGroupPerTGCapacityExceeded OBJECT-TYPE
    SYNTAX      Counter32
    MAX-ACCESS  read-write
    STATUS      current
    DESCRIPTION 
        "The counter is incremented each time a trunk group call capacity is exceeded."
    ::= { bwTrunkGroupPerTGEntry 3 }

  bwTrunkGroupPerTGUnreachableDestination OBJECT-TYPE
    SYNTAX      Counter32
    MAX-ACCESS  read-write
    STATUS      current
    DESCRIPTION 
        "The counter is incremented each time a trunk group is deemed unreachable."
    ::= { bwTrunkGroupPerTGEntry 4 }

  bwTrunkGroupPerTGMaxActiveCalls OBJECT-TYPE
    SYNTAX      Gauge32
    MAX-ACCESS  read-only
    STATUS      current
    DESCRIPTION 
        "Indicates the value of the Maximum Active Calls Allowed parameter for a trunk group."
    ::= { bwTrunkGroupPerTGEntry 5 }

  bwTrunkGroupPerTGMaxOutgoingActiveCalls OBJECT-TYPE
    SYNTAX      Gauge32
    MAX-ACCESS  read-only
    STATUS      current
    DESCRIPTION 
        "Indicates the value of the Maximum Outgoing Active Calls Allowed parameter a the trunk group."
    ::= { bwTrunkGroupPerTGEntry 6 }

  bwTrunkGroupPerTGMaxIncomingActiveCalls OBJECT-TYPE
    SYNTAX      Gauge32
    MAX-ACCESS  read-only
    STATUS      current
    DESCRIPTION 
        "Indicates the value of the Maximum Incoming Active Calls Allowed parameter a the trunk group."
    ::= { bwTrunkGroupPerTGEntry 7 }

  bwTrunkGroupPerTGCapacityExceededInitialValue OBJECT-TYPE
    SYNTAX      Gauge32
    MAX-ACCESS  read-only
    STATUS      current
    DESCRIPTION 
        "Indicates the value of the Capacity Exceeded Initial Value parameter for a trunk group."
    ::= { bwTrunkGroupPerTGEntry 8 }

  bwTrunkGroupPerTGCapacityExceededOffsetValue OBJECT-TYPE
    SYNTAX      Gauge32
    MAX-ACCESS  read-only
    STATUS      current
    DESCRIPTION 
        "Indicates the value of the Capacity Exceeded Offset Value parameter for a trunk group."
    ::= { bwTrunkGroupPerTGEntry 9 }

  bwTrunkGroupPerTGBursting OBJECT-TYPE
    SYNTAX      DisplayString
    MAX-ACCESS  read-only
    STATUS      current
    DESCRIPTION 
        "Indicates the value bursting parameter for the trunk group."
    ::= { bwTrunkGroupPerTGEntry 12 }

  bwTrunkGroupPerTGBurstingMaxActiveCalls OBJECT-TYPE
    SYNTAX      Gauge32
    MAX-ACCESS  read-only
    STATUS      current
    DESCRIPTION 
        "Indicates the value of the Bursting Maximum Active Calls Allowed parameter for the trunk group."
    ::= { bwTrunkGroupPerTGEntry 13 }

  bwTrunkGroupPerTGBurstingMaxOutgoingActiveCalls OBJECT-TYPE
    SYNTAX      Gauge32
    MAX-ACCESS  read-only
    STATUS      current
    DESCRIPTION 
        "Indicates the value of the Bursting Maximum Outgoing Active Calls Allowed parameter for the trunk group."
    ::= { bwTrunkGroupPerTGEntry 14 }

  bwTrunkGroupPerTGBurstingMaxIncomingActiveCalls OBJECT-TYPE
    SYNTAX      Gauge32
    MAX-ACCESS  read-only
    STATUS      current
    DESCRIPTION 
        "Indicates the value of the Bursting Maximum Incoming Active Calls Allowed parameter for the trunk group."
    ::= { bwTrunkGroupPerTGEntry 15 }

  bwTrunkGroupPerTGGroupID OBJECT-TYPE
    SYNTAX      DisplayString
    MAX-ACCESS  read-only
    STATUS      current
    DESCRIPTION 
        "This string represents a group ID."
    ::= { bwTrunkGroupPerTGEntry 16 }

   bwTrunkGroupPerTGTotalActiveCalls OBJECT-TYPE
    SYNTAX      Gauge32
    MAX-ACCESS  read-only
    STATUS      current
    DESCRIPTION 
        "Number of active trunking calls for a given trunk group."
-- @feature:166299
    ::= { bwTrunkGroupPerTGEntry 17 }

  bwTrunkGroupPerTGOutgoingActiveCalls OBJECT-TYPE
    SYNTAX      Gauge32
    MAX-ACCESS  read-only
    STATUS      current
    DESCRIPTION 
        "Number of outgoing active trunking calls for a given trunk group."
-- @feature:166299
    ::= { bwTrunkGroupPerTGEntry 18 }

  bwTrunkGroupPerTGIncomingActiveCalls OBJECT-TYPE
    SYNTAX      Gauge32
    MAX-ACCESS  read-only
    STATUS      current
    DESCRIPTION 
        "Number of incoming active trunking calls for a given trunk group."
-- @feature:166299
    ::= { bwTrunkGroupPerTGEntry 19 }

  bwTrunkGroupPerTGTotalCallHighWaterMark OBJECT-TYPE
    SYNTAX      Gauge32
    MAX-ACCESS  read-only
    STATUS      current
    DESCRIPTION 
        "The current high-water mark value of trunking calls for a given trunk group."
-- @feature:166299
    ::= { bwTrunkGroupPerTGEntry 20 }

  bwTrunkGroupPerTGOutgoingCallHighWaterMark OBJECT-TYPE
    SYNTAX      Gauge32
    MAX-ACCESS  read-only
    STATUS      current
    DESCRIPTION 
        "The current high-water mark value of outgoing trunking calls for a given trunk group."
-- @feature:166299
    ::= { bwTrunkGroupPerTGEntry 21 }

  bwTrunkGroupPerTGIncomingCallHighWaterMark OBJECT-TYPE
    SYNTAX      Gauge32
    MAX-ACCESS  read-only
    STATUS      current
    DESCRIPTION 
        "The current high-water mark value of incoming trunking calls for a given trunk group."
-- @feature:166299
    ::= { bwTrunkGroupPerTGEntry 22 }

  bwTrunkGroupPerTGCallHighWaterMarkReset OBJECT-TYPE
    SYNTAX      Counter32
    MAX-ACCESS  read-write
    STATUS      current
    DESCRIPTION 
        "When set to a value other than '0', the high-water marks are set to the current values of the corresponding trunking call counts."
-- @feature:166299
    ::= { bwTrunkGroupPerTGEntry 23 }

  bwTrunkGroupPerTGHoldingTotalCallHighWaterMark OBJECT-TYPE
    SYNTAX      Gauge32
    MAX-ACCESS  read-only
    STATUS      current
    DESCRIPTION 
        "The holdover high-water mark value of trunking calls for a given trunk group."
-- @feature:166299
    ::= { bwTrunkGroupPerTGEntry 24 }

  bwTrunkGroupPerTGHoldingOutgoingCallHighWaterMark OBJECT-TYPE
    SYNTAX      Gauge32
    MAX-ACCESS  read-only
    STATUS      current
    DESCRIPTION 
        "The holdover high-water mark value of outgoing trunking calls for a given trunk group."
-- @feature:166299
    ::= { bwTrunkGroupPerTGEntry 25 }

  bwTrunkGroupPerTGHoldingIncomingCallHighWaterMark OBJECT-TYPE
    SYNTAX      Gauge32
    MAX-ACCESS  read-only
    STATUS      current
    DESCRIPTION 
        "The holdover high-water mark value of incoming trunking calls for a given trunk group."
-- @feature:166299
    ::= { bwTrunkGroupPerTGEntry 26 }

  bwTrunkGroupPerTGOriginationAttempt OBJECT-TYPE
    SYNTAX      Counter32
    MAX-ACCESS  read-write
    STATUS      current
    DESCRIPTION 
        "The number of times a trunking origination associated with a trunk group is attempted."
-- @feature:166299
    ::= { bwTrunkGroupPerTGEntry 27 }

  bwTrunkGroupPerTGOriginationBlocked OBJECT-TYPE
    SYNTAX      Counter32
    MAX-ACCESS  read-write
    STATUS      current
    DESCRIPTION 
        "The number of times a trunking origination associated with a trunk group is blocked because the trunk capacity is reached."
-- @feature:166299
    ::= { bwTrunkGroupPerTGEntry 28 }

  bwTrunkGroupPerTGTerminationAttempt OBJECT-TYPE
    SYNTAX      Counter32
    MAX-ACCESS  read-write
    STATUS      current
    DESCRIPTION 
        "The number of times a trunking termination associated with a trunk group is attempted."
-- @feature:166299
    ::= { bwTrunkGroupPerTGEntry 29 }

  bwTrunkGroupPerTGTerminationBlocked OBJECT-TYPE
    SYNTAX      Counter32
    MAX-ACCESS  read-write
    STATUS      current
    DESCRIPTION 
        "The number of times a trunking termination associated with a trunk group is blocked because the trunk capacity is reached."
-- @feature:166299
    ::= { bwTrunkGroupPerTGEntry 30 }

  bwTrunkGroupPerTGTerminationFailure OBJECT-TYPE
    SYNTAX      Counter32
    MAX-ACCESS  read-write
    STATUS      current
    DESCRIPTION 
        "The number of times a trunking termination associated with a trunk group is failed."
-- @feature:166299
    ::= { bwTrunkGroupPerTGEntry 31 }

  bwTrunkGroupPerTGOodPbxRedirectionAttempt OBJECT-TYPE
    SYNTAX      Counter32
    MAX-ACCESS  read-write
    STATUS      current
    DESCRIPTION 
        "This count reflects the total number of attempts of Out-Of-Dialog (OOD) Private Branch Exchange (PBX) redirections that have been attempted for a trunk group."
-- @feature:208093
    ::= { bwTrunkGroupPerTGEntry 32 }

  bwTrunkGroupPerTGOodPbxRedirectionBlocked OBJECT-TYPE
    SYNTAX      Counter32
    MAX-ACCESS  read-write
    STATUS      current
    DESCRIPTION 
        "This count reflects the total number of trunking Out-Of-Dialog (OOD) Private Branch Exchange (PBX) redirections that are blocked because the trunk group call capacity has been reached for a trunk group."
-- @feature:208093
    ::= { bwTrunkGroupPerTGEntry 33 }

  bwTrunkGroupCallHighWaterMarkReset OBJECT-TYPE
    SYNTAX      Counter32
    MAX-ACCESS  read-write
    STATUS      current
    DESCRIPTION 
        "When set to a value other than '0', the high-water marks of all trunk groups are set to the current values of the corresponding trunking call counts."
-- @feature:166299
    ::= { trunkGroup 8 }

  bwTrunkOodPbxRedirectionAttempt OBJECT-TYPE
    SYNTAX      Counter32
    MAX-ACCESS  read-write
    STATUS      current
    DESCRIPTION 
        "This count reflects the total number of  trunking Out-Of-Dialog (OOD) Private Branch Exchange (PBX) redirections that have been attempted."
-- @feature:208093
    ::= { trunkGroup 9 }

  bwTrunkOodPbxRedirectionBlocked OBJECT-TYPE
    SYNTAX      Counter32
    MAX-ACCESS  read-write
    STATUS      current
    DESCRIPTION 
        "This count reflects the total number of trunking Out-Of-Dialog (OOD) Private Branch Exchange (PBX) redirections that are blocked because the trunk group call capacity has been reached."
-- @feature:208093
    ::= { trunkGroup 10 }

-- Service : Custom Ringback ...........................................

  bwCustomRingbackUserAudioAttempts OBJECT-TYPE
    SYNTAX      Counter32
    MAX-ACCESS  read-write
    STATUS      current
    DESCRIPTION 
        "This counter is incremented each time a command is sent to the Media Server in an attempt to play a user custom audio ringback."
    ::= { customRingback 1 }

  bwCustomRingbackUserVideoAttempts OBJECT-TYPE
    SYNTAX      Counter32
    MAX-ACCESS  read-write
    STATUS      current
    DESCRIPTION 
        "This counter is incremented each time a command is sent to the Media Server in an attempt to play a user custom video ringback."
    ::= { customRingback 2 }

  bwCustomRingbackUserAudioFailures OBJECT-TYPE
    SYNTAX      Counter32
    MAX-ACCESS  read-write
    STATUS      current
    DESCRIPTION 
        "This counter is incremented each time where an attempt is made to play a user custom audio ringback, and that the Media Server reports any failure to play it."
    ::= { customRingback 3 }

  bwCustomRingbackUserVideoFailures OBJECT-TYPE
    SYNTAX      Counter32
    MAX-ACCESS  read-write
    STATUS      current
    DESCRIPTION 
        "This counter is incremented each time where an attempt is made to play a user custom video ringback, and that the Media Server reports any failure to play it."
    ::= { customRingback 4 }

  bwCustomRingbackGroupAudioAttempts OBJECT-TYPE
    SYNTAX      Counter32
    MAX-ACCESS  read-write
    STATUS      current
    DESCRIPTION 
        "This counter is incremented each time a command is sent to the Media Server in an attempt to play a group custom audio ringback."
    ::= { customRingback 5 }

  bwCustomRingbackGroupVideoAttempts OBJECT-TYPE
    SYNTAX      Counter32
    MAX-ACCESS  read-write
    STATUS      current
    DESCRIPTION 
        "This counter is incremented each time a command is sent to the Media Server in an attempt to play a group custom video ringback."
    ::= { customRingback 6 }

  bwCustomRingbackGroupAudioFailures OBJECT-TYPE
    SYNTAX      Counter32
    MAX-ACCESS  read-write
    STATUS      current
    DESCRIPTION 
        "This counter is incremented each time where an attempt is made to play a group custom audio ringback, and that the Media Server reports any failure to play it."
    ::= { customRingback 7 }

  bwCustomRingbackGroupVideoFailures OBJECT-TYPE
    SYNTAX      Counter32
    MAX-ACCESS  read-write
    STATUS      current
    DESCRIPTION 
        "This counter is incremented each time where an attempt is made to play a group custom video ringback, and that the Media Server reports any failure to play it."
    ::= { customRingback 8 }

  bwCustomRingbackSPTable OBJECT-TYPE
    SYNTAX      SEQUENCE OF BwCustomRingbackSPEntry
    MAX-ACCESS  not-accessible
    STATUS      current
    DESCRIPTION 
        "Counters for the Custom Ringback service measurements for service providers."
    ::= { customRingback 9 }

  bwCustomRingbackSPEntry OBJECT-TYPE
    SYNTAX      BwCustomRingbackSPEntry
    MAX-ACCESS  not-accessible
    STATUS      current
    DESCRIPTION 
        "Each row contains the service counters for the Custom Ringback service for each service provider in the system."
    INDEX       { bwCustomRingbackSPIndex }
    ::= { bwCustomRingbackSPTable 1 }

  BwCustomRingbackSPEntry ::= SEQUENCE {
    bwCustomRingbackSPIndex                 Unsigned32,
    bwCustomRingbackSPID                    DisplayString,
    bwCustomRingbackUserAudioSPAttempts     Counter32,
    bwCustomRingbackUserVideoSPAttempts     Counter32,
    bwCustomRingbackUserAudioSPFailures     Counter32,
    bwCustomRingbackUserVideoSPFailures     Counter32,
    bwCustomRingbackGroupAudioSPAttempts    Counter32,
    bwCustomRingbackGroupVideoSPAttempts    Counter32,
    bwCustomRingbackGroupAudioSPFailures    Counter32,
    bwCustomRingbackGroupVideoSPFailures    Counter32,
    bwCustomRingbackUserAudioCWSPAttempts   Counter32,
    bwCustomRingbackUserVideoCWSPAttempts   Counter32,
    bwCustomRingbackUserAudioCWSPFailures   Counter32,
    bwCustomRingbackUserVideoCWSPFailures   Counter32
  }

  bwCustomRingbackSPIndex OBJECT-TYPE
    SYNTAX      Unsigned32
    MAX-ACCESS  read-only
    STATUS      current
    DESCRIPTION 
        "This column represents the index of the service provider in the system."
    ::= { bwCustomRingbackSPEntry 1 }

  bwCustomRingbackSPID OBJECT-TYPE
    SYNTAX      DisplayString
    MAX-ACCESS  read-only
    STATUS      current
    DESCRIPTION 
        "This string represents a service provider ID."
    ::= { bwCustomRingbackSPEntry 2 }

  bwCustomRingbackUserAudioSPAttempts OBJECT-TYPE
    SYNTAX      Counter32
    MAX-ACCESS  read-write
    STATUS      current
    DESCRIPTION 
        "This counter is incremented each time a command is sent to the Media Server in an attempt to play a user custom audio ringback for a given service provider."
    ::= { bwCustomRingbackSPEntry 3 }

  bwCustomRingbackUserVideoSPAttempts OBJECT-TYPE
    SYNTAX      Counter32
    MAX-ACCESS  read-write
    STATUS      current
    DESCRIPTION 
        "This counter is incremented each time a command is sent to the Media Server in an attempt to play a user custom video ringback for a given service provider."
    ::= { bwCustomRingbackSPEntry 4 }

  bwCustomRingbackUserAudioSPFailures OBJECT-TYPE
    SYNTAX      Counter32
    MAX-ACCESS  read-write
    STATUS      current
    DESCRIPTION 
        "This counter is incremented each time where an attempt is made to play a user custom audio ringback, and that the Media Server reports any failure to play it for a given service provider."
    ::= { bwCustomRingbackSPEntry 5 }

  bwCustomRingbackUserVideoSPFailures OBJECT-TYPE
    SYNTAX      Counter32
    MAX-ACCESS  read-write
    STATUS      current
    DESCRIPTION 
        "This counter is incremented each time where an attempt is made to play a user custom video ringback, and that the Media Server reports any failure to play it for a given service provider."
    ::= { bwCustomRingbackSPEntry 6 }

  bwCustomRingbackGroupAudioSPAttempts OBJECT-TYPE
    SYNTAX      Counter32
    MAX-ACCESS  read-write
    STATUS      current
    DESCRIPTION 
        "This counter is incremented each time a command is sent to the Media Server in an attempt to play a group custom audio ringback for a given service provider."
    ::= { bwCustomRingbackSPEntry 7 }

  bwCustomRingbackGroupVideoSPAttempts OBJECT-TYPE
    SYNTAX      Counter32
    MAX-ACCESS  read-write
    STATUS      current
    DESCRIPTION 
        "This counter is incremented each time a command is sent to the Media Server in an attempt to play a group custom video ringback for a given service provider."
    ::= { bwCustomRingbackSPEntry 8 }

  bwCustomRingbackGroupAudioSPFailures OBJECT-TYPE
    SYNTAX      Counter32
    MAX-ACCESS  read-write
    STATUS      current
    DESCRIPTION 
        "This counter is incremented each time where an attempt is made to play a group custom audio ringback, and that the Media Server reports any failure to play it for a given service provider."
    ::= { bwCustomRingbackSPEntry 9 }

  bwCustomRingbackGroupVideoSPFailures OBJECT-TYPE
    SYNTAX      Counter32
    MAX-ACCESS  read-write
    STATUS      current
    DESCRIPTION 
        "This counter is incremented each time where an attempt is made to play a group custom video ringback, and that the Media Server reports any failure to play it for a given service provider."
    ::= { bwCustomRingbackSPEntry 10 }

  bwCustomRingbackUserAudioCWSPAttempts OBJECT-TYPE
    SYNTAX      Counter32
    MAX-ACCESS  read-write
    STATUS      current
    DESCRIPTION 
        "Number of attempts to play a user custom audio Ringback for Call Waiting for a service provider."
    ::= { bwCustomRingbackSPEntry 11 }

  bwCustomRingbackUserVideoCWSPAttempts OBJECT-TYPE
    SYNTAX      Counter32
    MAX-ACCESS  read-write
    STATUS      current
    DESCRIPTION 
        "Number of attempts to play a user custom video Ringback for Call Waiting for a service provider."
    ::= { bwCustomRingbackSPEntry 12 }

  bwCustomRingbackUserAudioCWSPFailures OBJECT-TYPE
    SYNTAX      Counter32
    MAX-ACCESS  read-write
    STATUS      current
    DESCRIPTION 
        "Number of failures to play a user custom audio Ringback for Call Waiting for a service provider."
    ::= { bwCustomRingbackSPEntry 13 }

  bwCustomRingbackUserVideoCWSPFailures OBJECT-TYPE
    SYNTAX      Counter32
    MAX-ACCESS  read-write
    STATUS      current
    DESCRIPTION 
        "Number of failures to play a user custom video Ringback for Call Waiting for a service provider."
    ::= { bwCustomRingbackSPEntry 14 }

  bwCustomRingbackGroupTable OBJECT-TYPE
    SYNTAX      SEQUENCE OF BwCustomRingbackGroupEntry
    MAX-ACCESS  not-accessible
    STATUS      current
    DESCRIPTION 
        "Counters for the Custom Ringback service measurements for groups."
    ::= { customRingback 10 }

  bwCustomRingbackGroupEntry OBJECT-TYPE
    SYNTAX      BwCustomRingbackGroupEntry
    MAX-ACCESS  not-accessible
    STATUS      current
    DESCRIPTION 
        "Each row contains the service counters for the Custom Ringback service for each group in the system."
    INDEX       { bwCustomRingbackGroupIndex }
    ::= { bwCustomRingbackGroupTable 1 }

  BwCustomRingbackGroupEntry ::= SEQUENCE {
    bwCustomRingbackGroupIndex                  Unsigned32,
    bwCustomRingbackGroupID                     DisplayString,
    bwCustomRingbackUserAudioGroupAttempts      Counter32,
    bwCustomRingbackUserVideoGroupAttempts      Counter32,
    bwCustomRingbackUserAudioGroupFailures      Counter32,
    bwCustomRingbackUserVideoGroupFailures      Counter32,
    bwCustomRingbackGroupAudioGroupAttempts     Counter32,
    bwCustomRingbackGroupVideoGroupAttempts     Counter32,
    bwCustomRingbackGroupAudioGroupFailures     Counter32,
    bwCustomRingbackGroupVideoGroupFailures     Counter32,
    bwCustomRingbackUserAudioCWGroupAttempts    Counter32,
    bwCustomRingbackUserVideoCWGroupAttempts    Counter32,
    bwCustomRingbackUserAudioCWGroupFailures    Counter32,
    bwCustomRingbackUserVideoCWGroupFailures    Counter32
  }

  bwCustomRingbackGroupIndex OBJECT-TYPE
    SYNTAX      Unsigned32
    MAX-ACCESS  read-only
    STATUS      current
    DESCRIPTION 
        "This column represents the index of the group in the system."
    ::= { bwCustomRingbackGroupEntry 1 }

  bwCustomRingbackGroupID OBJECT-TYPE
    SYNTAX      DisplayString
    MAX-ACCESS  read-only
    STATUS      current
    DESCRIPTION 
        "This string represents a group ID."
    ::= { bwCustomRingbackGroupEntry 2 }

  bwCustomRingbackUserAudioGroupAttempts OBJECT-TYPE
    SYNTAX      Counter32
    MAX-ACCESS  read-write
    STATUS      current
    DESCRIPTION 
        "This counter is incremented each time a command is sent to the Media Server in an attempt to play a user custom audio ringback for a given group."
    ::= { bwCustomRingbackGroupEntry 3 }

  bwCustomRingbackUserVideoGroupAttempts OBJECT-TYPE
    SYNTAX      Counter32
    MAX-ACCESS  read-write
    STATUS      current
    DESCRIPTION 
        "This counter is incremented each time a command is sent to the Media Server in an attempt to play a user custom video ringback for a given group."
    ::= { bwCustomRingbackGroupEntry 4 }

  bwCustomRingbackUserAudioGroupFailures OBJECT-TYPE
    SYNTAX      Counter32
    MAX-ACCESS  read-write
    STATUS      current
    DESCRIPTION 
        "This counter is incremented each time where an attempt is made to play a user custom audio ringback, and that the Media Server reports any failure to play it for a given group."
    ::= { bwCustomRingbackGroupEntry 5 }

  bwCustomRingbackUserVideoGroupFailures OBJECT-TYPE
    SYNTAX      Counter32
    MAX-ACCESS  read-write
    STATUS      current
    DESCRIPTION 
        "This counter is incremented each time where an attempt is made to play a user custom video ringback, and that the Media Server reports any failure to play it for a given group."
    ::= { bwCustomRingbackGroupEntry 6 }

  bwCustomRingbackGroupAudioGroupAttempts OBJECT-TYPE
    SYNTAX      Counter32
    MAX-ACCESS  read-write
    STATUS      current
    DESCRIPTION 
        "This counter is incremented each time a command is sent to the Media Server in an attempt to play a group custom audio ringback for a given group."
    ::= { bwCustomRingbackGroupEntry 7 }

  bwCustomRingbackGroupVideoGroupAttempts OBJECT-TYPE
    SYNTAX      Counter32
    MAX-ACCESS  read-write
    STATUS      current
    DESCRIPTION 
        "This counter is incremented each time a command is sent to the Media Server in an attempt to play a group custom video ringback for a given group."
    ::= { bwCustomRingbackGroupEntry 8 }

  bwCustomRingbackGroupAudioGroupFailures OBJECT-TYPE
    SYNTAX      Counter32
    MAX-ACCESS  read-write
    STATUS      current
    DESCRIPTION 
        "This counter is incremented each time where an attempt is made to play a group custom audio ringback, and that the Media Server reports any failure to play it for a given group."
    ::= { bwCustomRingbackGroupEntry 9 }

  bwCustomRingbackGroupVideoGroupFailures OBJECT-TYPE
    SYNTAX      Counter32
    MAX-ACCESS  read-write
    STATUS      current
    DESCRIPTION 
        "This counter is incremented each time where an attempt is made to play a group custom video ringback, and that the Media Server reports any failure to play it for a given group."
    ::= { bwCustomRingbackGroupEntry 10 }

  bwCustomRingbackUserAudioCWGroupAttempts OBJECT-TYPE
    SYNTAX      Counter32
    MAX-ACCESS  read-write
    STATUS      current
    DESCRIPTION 
        "Number of attempts to play a user custom audio Ringback for Call Waiting for a group."
    ::= { bwCustomRingbackGroupEntry 11 }

  bwCustomRingbackUserVideoCWGroupAttempts OBJECT-TYPE
    SYNTAX      Counter32
    MAX-ACCESS  read-write
    STATUS      current
    DESCRIPTION 
        "Number of attempts to play a user custom video Ringback for Call Waiting for a group."
    ::= { bwCustomRingbackGroupEntry 12 }

  bwCustomRingbackUserAudioCWGroupFailures OBJECT-TYPE
    SYNTAX      Counter32
    MAX-ACCESS  read-write
    STATUS      current
    DESCRIPTION 
        "Number of failures to play a user custom audio Ringback for Call Waiting for a group."
    ::= { bwCustomRingbackGroupEntry 13 }

  bwCustomRingbackUserVideoCWGroupFailures OBJECT-TYPE
    SYNTAX      Counter32
    MAX-ACCESS  read-write
    STATUS      current
    DESCRIPTION 
        "Number of failures to play a user custom video Ringback for Call Waiting for a group."
    ::= { bwCustomRingbackGroupEntry 14 }

  bwCustomRingbackUserAudioCWAttempts OBJECT-TYPE
    SYNTAX      Counter32
    MAX-ACCESS  read-write
    STATUS      current
    DESCRIPTION 
        "Number of attempts to play a user custom audio Ringback for Call Waiting."
    ::= { customRingback 11 }

  bwCustomRingbackUserVideoCWAttempts OBJECT-TYPE
    SYNTAX      Counter32
    MAX-ACCESS  read-write
    STATUS      current
    DESCRIPTION 
        "Number of attempts to play a user custom video Ringback for Call Waiting."
    ::= { customRingback 12 }

  bwCustomRingbackUserAudioCWFailures OBJECT-TYPE
    SYNTAX      Counter32
    MAX-ACCESS  read-write
    STATUS      current
    DESCRIPTION 
        "Number of failures to play a user custom audio Ringback for Call Waiting."
    ::= { customRingback 13 }

  bwCustomRingbackUserVideoCWFailures OBJECT-TYPE
    SYNTAX      Counter32
    MAX-ACCESS  read-write
    STATUS      current
    DESCRIPTION 
        "Number of failures to play a user custom video Ringback for Call Waiting."
    ::= { customRingback 14 }

  bwNbPhysicalLocationOriginationBlocked OBJECT-TYPE
    SYNTAX      Counter32
    MAX-ACCESS  read-write
    STATUS      current
    DESCRIPTION 
        "Number of times a user has an origination blocked by the Physical Location service."
    ::= { physicalLocation 1 }

  bwPhysicalLocationSPTable OBJECT-TYPE
    SYNTAX      SEQUENCE OF BwPhysicalLocationSPEntry
    MAX-ACCESS  not-accessible
    STATUS      current
    DESCRIPTION 
        "Counters for the Physical Location service measurements for service providers"
    ::= { physicalLocation 2 }

  bwPhysicalLocationSPEntry OBJECT-TYPE
    SYNTAX      BwPhysicalLocationSPEntry
    MAX-ACCESS  not-accessible
    STATUS      current
    DESCRIPTION 
        "Each row contains the service counters for the Physical Location service for each service provider in the system"
    INDEX       { bwPhysicalLocationSPIndex }
    ::= { bwPhysicalLocationSPTable 1 }

  BwPhysicalLocationSPEntry ::= SEQUENCE {
    bwPhysicalLocationSPIndex               Unsigned32,
    bwPhysicalLocationSPID                  DisplayString,
    bwPhysicalLocationSPOriginationBlocked  Counter32
  }

  bwPhysicalLocationSPIndex OBJECT-TYPE
    SYNTAX      Unsigned32
    MAX-ACCESS  read-only
    STATUS      current
    DESCRIPTION 
        "This column represents the index of the service provider in the system"
    ::= { bwPhysicalLocationSPEntry 1 }

  bwPhysicalLocationSPID OBJECT-TYPE
    SYNTAX      DisplayString
    MAX-ACCESS  read-only
    STATUS      current
    DESCRIPTION 
        "This string represents a service provider ID"
    ::= { bwPhysicalLocationSPEntry 2 }

  bwPhysicalLocationSPOriginationBlocked OBJECT-TYPE
    SYNTAX      Counter32
    MAX-ACCESS  read-write
    STATUS      current
    DESCRIPTION 
        "Number of times a user under the Service Provider has an origination blocked by the Physical Location service."
    ::= { bwPhysicalLocationSPEntry 3 }

  bwPhysicalLocationGroupTable OBJECT-TYPE
    SYNTAX      SEQUENCE OF BwPhysicalLocationGroupEntry
    MAX-ACCESS  not-accessible
    STATUS      current
    DESCRIPTION 
        "Counters for the Physical Location service measurements for groups"
    ::= { physicalLocation 3 }

  bwPhysicalLocationGroupEntry OBJECT-TYPE
    SYNTAX      BwPhysicalLocationGroupEntry
    MAX-ACCESS  not-accessible
    STATUS      current
    DESCRIPTION 
        "Each row contains the service counters for the Physical Location service for each group in the system"
    INDEX       { bwPhysicalLocationGroupIndex }
    ::= { bwPhysicalLocationGroupTable 1 }

  BwPhysicalLocationGroupEntry ::= SEQUENCE {
    bwPhysicalLocationGroupIndex                Unsigned32,
    bwPhysicalLocationGroupID                   DisplayString,
    bwPhysicalLocationGroupOriginationBlocked   Counter32
  }

  bwPhysicalLocationGroupIndex OBJECT-TYPE
    SYNTAX      Unsigned32
    MAX-ACCESS  read-only
    STATUS      current
    DESCRIPTION 
        "This column represents the index of the group in the system"
    ::= { bwPhysicalLocationGroupEntry 1 }

  bwPhysicalLocationGroupID OBJECT-TYPE
    SYNTAX      DisplayString
    MAX-ACCESS  read-only
    STATUS      current
    DESCRIPTION 
        "This string represents a service provider ID"
    ::= { bwPhysicalLocationGroupEntry 2 }

  bwPhysicalLocationGroupOriginationBlocked OBJECT-TYPE
    SYNTAX      Counter32
    MAX-ACCESS  read-write
    STATUS      current
    DESCRIPTION 
        "Number of times a user under the group has an origination blocked by the Physical Location service."
    ::= { bwPhysicalLocationGroupEntry 3 }

  bwFaxMessagingReceived OBJECT-TYPE
    SYNTAX      Counter32
    MAX-ACCESS  read-write
    STATUS      current
    DESCRIPTION 
        "This counter is incremented each time a user receives a fax."
    ::= { faxMessaging 1 }

  bwFaxMessagingReceptionFailure OBJECT-TYPE
    SYNTAX      Counter32
    MAX-ACCESS  read-write
    STATUS      current
    DESCRIPTION 
        "This counter is incremented whenever the reception of a fax fails."
    ::= { faxMessaging 2 }

  bwFaxMessagingPrinted OBJECT-TYPE
    SYNTAX      Counter32
    MAX-ACCESS  read-write
    STATUS      current
    DESCRIPTION 
        "This counter is incremented each time a user sends a fax."
    ::= { faxMessaging 3 }

  bwFaxMessagingPrintingFailure OBJECT-TYPE
    SYNTAX      Counter32
    MAX-ACCESS  read-write
    STATUS      current
    DESCRIPTION 
        "This counter is incremented each time the printing of a fax over a fax number fails."
    ::= { faxMessaging 4 }

  bwFaxMessagingSPTable OBJECT-TYPE
    SYNTAX      SEQUENCE OF BwFaxMessagingSPEntry
    MAX-ACCESS  not-accessible
    STATUS      current
    DESCRIPTION 
        "Counters for the Fax Messaging service measurements for service providers"
    ::= { faxMessaging 5 }

  bwFaxMessagingSPEntry OBJECT-TYPE
    SYNTAX      BwFaxMessagingSPEntry
    MAX-ACCESS  not-accessible
    STATUS      current
    DESCRIPTION 
        "Each row contains the service counters for the Fax Messaging service for each service provider in the system"
    INDEX       { bwFaxMessagingSPIndex }
    ::= { bwFaxMessagingSPTable 1 }

  BwFaxMessagingSPEntry ::= SEQUENCE {
    bwFaxMessagingSPIndex               Unsigned32,
    bwFaxMessagingSPID                  DisplayString,
    bwFaxMessagingSPReceived            Counter32,
    bwFaxMessagingSPReceptionFailure    Counter32,
    bwFaxMessagingSPPrinted             Counter32,
    bwFaxMessagingSPPrintingFailure     Counter32
  }

  bwFaxMessagingSPIndex OBJECT-TYPE
    SYNTAX      Unsigned32
    MAX-ACCESS  read-only
    STATUS      current
    DESCRIPTION 
        "This column represents the index of the service provider in the system"
    ::= { bwFaxMessagingSPEntry 1 }

  bwFaxMessagingSPID OBJECT-TYPE
    SYNTAX      DisplayString
    MAX-ACCESS  read-only
    STATUS      current
    DESCRIPTION 
        "This string represents a service provider ID"
    ::= { bwFaxMessagingSPEntry 2 }

  bwFaxMessagingSPReceived OBJECT-TYPE
    SYNTAX      Counter32
    MAX-ACCESS  read-write
    STATUS      current
    DESCRIPTION 
        "This counter is incremented each time a user for a given service provider receives a fax."
    ::= { bwFaxMessagingSPEntry 3 }

  bwFaxMessagingSPReceptionFailure OBJECT-TYPE
    SYNTAX      Counter32
    MAX-ACCESS  read-write
    STATUS      current
    DESCRIPTION 
        "This counter is incremented whenever the reception of a fax fails for a user for a given service provider."
    ::= { bwFaxMessagingSPEntry 4 }

  bwFaxMessagingSPPrinted OBJECT-TYPE
    SYNTAX      Counter32
    MAX-ACCESS  read-write
    STATUS      current
    DESCRIPTION 
        "This counter is incremented each time a user for a given service provider sends a fax."
    ::= { bwFaxMessagingSPEntry 5 }

  bwFaxMessagingSPPrintingFailure OBJECT-TYPE
    SYNTAX      Counter32
    MAX-ACCESS  read-write
    STATUS      current
    DESCRIPTION 
        "This counter is incremented each time the printing of a fax over a fax number fails for a user for a given service provider."
    ::= { bwFaxMessagingSPEntry 6 }

  bwFaxMessagingGroupTable OBJECT-TYPE
    SYNTAX      SEQUENCE OF BwFaxMessagingGroupEntry
    MAX-ACCESS  not-accessible
    STATUS      current
    DESCRIPTION 
        "Counters for the Fax Messaging service measurements for groups"
    ::= { faxMessaging 6 }

  bwFaxMessagingGroupEntry OBJECT-TYPE
    SYNTAX      BwFaxMessagingGroupEntry
    MAX-ACCESS  not-accessible
    STATUS      current
    DESCRIPTION 
        "Each row contains the service counters for the Fax Messaging service for each group in the system"
    INDEX       { bwFaxMessagingGroupIndex }
    ::= { bwFaxMessagingGroupTable 1 }

  BwFaxMessagingGroupEntry ::= SEQUENCE {
    bwFaxMessagingGroupIndex                Unsigned32,
    bwFaxMessagingGroupID                   DisplayString,
    bwFaxMessagingGroupReceived             Counter32,
    bwFaxMessagingGroupReceptionFailure     Counter32,
    bwFaxMessagingGroupPrinted              Counter32,
    bwFaxMessagingGroupPrintingFailure      Counter32
  }

  bwFaxMessagingGroupIndex OBJECT-TYPE
    SYNTAX      Unsigned32
    MAX-ACCESS  read-only
    STATUS      current
    DESCRIPTION 
        "This column represents the index of the group in the system"
    ::= { bwFaxMessagingGroupEntry 1 }

  bwFaxMessagingGroupID OBJECT-TYPE
    SYNTAX      DisplayString
    MAX-ACCESS  read-only
    STATUS      current
    DESCRIPTION 
        "This string represents a group ID"
    ::= { bwFaxMessagingGroupEntry 2 }

  bwFaxMessagingGroupReceived OBJECT-TYPE
    SYNTAX      Counter32
    MAX-ACCESS  read-write
    STATUS      current
    DESCRIPTION 
        "This counter is incremented each time a user for a given group receives a fax."
    ::= { bwFaxMessagingGroupEntry 3 }

  bwFaxMessagingGroupReceptionFailure OBJECT-TYPE
    SYNTAX      Counter32
    MAX-ACCESS  read-write
    STATUS      current
    DESCRIPTION 
        "This counter is incremented whenever the reception of a fax fails for a user for a given group."
    ::= { bwFaxMessagingGroupEntry 4 }

  bwFaxMessagingGroupPrinted OBJECT-TYPE
    SYNTAX      Counter32
    MAX-ACCESS  read-write
    STATUS      current
    DESCRIPTION 
        "This counter is incremented each time a user for a given group sends a fax."
    ::= { bwFaxMessagingGroupEntry 5 }

  bwFaxMessagingGroupPrintingFailure OBJECT-TYPE
    SYNTAX      Counter32
    MAX-ACCESS  read-write
    STATUS      current
    DESCRIPTION 
        "This counter is incremented each time the printing of a fax over a fax number fails for a user for a given group."
    ::= { bwFaxMessagingGroupEntry 6 }

  bwExtEmergencyRtgQuerySent OBJECT-TYPE
    SYNTAX      Counter32
    MAX-ACCESS  read-write
    STATUS      current
    DESCRIPTION 
        "The counter shall be incremented each time the service results in a query being sent to the EN Server."
    ::= { externalemergencyrouting 1 }

  bwExtEmergencyRtgQueryFailure OBJECT-TYPE
    SYNTAX      Counter32
    MAX-ACCESS  read-write
    STATUS      current
    DESCRIPTION 
        "The counter shall be incremented each time the query is not successful, either because the EN Server is unreachable, or because the routing number is invalid."
    ::= { externalemergencyrouting 2 }

  bwExtEmergencyRtgENServerTimeout OBJECT-TYPE
    SYNTAX      Counter32
    MAX-ACCESS  read-write
    STATUS      current
    DESCRIPTION 
        "The counter shall be incremented each time an active connection to an EN Server times out."
    ::= { externalemergencyrouting 3 }

  bwTwoStageDialingInvocation OBJECT-TYPE
    SYNTAX      Counter32
    MAX-ACCESS  read-write
    STATUS      current
    DESCRIPTION 
        "Number of times a user invokes the Two-Stage Dialing service."
    ::= { twoStageDialing 1 }

  bwTwoStageDialingSPTable OBJECT-TYPE
    SYNTAX      SEQUENCE OF BwTwoStageDialingSPEntry
    MAX-ACCESS  not-accessible
    STATUS      current
    DESCRIPTION 
        "Counters for the Two Stage Dialing service measurements for service providers"
    ::= { twoStageDialing 2 }

  bwTwoStageDialingSPEntry OBJECT-TYPE
    SYNTAX      BwTwoStageDialingSPEntry
    MAX-ACCESS  not-accessible
    STATUS      current
    DESCRIPTION 
        "Each row contains the service counters for the Fax Messaging service for each service provider in the system"
    INDEX       { bwTwoStageDialingSPIndex }
    ::= { bwTwoStageDialingSPTable 1 }

  BwTwoStageDialingSPEntry ::= SEQUENCE {
    bwTwoStageDialingSPIndex        Unsigned32,
    bwTwoStageDialingSPID           DisplayString,
    bwTwoStageDialingSPInvocation   Counter32
  }

  bwTwoStageDialingSPIndex OBJECT-TYPE
    SYNTAX      Unsigned32
    MAX-ACCESS  read-only
    STATUS      current
    DESCRIPTION 
        "This column represents the index of the Service Provider in the system"
    ::= { bwTwoStageDialingSPEntry 1 }

  bwTwoStageDialingSPID OBJECT-TYPE
    SYNTAX      DisplayString
    MAX-ACCESS  read-only
    STATUS      current
    DESCRIPTION 
        "This string represents a Service Provider ID"
    ::= { bwTwoStageDialingSPEntry 2 }

  bwTwoStageDialingSPInvocation OBJECT-TYPE
    SYNTAX      Counter32
    MAX-ACCESS  read-write
    STATUS      current
    DESCRIPTION 
        "Number of times a user invokes the Two-Stage Dialing service.  There is one instance of this counter for each service provider defined in the system."
    ::= { bwTwoStageDialingSPEntry 3 }

  bwTwoStageDialingGroupTable OBJECT-TYPE
    SYNTAX      SEQUENCE OF BwTwoStageDialingGroupEntry
    MAX-ACCESS  not-accessible
    STATUS      current
    DESCRIPTION 
        "Counters for the Two Stage Dialing service measurements for groups"
    ::= { twoStageDialing 3 }

  bwTwoStageDialingGroupEntry OBJECT-TYPE
    SYNTAX      BwTwoStageDialingGroupEntry
    MAX-ACCESS  not-accessible
    STATUS      current
    DESCRIPTION 
        "Each row contains the service counters for the Fax Messaging service for each service provider in the system"
    INDEX       { bwTwoStageDialingGroupIndex }
    ::= { bwTwoStageDialingGroupTable 1 }

  BwTwoStageDialingGroupEntry ::= SEQUENCE {
    bwTwoStageDialingGroupIndex         Unsigned32,
    bwTwoStageDialingGroupID            DisplayString,
    bwTwoStageDialingGroupInvocation    Counter32
  }

  bwTwoStageDialingGroupIndex OBJECT-TYPE
    SYNTAX      Unsigned32
    MAX-ACCESS  read-only
    STATUS      current
    DESCRIPTION 
        "This column represents the index of the Group in the system"
    ::= { bwTwoStageDialingGroupEntry 1 }

  bwTwoStageDialingGroupID OBJECT-TYPE
    SYNTAX      DisplayString
    MAX-ACCESS  read-only
    STATUS      current
    DESCRIPTION 
        "This string represents a Group ID"
    ::= { bwTwoStageDialingGroupEntry 2 }

  bwTwoStageDialingGroupInvocation OBJECT-TYPE
    SYNTAX      Counter32
    MAX-ACCESS  read-write
    STATUS      current
    DESCRIPTION 
        "Number of times a user invokes the Two-Stage Dialing service.  There is one instance of this counter for each group defined in the system."
    ::= { bwTwoStageDialingGroupEntry 3 }

  bwCFNRcNumForwarded OBJECT-TYPE
    SYNTAX      Counter32
    MAX-ACCESS  read-write
    STATUS      current
    DESCRIPTION 
        "This is the number of times a call is redirected by the Call Forwarding Not Reachable service."
    ::= { callForwardingNotReachable 1 }

  bwCFNRcNumPhoneActivations OBJECT-TYPE
    SYNTAX      Counter32
    MAX-ACCESS  read-write
    STATUS      current
    DESCRIPTION 
        "This is the number of times the Call Forwarding Not Reachable service is activated with a FAC."
    ::= { callForwardingNotReachable 2 }

  bwCFNRcNumPhoneDeactivations OBJECT-TYPE
    SYNTAX      Counter32
    MAX-ACCESS  read-write
    STATUS      current
    DESCRIPTION 
        "This is the number of times the Call Forwarding Not Reachable service is deactivated with a FAC."
    ::= { callForwardingNotReachable 3 }

  bwCFNRcDestinationChanged OBJECT-TYPE
    SYNTAX      Counter32
    MAX-ACCESS  read-write
    STATUS      current
    DESCRIPTION 
        "This is the number of times the Call Forwarding Not Reachable service destination is modified with the activation FAC."
    ::= { callForwardingNotReachable 4 }

  bwCallForwardingNotReachableSPTable OBJECT-TYPE
    SYNTAX      SEQUENCE OF BwCallForwardingNotReachableSPEntry
    MAX-ACCESS  not-accessible
    STATUS      current
    DESCRIPTION 
        "This is the number of times a call is redirected by the Call Forwarding Not Reachable service.  There is one instance of this counter for each service provider or enterprise defined in the system."
    ::= { callForwardingNotReachable 5 }

  bwCallForwardingNotReachableSPEntry OBJECT-TYPE
    SYNTAX      BwCallForwardingNotReachableSPEntry
    MAX-ACCESS  not-accessible
    STATUS      current
    DESCRIPTION 
        "Each row contains the service counters for the Call Forwarding Not Reachable service for each service provider in the system"
    INDEX       { bwCFNRcSPIndex }
    ::= { bwCallForwardingNotReachableSPTable 1 }

  BwCallForwardingNotReachableSPEntry ::= SEQUENCE {
    bwCFNRcSPIndex                  Unsigned32,
    bwCFNRcSPID                     DisplayString,
    bwCFNRcSPNumForwarded           Counter32,
    bwCFNRcSPNumPhoneActivations    Counter32,
    bwCFNRcSPNumPhoneDeactivations  Counter32,
    bwCFNRcSPDestinationChanged     Counter32,
    bwCFNRcSPNumPhoneInterrogation  Counter32
  }

  bwCFNRcSPIndex OBJECT-TYPE
    SYNTAX      Unsigned32
    MAX-ACCESS  read-only
    STATUS      current
    DESCRIPTION 
        "This column represents the index of the Service Provider in the system."
    ::= { bwCallForwardingNotReachableSPEntry 1 }

  bwCFNRcSPID OBJECT-TYPE
    SYNTAX      DisplayString
    MAX-ACCESS  read-only
    STATUS      current
    DESCRIPTION 
        "This string represents a Service Provider ID."
    ::= { bwCallForwardingNotReachableSPEntry 2 }

  bwCFNRcSPNumForwarded OBJECT-TYPE
    SYNTAX      Counter32
    MAX-ACCESS  read-write
    STATUS      current
    DESCRIPTION 
        "This is the number of times a call is redirected by the Call Forwarding Not Reachable service.  There is one instance of this counter for each service provider or enterprise defined in the system."
    ::= { bwCallForwardingNotReachableSPEntry 3 }

  bwCFNRcSPNumPhoneActivations OBJECT-TYPE
    SYNTAX      Counter32
    MAX-ACCESS  read-write
    STATUS      current
    DESCRIPTION 
        "This is the number of times the Call Forwarding Not Reachable service is activated with a FAC.  There is one instance of this counter for each service provider or enterprise defined in the system."
    ::= { bwCallForwardingNotReachableSPEntry 4 }

  bwCFNRcSPNumPhoneDeactivations OBJECT-TYPE
    SYNTAX      Counter32
    MAX-ACCESS  read-write
    STATUS      current
    DESCRIPTION 
        "This is the number of times the Call Forwarding Not Reachable service is deactivated with a FAC.  There is one instance of this counter for each service provider or enterprise defined in the system."
    ::= { bwCallForwardingNotReachableSPEntry 5 }

  bwCFNRcSPDestinationChanged OBJECT-TYPE
    SYNTAX      Counter32
    MAX-ACCESS  read-write
    STATUS      current
    DESCRIPTION 
        "This is the number of times the Call Forwarding Not Reachable service destination is modified with the activation FAC.  There is one instance of this counter for each service provider or enterprise defined in the system."
    ::= { bwCallForwardingNotReachableSPEntry 6 }

  bwCFNRcSPNumPhoneInterrogation OBJECT-TYPE
    SYNTAX      Counter32
    MAX-ACCESS  read-write
    STATUS      current
    DESCRIPTION
        "This is the number of times Call Forwarding Not Reachable has been interrogated with a FAC for users in a given service provider."
    ::= { bwCallForwardingNotReachableSPEntry 7 }

  bwCallForwardingNotReachableGroupTable OBJECT-TYPE
    SYNTAX      SEQUENCE OF BwCallForwardingNotReachableGroupEntry
    MAX-ACCESS  not-accessible
    STATUS      current
    DESCRIPTION 
        "This is the number of times a call is redirected by the Call Forwarding Not Reachable service.  There is one instance of this counter for each group defined in the system."
    ::= { callForwardingNotReachable 6 }

  bwCallForwardingNotReachableGroupEntry OBJECT-TYPE
    SYNTAX      BwCallForwardingNotReachableGroupEntry
    MAX-ACCESS  not-accessible
    STATUS      current
    DESCRIPTION 
        "Each row contains the service counters for the Call Forwarding Not Reachable service for each group in the system"
    INDEX       { bwCFNRcGroupIndex }
    ::= { bwCallForwardingNotReachableGroupTable 1 }

  BwCallForwardingNotReachableGroupEntry ::= SEQUENCE {
    bwCFNRcGroupIndex                   Unsigned32,
    bwCFNRcGroupID                      DisplayString,
    bwCFNRcGroupNumForwarded            Counter32,
    bwCFNRcGroupNumPhoneActivations     Counter32,
    bwCFNRcGroupNumPhoneDeactivations   Counter32,
    bwCFNRcGroupDestinationChanged      Counter32,
    bwCFNRcGroupNumPhoneInterrogation   Counter32
  }

  bwCFNRcGroupIndex OBJECT-TYPE
    SYNTAX      Unsigned32
    MAX-ACCESS  read-only
    STATUS      current
    DESCRIPTION 
        "This column represents the index of the Group in the system."
    ::= { bwCallForwardingNotReachableGroupEntry 1 }

  bwCFNRcGroupID OBJECT-TYPE
    SYNTAX      DisplayString
    MAX-ACCESS  read-only
    STATUS      current
    DESCRIPTION 
        "This string represents a Group ID."
    ::= { bwCallForwardingNotReachableGroupEntry 2 }

  bwCFNRcGroupNumForwarded OBJECT-TYPE
    SYNTAX      Counter32
    MAX-ACCESS  read-write
    STATUS      current
    DESCRIPTION 
        "This is the number of times a call is redirected by the Call Forwarding Not Reachable service.  There is one instance of this counter for each group defined in the system."
    ::= { bwCallForwardingNotReachableGroupEntry 3 }

  bwCFNRcGroupNumPhoneActivations OBJECT-TYPE
    SYNTAX      Counter32
    MAX-ACCESS  read-write
    STATUS      current
    DESCRIPTION 
        "This is the number of times the Call Forwarding Not Reachable service is activated with a FAC.  There is one instance of this counter for each group defined in the system."
    ::= { bwCallForwardingNotReachableGroupEntry 4 }

  bwCFNRcGroupNumPhoneDeactivations OBJECT-TYPE
    SYNTAX      Counter32
    MAX-ACCESS  read-write
    STATUS      current
    DESCRIPTION 
        "This is the number of times the Call Forwarding Not Reachable service is deactivated with a FAC.  There is one instance of this counter for each group defined in the system."
    ::= { bwCallForwardingNotReachableGroupEntry 5 }

  bwCFNRcGroupDestinationChanged OBJECT-TYPE
    SYNTAX      Counter32
    MAX-ACCESS  read-write
    STATUS      current
    DESCRIPTION 
        "This is the number of times the Call Forwarding Not Reachable service destination is modified with the activation FAC.  There is one instance of this counter for each group defined in the system."
    ::= { bwCallForwardingNotReachableGroupEntry 6 }

  bwCFNRcGroupNumPhoneInterrogation    OBJECT-TYPE
    SYNTAX      Counter32
    MAX-ACCESS    read-write
    STATUS      current
    DESCRIPTION
        "This is the number of times Call Forwarding Not Reachable has been interrogated with a FAC for users in a given group."
    ::= { bwCallForwardingNotReachableGroupEntry 7 }

  bwCFNRcNumPhoneInterrogation OBJECT-TYPE
    SYNTAX      Counter32
    MAX-ACCESS  read-write
    STATUS      current
    DESCRIPTION
        "This is the number of times Call Forwarding Not Reachable has been interrogated with a FAC."
    ::= { callForwardingNotReachable 7 }

  bwMWISMSSent OBJECT-TYPE
    SYNTAX      Counter32
    MAX-ACCESS  read-write
    STATUS      current
    DESCRIPTION 
        "Number of SMS notifications sent for all users."
    ::= { mwiDeliveryToMobile 1 }

  bwMWIDeliveryToMobileSPTable OBJECT-TYPE
    SYNTAX      SEQUENCE OF BwMWIDeliveryToMobileSPEntry
    MAX-ACCESS  not-accessible
    STATUS      current
    DESCRIPTION 
        "This is the number of times a SMS is sent by the Message Waiting Indicator Delivery to Mobile service.  There is one instance of this counter for each service provider or enterprise defined in the system."
    ::= { mwiDeliveryToMobile 2 }

  bwMWIDeliveryToMobileSPEntry OBJECT-TYPE
    SYNTAX      BwMWIDeliveryToMobileSPEntry
    MAX-ACCESS  not-accessible
    STATUS      current
    DESCRIPTION 
        "Each row contains the service counters for the Message Waiting Indicator Delivery to Mobile service for each service provider in the system"
    INDEX       { bwMWISPIndex }
    ::= { bwMWIDeliveryToMobileSPTable 1 }

  BwMWIDeliveryToMobileSPEntry ::= SEQUENCE {
    bwMWISPIndex    Unsigned32,
    bwMWISPID       DisplayString,
    bwSPMWISMSSent  Counter32
  }

  bwMWISPIndex OBJECT-TYPE
    SYNTAX      Unsigned32
    MAX-ACCESS  read-only
    STATUS      current
    DESCRIPTION 
        "This column represents the index of the Service Provider in the system."
    ::= { bwMWIDeliveryToMobileSPEntry 1 }

  bwMWISPID OBJECT-TYPE
    SYNTAX      DisplayString
    MAX-ACCESS  read-only
    STATUS      current
    DESCRIPTION 
        "This string represents a Service Provider ID."
    ::= { bwMWIDeliveryToMobileSPEntry 2 }

  bwSPMWISMSSent OBJECT-TYPE
    SYNTAX      Counter32
    MAX-ACCESS  read-write
    STATUS      current
    DESCRIPTION 
        "Same as bwMWISMSSent, per service provider."
    ::= { bwMWIDeliveryToMobileSPEntry 3 }

  bwMWIDeliveryToMobileGroupTable OBJECT-TYPE
    SYNTAX      SEQUENCE OF BwMWIDeliveryToMobileGroupEntry
    MAX-ACCESS  not-accessible
    STATUS      current
    DESCRIPTION 
        "This is the number of times a SMS is sent by the Message Waiting Indicator Delivery to Mobile service.  There is one instance of this counter for each group defined in the system."
    ::= { mwiDeliveryToMobile 3 }

  bwMWIDeliveryToMobileGroupEntry OBJECT-TYPE
    SYNTAX      BwMWIDeliveryToMobileGroupEntry
    MAX-ACCESS  not-accessible
    STATUS      current
    DESCRIPTION 
        "Each row contains the service counters for the Message Waiting Indicator Delivery to Mobile service for each service provider in the system"
    INDEX       { bwMWIGroupIndex }
    ::= { bwMWIDeliveryToMobileGroupTable 1 }

  BwMWIDeliveryToMobileGroupEntry ::= SEQUENCE {
    bwMWIGroupIndex     Unsigned32,
    bwMWIGroupID        DisplayString,
    bwGroupMWISMSSent   Counter32
  }

  bwMWIGroupIndex OBJECT-TYPE
    SYNTAX      Unsigned32
    MAX-ACCESS  read-only
    STATUS      current
    DESCRIPTION 
        "This column represents the index of the Group in the system."
    ::= { bwMWIDeliveryToMobileGroupEntry 1 }

  bwMWIGroupID OBJECT-TYPE
    SYNTAX      DisplayString
    MAX-ACCESS  read-only
    STATUS      current
    DESCRIPTION 
        "This string represents a Group ID."
    ::= { bwMWIDeliveryToMobileGroupEntry 2 }

  bwGroupMWISMSSent OBJECT-TYPE
    SYNTAX      Counter32
    MAX-ACCESS  read-write
    STATUS      current
    DESCRIPTION 
        "Same as bwMWISMSSent, per service provider."
    ::= { bwMWIDeliveryToMobileGroupEntry 3 }

  bwExternalCustomRingbackAttempts OBJECT-TYPE
    SYNTAX      Counter32
    MAX-ACCESS  read-write
    STATUS      current
    DESCRIPTION 
        "This is the number of attempts made to play ringback from an external custom ringback source."
    ::= { externalCustomRingback 1 }

  bwExternalCustomRingbackFailures OBJECT-TYPE
    SYNTAX      Counter32
    MAX-ACCESS  read-write
    STATUS      current
    DESCRIPTION 
        "This is the number of times an attempt to play ringback from an external custom ringback source failed, due to timeout or error."
    ::= { externalCustomRingback 2 }

  bwExternalCustomRingbackSPTable OBJECT-TYPE
    SYNTAX      SEQUENCE OF BwExternalCustomRingbackSPEntry
    MAX-ACCESS  not-accessible
    STATUS      current
    DESCRIPTION 
        "This table contains the counters for External Custom Ringback service measurements for service providers."
    ::= { externalCustomRingback 3 }

  bwExternalCustomRingbackSPEntry OBJECT-TYPE
    SYNTAX      BwExternalCustomRingbackSPEntry
    MAX-ACCESS  not-accessible
    STATUS      current
    DESCRIPTION 
        "Each row contains the service counters for the External Custom Ringback service for each service provider in the system"
    INDEX       { bwExternalCustomRingbackSPIndex }
    ::= { bwExternalCustomRingbackSPTable 1 }

  BwExternalCustomRingbackSPEntry ::= SEQUENCE {
    bwExternalCustomRingbackSPIndex     Unsigned32,
    bwExternalCustomRingbackSPID        DisplayString,
    bwExternalCustomRingbackSPAttempts  Counter32,
    bwExternalCustomRingbackSPFailures  Counter32
  }

  bwExternalCustomRingbackSPIndex OBJECT-TYPE
    SYNTAX      Unsigned32
    MAX-ACCESS  read-only
    STATUS      current
    DESCRIPTION 
        "This column represents the index of the Service Provider in the system."
    ::= { bwExternalCustomRingbackSPEntry 1 }

  bwExternalCustomRingbackSPID OBJECT-TYPE
    SYNTAX      DisplayString
    MAX-ACCESS  read-only
    STATUS      current
    DESCRIPTION 
        "This string represents a Service Provider ID."
    ::= { bwExternalCustomRingbackSPEntry 2 }

  bwExternalCustomRingbackSPAttempts OBJECT-TYPE
    SYNTAX      Counter32
    MAX-ACCESS  read-write
    STATUS      current
    DESCRIPTION 
        "This is the number of attempts made to play ringback from an external custom ringback source for a given service provider. There is one instance of this counter for each service provider or enterprise defined in the system."
    ::= { bwExternalCustomRingbackSPEntry 3 }

  bwExternalCustomRingbackSPFailures OBJECT-TYPE
    SYNTAX      Counter32
    MAX-ACCESS  read-write
    STATUS      current
    DESCRIPTION 
        "This is the number of times an attempt to play ringback from an external custom ringback source failed, due to timeout or error, for a given service provider. There is one instance of this counter for each service provider or enterprise defined in the system."
    ::= { bwExternalCustomRingbackSPEntry 4 }

  bwExternalCustomRingbackGroupTable OBJECT-TYPE
    SYNTAX      SEQUENCE OF BwExternalCustomRingbackGroupEntry
    MAX-ACCESS  not-accessible
    STATUS      current
    DESCRIPTION 
        "This table contains the counters for External Custom Ringback service measurements for groups."
    ::= { externalCustomRingback 4 }

  bwExternalCustomRingbackGroupEntry OBJECT-TYPE
    SYNTAX      BwExternalCustomRingbackGroupEntry
    MAX-ACCESS  not-accessible
    STATUS      current
    DESCRIPTION 
        "Each row contains the service counters for the External Custom Ringback service for each group in the system"
    INDEX       { bwExternalCustomRingbackGroupIndex }
    ::= { bwExternalCustomRingbackGroupTable 1 }

  BwExternalCustomRingbackGroupEntry ::= SEQUENCE {
    bwExternalCustomRingbackGroupIndex      Unsigned32,
    bwExternalCustomRingbackGroupID         DisplayString,
    bwExternalCustomRingbackGroupAttempts   Counter32,
    bwExternalCustomRingbackGroupFailures   Counter32
  }

  bwExternalCustomRingbackGroupIndex OBJECT-TYPE
    SYNTAX      Unsigned32
    MAX-ACCESS  read-only
    STATUS      current
    DESCRIPTION 
        "This column represents the index of the Group in the system."
    ::= { bwExternalCustomRingbackGroupEntry 1 }

  bwExternalCustomRingbackGroupID OBJECT-TYPE
    SYNTAX      DisplayString
    MAX-ACCESS  read-only
    STATUS      current
    DESCRIPTION 
        "This string represents a Group ID."
    ::= { bwExternalCustomRingbackGroupEntry 2 }

  bwExternalCustomRingbackGroupAttempts OBJECT-TYPE
    SYNTAX      Counter32
    MAX-ACCESS  read-write
    STATUS      current
    DESCRIPTION 
        "This is the number of attempts made to play ringback from an external custom ringback source for a given group. There is one instance of this counter for each group defined in the system."
    ::= { bwExternalCustomRingbackGroupEntry 3 }

  bwExternalCustomRingbackGroupFailures OBJECT-TYPE
    SYNTAX      Counter32
    MAX-ACCESS  read-write
    STATUS      current
    DESCRIPTION 
        "This is the number of times an attempt to play ringback from an external custom ringback source failed, due to timeout or error, for a given group. There is one instance of this counter for each group defined in the system."
    ::= { bwExternalCustomRingbackGroupEntry 4 }

  bwInCallServiceActivationSPTable OBJECT-TYPE
    SYNTAX      SEQUENCE OF BwInCallServiceActivationSPEntry
    MAX-ACCESS  not-accessible
    STATUS      current
    DESCRIPTION 
        "Each row contains the service counters for the In Call Service Activation service for each service provider in the system"
    ::= { inCallServiceActivation 1 }

  bwInCallServiceActivationSPEntry OBJECT-TYPE
    SYNTAX      BwInCallServiceActivationSPEntry
    MAX-ACCESS  not-accessible
    STATUS      current
    DESCRIPTION 
        "Each row contains the service counters for the In Call Service Activation service for each service provider in the system"
    INDEX       { bwICSASPIndex }
    ::= { bwInCallServiceActivationSPTable 1 }

  BwInCallServiceActivationSPEntry ::= SEQUENCE {
    bwICSASPIndex                   Unsigned32,
    bwICSASPID                      DisplayString,
    bwICSASPMonitoringStarted       Counter32,
    bwICSASPMonitoringFailure       Counter32,
    bwICSASPFlashDigitsDetected     Counter32,
    bwICSASPCallTransferInvocation  Counter32
  }

  bwICSASPIndex OBJECT-TYPE
    SYNTAX      Unsigned32
    MAX-ACCESS  read-only
    STATUS      current
    DESCRIPTION 
        "This column represents the index of the Service Provider in the system."
    ::= { bwInCallServiceActivationSPEntry 1 }

  bwICSASPID OBJECT-TYPE
    SYNTAX      DisplayString
    MAX-ACCESS  read-only
    STATUS      current
    DESCRIPTION 
        "This string represents a Service Provider ID."
    ::= { bwInCallServiceActivationSPEntry 2 }

  bwICSASPMonitoringStarted OBJECT-TYPE
    SYNTAX      Counter32
    MAX-ACCESS  read-write
    STATUS      current
    DESCRIPTION 
        "This is the number of times a media path is monitored for Flash Tone digits by the In Call Service Activation service.  There is one instance of this counter for each service provider or enterprise defined in the system."
    ::= { bwInCallServiceActivationSPEntry 3 }

  bwICSASPMonitoringFailure OBJECT-TYPE
    SYNTAX      Counter32
    MAX-ACCESS  read-write
    STATUS      current
    DESCRIPTION 
        "This is the number of times media path monitoring fails to be started by the In Call Service Activation service.  There is one instance of this counter for each service provider or enterprise defined in the system."
    ::= { bwInCallServiceActivationSPEntry 4 }

  bwICSASPFlashDigitsDetected OBJECT-TYPE
    SYNTAX      Counter32
    MAX-ACCESS  read-write
    STATUS      current
    DESCRIPTION 
        "This is the number of times the In Call Service Activation service detects the Flash digit string.  There is one instance of this counter for each service provider or enterprise defined in the system."
    ::= { bwInCallServiceActivationSPEntry 5 }

  bwICSASPCallTransferInvocation OBJECT-TYPE
    SYNTAX      Counter32
    MAX-ACCESS  read-write
    STATUS      current
    DESCRIPTION 
        "This is the number of times the In-Call Service Activation Call Transfer functionality is invoked.  There is one instance of this counter for each service provider or enterprise defined in the system."
    ::= { bwInCallServiceActivationSPEntry 6 }

  bwInCallServiceActivationGroupTable OBJECT-TYPE
    SYNTAX      SEQUENCE OF BwInCallServiceActivationGroupEntry
    MAX-ACCESS  not-accessible
    STATUS      current
    DESCRIPTION 
        "Each row contains the service counters for the In Call Service Activation service for each group in the system"
    ::= { inCallServiceActivation 2 }

  bwInCallServiceActivationGroupEntry OBJECT-TYPE
    SYNTAX      BwInCallServiceActivationGroupEntry
    MAX-ACCESS  not-accessible
    STATUS      current
    DESCRIPTION 
        "Each row contains the service counters for the In Call Service Activation service for each group in the system"
    INDEX       { bwICSAGroupIndex }
    ::= { bwInCallServiceActivationGroupTable 1 }

  BwInCallServiceActivationGroupEntry ::= SEQUENCE {
    bwICSAGroupIndex                  Unsigned32,
    bwICSAGroupID                     DisplayString,
    bwICSAGroupMonitoringStarted      Counter32,
    bwICSAGroupMonitoringFailure      Counter32,
    bwICSAGroupFlashDigitsDetected    Counter32,
    bwICSAGroupCallTransferInvocation Counter32
  }

  bwICSAGroupIndex OBJECT-TYPE
    SYNTAX      Unsigned32
    MAX-ACCESS  read-only
    STATUS      current
    DESCRIPTION 
        "This column represents the index of the Group in the system."
    ::= { bwInCallServiceActivationGroupEntry 1 }

  bwICSAGroupID OBJECT-TYPE
    SYNTAX      DisplayString
    MAX-ACCESS  read-only
    STATUS      current
    DESCRIPTION 
        "This string represents a Group ID."
    ::= { bwInCallServiceActivationGroupEntry 2 }

  bwICSAGroupMonitoringStarted OBJECT-TYPE
    SYNTAX      Counter32
    MAX-ACCESS  read-write
    STATUS      current
    DESCRIPTION 
        "This is the number of times a media path is monitored for Flash Tone digits by the In Call Service Activation service.  There is one instance of this counter for each service provider or enterprise defined in the system."
    ::= { bwInCallServiceActivationGroupEntry 3 }

  bwICSAGroupMonitoringFailure OBJECT-TYPE
    SYNTAX      Counter32
    MAX-ACCESS  read-write
    STATUS      current
    DESCRIPTION 
        "This is the number of times media path monitoring fails to be started by the In Call Service Activation service.  There is one instance of this counter for each group defined in the system."
    ::= { bwInCallServiceActivationGroupEntry 4 }

  bwICSAGroupFlashDigitsDetected OBJECT-TYPE
    SYNTAX      Counter32
    MAX-ACCESS  read-write
    STATUS      current
    DESCRIPTION 
        "This is the number of times the In Call Service Activation service detects the Flash digit string.  There is one instance of this counter for each group defined in the system."
    ::= { bwInCallServiceActivationGroupEntry 5 }

  bwICSAGroupCallTransferInvocation OBJECT-TYPE
    SYNTAX      Counter32
    MAX-ACCESS  read-write
    STATUS      current
    DESCRIPTION 
        "This is the number of times the In-Call Service Activation Call Transfer functionality is invoked.  There is one instance of this counter for each group defined in the system."
    ::= { bwInCallServiceActivationGroupEntry 6 }

  bwICSAMonitoringStarted OBJECT-TYPE
    SYNTAX      Counter32
    MAX-ACCESS  read-write
    STATUS      current
    DESCRIPTION 
        "This is the number of times a media path is monitored for Flash Tone digits by the In Call Service Activation service."
    ::= { inCallServiceActivation 3 }

  bwICSAMonitoringFailure OBJECT-TYPE
    SYNTAX      Counter32
    MAX-ACCESS  read-write
    STATUS      current
    DESCRIPTION 
        "This is the number of times media path monitoring fails to be started by the In Call Service Activation service."
    ::= { inCallServiceActivation 4 }

  bwICSAFlashDigitsDetected OBJECT-TYPE
    SYNTAX      Counter32
    MAX-ACCESS  read-write
    STATUS      current
    DESCRIPTION 
        "This is the number of times the In Call Service Activation service detects the Flash digit string."
    ::= { inCallServiceActivation 5 }

  bwICSACallTransferInvocation OBJECT-TYPE
    SYNTAX      Counter32
    MAX-ACCESS  read-write
    STATUS      current
    DESCRIPTION 
        "This is the number of times the In-Call Service Activation Call Transfer functionality is invoked."
    ::= { inCallServiceActivation 6 }

  bwECNWarningAnnouncementAttempts OBJECT-TYPE
    SYNTAX      Counter32
    MAX-ACCESS  read-write
    STATUS      current
    DESCRIPTION 
        "This is the number of times the Expensive Call Notification service attempted to play a warning announcement for a call identified as expensive."
    ::= { expensiveCallNotification 1 }

  bwECNExpensiveCallReleased OBJECT-TYPE
    SYNTAX      Counter32
    MAX-ACCESS  read-write
    STATUS      current
    DESCRIPTION 
        "This is the number of times a user released an expensive call (identified as such by the Expensive Call Notification service) before it was answered."
    ::= { expensiveCallNotification 2 }

  bwLocationControlSPTable OBJECT-TYPE
    SYNTAX      SEQUENCE OF BwLocationControlSPEntry
    MAX-ACCESS  not-accessible
    STATUS      current
    DESCRIPTION 
        "Each row contains the service counters for the Location Control service for each service provider in the system"
    ::= { locationControl 1 }

  bwLocationControlSPEntry OBJECT-TYPE
    SYNTAX      BwLocationControlSPEntry
    MAX-ACCESS  not-accessible
    STATUS      current
    DESCRIPTION 
        "Each row contains the service counters for the Location Control service for each service provider in the system"
    INDEX       { bwLocationControlSPIndex }
    ::= { bwLocationControlSPTable 1 }

  BwLocationControlSPEntry ::= SEQUENCE {
    bwLocationControlSPIndex                Unsigned32,
    bwLocationControlSPID                   DisplayString,
    bwLocationControlSPActivationSuccess    Counter32,
    bwLocationControlSPDeactivationSuccess  Counter32
  }

  bwLocationControlSPIndex OBJECT-TYPE
    SYNTAX      Unsigned32
    MAX-ACCESS  read-only
    STATUS      current
    DESCRIPTION 
        "This column represents the index of the Service Provider in the system."
    ::= { bwLocationControlSPEntry 1 }

  bwLocationControlSPID OBJECT-TYPE
    SYNTAX      DisplayString
    MAX-ACCESS  read-only
    STATUS      current
    DESCRIPTION 
        "This string represents a Service Provider ID."
    ::= { bwLocationControlSPEntry 2 }

  bwLocationControlSPActivationSuccess OBJECT-TYPE
    SYNTAX      Counter32
    MAX-ACCESS  read-write
    STATUS      current
    DESCRIPTION 
        "This is the number of times a user activates an alternate or BroadWorks Anywhere location using the Location Control feature.  There is one instance of this counter for each service provider defined in the system."
    ::= { bwLocationControlSPEntry 3 }

  bwLocationControlSPDeactivationSuccess OBJECT-TYPE
    SYNTAX      Counter32
    MAX-ACCESS  read-write
    STATUS      current
    DESCRIPTION 
        "This is the number of times a user deactivates an alternate or BroadWorks Anywhere location using the Location Control feature.  There is one instance of this counter for each service provider defined in the system."
    ::= { bwLocationControlSPEntry 4 }

  bwLocationControlGroupTable OBJECT-TYPE
    SYNTAX      SEQUENCE OF BwLocationControlGroupEntry
    MAX-ACCESS  not-accessible
    STATUS      current
    DESCRIPTION 
        "Each row contains the service counters for the Location Control service for each group in the system"
    ::= { locationControl 2 }

  bwLocationControlGroupEntry OBJECT-TYPE
    SYNTAX      BwLocationControlGroupEntry
    MAX-ACCESS  not-accessible
    STATUS      current
    DESCRIPTION 
        "Each row contains the service counters for the Location Control service for each group in the system"
    INDEX       { bwLocationControlGroupIndex }
    ::= { bwLocationControlGroupTable 1 }

  BwLocationControlGroupEntry ::= SEQUENCE {
    bwLocationControlGroupIndex                 Unsigned32,
    bwLocationControlGroupID                    DisplayString,
    bwLocationControlGroupActivationSuccess     Counter32,
    bwLocationControlGroupDeactivationSuccess   Counter32
  }

  bwLocationControlGroupIndex OBJECT-TYPE
    SYNTAX      Unsigned32
    MAX-ACCESS  read-only
    STATUS      current
    DESCRIPTION 
        "This column represents the index of the Group in the system."
    ::= { bwLocationControlGroupEntry 1 }

  bwLocationControlGroupID OBJECT-TYPE
    SYNTAX      DisplayString
    MAX-ACCESS  read-only
    STATUS      current
    DESCRIPTION 
        "This string represents a Group ID."
    ::= { bwLocationControlGroupEntry 2 }

  bwLocationControlGroupActivationSuccess OBJECT-TYPE
    SYNTAX      Counter32
    MAX-ACCESS  read-write
    STATUS      current
    DESCRIPTION 
        "This is the number of times a user activates an alternate or BroadWorks Anywhere location using the Location Control feature.  There is one instance of this counter for each group defined in the system."
    ::= { bwLocationControlGroupEntry 3 }

  bwLocationControlGroupDeactivationSuccess OBJECT-TYPE
    SYNTAX      Counter32
    MAX-ACCESS  read-write
    STATUS      current
    DESCRIPTION 
        "This is the number of times a user deactivates an alternate or BroadWorks Anywhere location using the Location Control feature.  There is one instance of this counter for each group defined in the system."
    ::= { bwLocationControlGroupEntry 4 }

  bwLocationControlActivationSuccess OBJECT-TYPE
    SYNTAX      Counter32
    MAX-ACCESS  read-write
    STATUS      current
    DESCRIPTION 
        "This is the number of times a user activates an alternate or BroadWorks Anywhere location using the Location Control feature."
    ::= { locationControl 3 }

  bwLocationControlDeactivationSuccess OBJECT-TYPE
    SYNTAX      Counter32
    MAX-ACCESS  read-write
    STATUS      current
    DESCRIPTION 
        "This is the number of times a user deactivates an alternate or BroadWorks Anywhere location using the Location Control feature."
    ::= { locationControl 4 }

  bwCallRetrieveSPTable OBJECT-TYPE
    SYNTAX      SEQUENCE OF BwCallRetrieveSPEntry
    MAX-ACCESS  not-accessible
    STATUS      current
    DESCRIPTION 
        "Each row contains the service counters for the Call Retrieve service for each service provider in the system"
    ::= { callRetrieve 1 }

  bwCallRetrieveSPEntry OBJECT-TYPE
    SYNTAX      BwCallRetrieveSPEntry
    MAX-ACCESS  not-accessible
    STATUS      current
    DESCRIPTION 
        "Each row contains the service counters for the Call Retrieve service for each service provider in the system"
    INDEX       { bwCallRetrieveSPIndex }
    ::= { bwCallRetrieveSPTable 1 }

  BwCallRetrieveSPEntry ::= SEQUENCE {
    bwCallRetrieveSPIndex       Unsigned32,
    bwCallRetrieveSPID          DisplayString,
    bwCallRetrieveSPSuccess     Counter32
  }

  bwCallRetrieveSPIndex OBJECT-TYPE
    SYNTAX      Unsigned32
    MAX-ACCESS  read-only
    STATUS      current
    DESCRIPTION 
        "This column represents the index of the Service Provider in the system."
    ::= { bwCallRetrieveSPEntry 1 }

  bwCallRetrieveSPID OBJECT-TYPE
    SYNTAX      DisplayString
    MAX-ACCESS  read-only
    STATUS      current
    DESCRIPTION 
        "This string represents a Service Provider ID."
    ::= { bwCallRetrieveSPEntry 2 }

  bwCallRetrieveSPSuccess OBJECT-TYPE
    SYNTAX      Counter32
    MAX-ACCESS  read-write
    STATUS      current
    DESCRIPTION 
        "The number of times a user successfully retrieves a call using the Call Retrieve feature.  There is one instance of this counter for each service provider defined in the system."
    ::= { bwCallRetrieveSPEntry 3 }

  bwCallRetrieveGroupTable OBJECT-TYPE
    SYNTAX      SEQUENCE OF BwCallRetrieveGroupEntry
    MAX-ACCESS  not-accessible
    STATUS      current
    DESCRIPTION 
        "Each row contains the service counters for the Call Retrieve service for each group in the system"
    ::= { callRetrieve 2 }

  bwCallRetrieveGroupEntry OBJECT-TYPE
    SYNTAX      BwCallRetrieveGroupEntry
    MAX-ACCESS  not-accessible
    STATUS      current
    DESCRIPTION 
        "Each row contains the service counters for the Call Retrieve service for each service provider in the system"
    INDEX       { bwCallRetrieveGroupIndex }
    ::= { bwCallRetrieveGroupTable 1 }

  BwCallRetrieveGroupEntry ::= SEQUENCE {
    bwCallRetrieveGroupIndex    Unsigned32,
    bwCallRetrieveGroupID       DisplayString,
    bwCallRetrieveGroupSuccess  Counter32
  }

  bwCallRetrieveGroupIndex OBJECT-TYPE
    SYNTAX      Unsigned32
    MAX-ACCESS  read-only
    STATUS      current
    DESCRIPTION 
        "This column represents the index of the Group in the system."
    ::= { bwCallRetrieveGroupEntry 1 }

  bwCallRetrieveGroupID OBJECT-TYPE
    SYNTAX      DisplayString
    MAX-ACCESS  read-only
    STATUS      current
    DESCRIPTION 
        "This string represents a Group ID."
    ::= { bwCallRetrieveGroupEntry 2 }

  bwCallRetrieveGroupSuccess OBJECT-TYPE
    SYNTAX      Counter32
    MAX-ACCESS  read-write
    STATUS      current
    DESCRIPTION 
        "The number of times a user successfully retrieves a call using the Call Retrieve feature.  There is one instance of this counter for each group defined in the system."
    ::= { bwCallRetrieveGroupEntry 3 }

  bwCallRetrieveSuccess OBJECT-TYPE
    SYNTAX      Counter32
    MAX-ACCESS  read-write
    STATUS      current
    DESCRIPTION 
        "This is the number of times a user successfully retrieves a call using the Call Retrieve feature."
    ::= { callRetrieve 3 }

  bwBroadWorksAnywhereSPTable OBJECT-TYPE
    SYNTAX      SEQUENCE OF BwBroadWorksAnywhereSPEntry
    MAX-ACCESS  not-accessible
    STATUS      current
    DESCRIPTION 
        "Each row contains the service counters for the BroadWorks Anywhere service for each service provider in the system"
    ::= { broadworksAnywhere 1 }

  bwBroadWorksAnywhereSPEntry OBJECT-TYPE
    SYNTAX      BwBroadWorksAnywhereSPEntry
    MAX-ACCESS  not-accessible
    STATUS      current
    DESCRIPTION 
        "Each row contains the service counters for the BroadWorks Anywhere service for each service provider in the system"
    INDEX       { bwBroadWorksAnywhereSPIndex }
    ::= { bwBroadWorksAnywhereSPTable 1 }

  BwBroadWorksAnywhereSPEntry ::= SEQUENCE {
    bwBroadWorksAnywhereSPIndex     Unsigned32,
    bwBroadWorksAnywhereSPID        DisplayString,
    bwBASPCallOriginations          Counter32,
    bwBASPCallTerminations          Counter32
  }

  bwBroadWorksAnywhereSPIndex OBJECT-TYPE
    SYNTAX      Unsigned32
    MAX-ACCESS  read-only
    STATUS      current
    DESCRIPTION 
        "This column represents the index of the Service Provider in the system."
    ::= { bwBroadWorksAnywhereSPEntry 1 }

  bwBroadWorksAnywhereSPID OBJECT-TYPE
    SYNTAX      DisplayString
    MAX-ACCESS  read-only
    STATUS      current
    DESCRIPTION 
        "This string represents a Service Provider ID."
    ::= { bwBroadWorksAnywhereSPEntry 2 }

  bwBASPCallOriginations OBJECT-TYPE
    SYNTAX      Counter32
    MAX-ACCESS  read-write
    STATUS      current
    DESCRIPTION 
        "This is the number of times a user originates a call through the BroadWorks Anywhere Portal. There is one instance of this counter for each service provider or enterprise defined in the system."
    ::= { bwBroadWorksAnywhereSPEntry 3 }

  bwBASPCallTerminations OBJECT-TYPE
    SYNTAX      Counter32
    MAX-ACCESS  read-write
    STATUS      current
    DESCRIPTION 
        "This is the number of times a call leg is extended to a BroadWorks Anywhere location. There is one instance of this counter for each service provider or enterprise defined in the system."
    ::= { bwBroadWorksAnywhereSPEntry 4 }

  bwBroadWorksAnywhereGroupTable OBJECT-TYPE
    SYNTAX      SEQUENCE OF BwBroadWorksAnywhereGroupEntry
    MAX-ACCESS  not-accessible
    STATUS      current
    DESCRIPTION 
        "Each row contains the service counters for the BroadWorks Anywhere service for each group in the system"
    ::= { broadworksAnywhere 2 }

  bwBroadWorksAnywhereGroupEntry OBJECT-TYPE
    SYNTAX      BwBroadWorksAnywhereGroupEntry
    MAX-ACCESS  not-accessible
    STATUS      current
    DESCRIPTION 
        "Each row contains the service counters for the BroadWorks Anywhere service for each service provider in the system"
    INDEX       { bwBroadWorksAnywhereGroupIndex }
    ::= { bwBroadWorksAnywhereGroupTable 1 }

  BwBroadWorksAnywhereGroupEntry ::= SEQUENCE {
    bwBroadWorksAnywhereGroupIndex  Unsigned32,
    bwBroadWorksAnywhereGroupID     DisplayString,
    bwBAGroupCallOriginations       Counter32,
    bwBAGroupCallTerminations       Counter32
  }

  bwBroadWorksAnywhereGroupIndex OBJECT-TYPE
    SYNTAX      Unsigned32
    MAX-ACCESS  read-only
    STATUS      current
    DESCRIPTION 
        "This column represents the index of the Group in the system."
    ::= { bwBroadWorksAnywhereGroupEntry 1 }

  bwBroadWorksAnywhereGroupID OBJECT-TYPE
    SYNTAX      DisplayString
    MAX-ACCESS  read-only
    STATUS      current
    DESCRIPTION 
        "This string represents a Group ID."
    ::= { bwBroadWorksAnywhereGroupEntry 2 }

  bwBAGroupCallOriginations OBJECT-TYPE
    SYNTAX      Counter32
    MAX-ACCESS  read-write
    STATUS      current
    DESCRIPTION 
        "This is the number of times a user originates a call through the BroadWorks Anywhere Portal. There is one instance of this counter for each group defined in the system."
    ::= { bwBroadWorksAnywhereGroupEntry 3 }

  bwBAGroupCallTerminations OBJECT-TYPE
    SYNTAX      Counter32
    MAX-ACCESS  read-write
    STATUS      current
    DESCRIPTION 
        "This is the number of times a call leg is extended to a BroadWorks Anywhere location. There is one instance of this counter for each group defined in the system."
    ::= { bwBroadWorksAnywhereGroupEntry 4 }

  bwBACallOriginations OBJECT-TYPE
    SYNTAX      Counter32
    MAX-ACCESS  read-write
    STATUS      current
    DESCRIPTION 
        "This is the number of times a user originates a call through the BroadWorks Anywhere Portal."
    ::= { broadworksAnywhere 3 }

  bwBACallTerminations OBJECT-TYPE
    SYNTAX      Counter32
    MAX-ACCESS  read-write
    STATUS      current
    DESCRIPTION 
        "This is the number of times a call leg is extended to a BroadWorks Anywhere location. "
    ::= { broadworksAnywhere 4 }

  bwZoneCallingRestrictionsRedirectionBlocked OBJECT-TYPE
    SYNTAX      Counter32
    MAX-ACCESS  read-write
    STATUS      current
    DESCRIPTION 
        "This is the number of times a redirection (transfer or forward) is blocked because of Zone Calling Restrictions.  This can be a redirection by any forwarding feature, such as a call forwarding destination, a Remote Office or BroadWorks Anywhere destination, a Simultaneous Ring location, Call Center agent, etc, that would have caused a toll bypass situation had it not been blocked."
    ::= { zoneCallingRestrictions 1 }

  bwZoneCallingRestrictionsConferenceBlocked OBJECT-TYPE
    SYNTAX      Counter32
    MAX-ACCESS  read-write
    STATUS      current
    DESCRIPTION 
        "This is the number of times a conference is blocked, or a conference participant is prevented from being added to a conference, because of Zone Calling Restrictions."
    ::= { zoneCallingRestrictions 2 }

  bwZoneCallingRestrictionsRoamingBlocked OBJECT-TYPE
    SYNTAX      Counter32
    MAX-ACCESS  read-write
    STATUS      current
    DESCRIPTION 
        "This is the number of times a roaming origination, termination, or registration is blocked, because of Zone Calling Restrictions."
    ::= { zoneCallingRestrictions 3 }

  bwZoneCallingRestrictionsSPTable OBJECT-TYPE
    SYNTAX      SEQUENCE OF BwZoneCallingRestrictionsSPEntry
    MAX-ACCESS  not-accessible
    STATUS      current
    DESCRIPTION 
        "Each row contains the service counters for the Zone Calling Restrictions service for each service provider in the system"
    ::= { zoneCallingRestrictions 4 }

  bwZoneCallingRestrictionsSPEntry OBJECT-TYPE
    SYNTAX      BwZoneCallingRestrictionsSPEntry
    MAX-ACCESS  not-accessible
    STATUS      current
    DESCRIPTION 
        "Each row contains the service counters for the Zone Calling Restriction service for each service provider in the system"
    INDEX       { bwZoneCallingRestrictionsSPIndex }
    ::= { bwZoneCallingRestrictionsSPTable 1 }

  BwZoneCallingRestrictionsSPEntry ::= SEQUENCE {
    bwZoneCallingRestrictionsSPIndex              Unsigned32,
    bwZoneCallingRestrictionsSPID                 DisplayString,
    bwZoneCallingRestrictionsSPRedirectionBlocked Counter32,
    bwZoneCallingRestrictionsSPConferenceBlocked  Counter32,
    bwZoneCallingRestrictionsSPRoamingBlocked     Counter32
  }

  bwZoneCallingRestrictionsSPIndex OBJECT-TYPE
    SYNTAX      Unsigned32
    MAX-ACCESS  read-only
    STATUS      current
    DESCRIPTION 
        "This column represents the index of the Service Provider in the system."
    ::= { bwZoneCallingRestrictionsSPEntry 1 }

  bwZoneCallingRestrictionsSPID OBJECT-TYPE
    SYNTAX      DisplayString
    MAX-ACCESS  read-only
    STATUS      current
    DESCRIPTION 
        "This string represents a Service Provider ID."
    ::= { bwZoneCallingRestrictionsSPEntry 2 }

  bwZoneCallingRestrictionsSPRedirectionBlocked OBJECT-TYPE
    SYNTAX      Counter32
    MAX-ACCESS  read-write
    STATUS      current
    DESCRIPTION 
        "This is the number of times a redirection (transfer or forward) is blocked because of Zone Calling Restrictions.  This can be a redirection by any feature, such as a call forwarding destination, a Remote Office or BroadWorks Anywhere destination, a Simultaneous Ring location, Call Center agent, etc, that would have caused a toll bypass situation had it not been blocked. There is one instance of this counter for each service provider or enterprise defined in the system."
    ::= { bwZoneCallingRestrictionsSPEntry 3 }

  bwZoneCallingRestrictionsSPConferenceBlocked OBJECT-TYPE
    SYNTAX      Counter32
    MAX-ACCESS  read-write
    STATUS      current
    DESCRIPTION 
        "This is the number of times a conference is blocked, or a conference participant is prevented from being added to a conference, because of Zone Calling Restrictions. There is one instance of this counter for each service provider or enterprise defined in the system."
    ::= { bwZoneCallingRestrictionsSPEntry 4 }

  bwZoneCallingRestrictionsSPRoamingBlocked OBJECT-TYPE
    SYNTAX      Counter32
    MAX-ACCESS  read-write
    STATUS      current
    DESCRIPTION 
        "This is the number of times a roaming origination, termination, or registration is blocked, because of Zone Calling Restrictions. There is one instance of this counter for each service provider or enterprise defined in the system."
    ::= { bwZoneCallingRestrictionsSPEntry 5 }

  bwZoneCallingRestrictionsGroupTable OBJECT-TYPE
    SYNTAX      SEQUENCE OF BwZoneCallingRestrictionsGroupEntry
    MAX-ACCESS  not-accessible
    STATUS      current
    DESCRIPTION 
        "Each row contains the service counters for the Zone Calling Restrictions service for each group in the system"
    ::= { zoneCallingRestrictions 5 }

  bwZoneCallingRestrictionsGroupEntry OBJECT-TYPE
    SYNTAX      BwZoneCallingRestrictionsGroupEntry
    MAX-ACCESS  not-accessible
    STATUS      current
    DESCRIPTION 
        "Each row contains the service counters for the Zone Calling Restriction service for each group in the system"
    INDEX       { bwZoneCallingRestrictionsGroupIndex }
    ::= { bwZoneCallingRestrictionsGroupTable 1 }

  BwZoneCallingRestrictionsGroupEntry ::= SEQUENCE {
    bwZoneCallingRestrictionsGroupIndex                 Unsigned32,
    bwZoneCallingRestrictionsGroupID                    DisplayString,
    bwZoneCallingRestrictionsGroupRedirectionBlocked    Counter32,
    bwZoneCallingRestrictionsGroupConferenceBlocked     Counter32,
    bwZoneCallingRestrictionsGroupRoamingBlocked        Counter32
  }

  bwZoneCallingRestrictionsGroupIndex OBJECT-TYPE
    SYNTAX      Unsigned32
    MAX-ACCESS  read-only
    STATUS      current
    DESCRIPTION 
        "This column represents the index of the Group in the system."
    ::= { bwZoneCallingRestrictionsGroupEntry 1 }

  bwZoneCallingRestrictionsGroupID OBJECT-TYPE
    SYNTAX      DisplayString
    MAX-ACCESS  read-only
    STATUS      current
    DESCRIPTION 
        "This string represents a Group ID."
    ::= { bwZoneCallingRestrictionsGroupEntry 2 }

  bwZoneCallingRestrictionsGroupRedirectionBlocked OBJECT-TYPE
    SYNTAX      Counter32
    MAX-ACCESS  read-write
    STATUS      current
    DESCRIPTION 
        "This is the number of times a redirection (transfer or forward) is blocked because of Zone Calling Restrictions.  This can be a redirection by any feature, such as a call forwarding destination, a Remote Office or BroadWorks Anywhere destination, a Simultaneous Ring location, Call Center agent, etc, that would have caused a toll bypass situation had it not been blocked. There is one instance of this counter for each group defined in the system."
    ::= { bwZoneCallingRestrictionsGroupEntry 3 }

  bwZoneCallingRestrictionsGroupConferenceBlocked OBJECT-TYPE
    SYNTAX      Counter32
    MAX-ACCESS  read-write
    STATUS      current
    DESCRIPTION 
        "This is the number of times a conference is blocked, or a conference participant is prevented from being added to a conference, because of Zone Calling Restrictions. There is one instance of this counter for each group defined in the system."
    ::= { bwZoneCallingRestrictionsGroupEntry 4 }

  bwZoneCallingRestrictionsGroupRoamingBlocked OBJECT-TYPE
    SYNTAX      Counter32
    MAX-ACCESS  read-write
    STATUS      current
    DESCRIPTION 
        "This is the number of times a roaming origination, termination, or registration is blocked, because of Zone Calling Restrictions. There is one instance of this counter for each group defined in the system."
    ::= { bwZoneCallingRestrictionsGroupEntry 5 }

  bwCommunicationBarringBlockedTreatment OBJECT-TYPE
    SYNTAX      Counter32
    MAX-ACCESS  read-write
    STATUS      current
    DESCRIPTION 
        "This is the number of times a call is blocked by the Communication Barring service with an action of Block or Treatment."
    ::= { communicationBarring 1 }

  bwCommunicationBarringBlockedTransfer OBJECT-TYPE
    SYNTAX      Counter32
    MAX-ACCESS  read-write
    STATUS      current
    DESCRIPTION 
        "This is the number of times a call is blocked by the Communication Barring service with an action of Transfer."
    ::= { communicationBarring 2 }

  bwCommunicationBarringPromptedPIN OBJECT-TYPE
    SYNTAX      Counter32
    MAX-ACCESS  read-write
    STATUS      current
    DESCRIPTION 
        "This is the number of times a subscriber is prompted for a PIN by the Communication Barring service."
    ::= { communicationBarring 3 }

  bwCommunicationBarringFailedPIN OBJECT-TYPE
    SYNTAX      Counter32
    MAX-ACCESS  read-write
    STATUS      current
    DESCRIPTION 
        "This is the number of times a subscriber fails to enter a valid PIN required by the Communication Barring service."
    ::= { communicationBarring 4 }

  bwCommunicationBarringSPTable OBJECT-TYPE
    SYNTAX      SEQUENCE OF BwCommunicationBarringSPEntry
    MAX-ACCESS  not-accessible
    STATUS      current
    DESCRIPTION 
        "Each row contains the service counters for the Communication Barring service for each service provider in the system"
    ::= { communicationBarring 5 }

  bwCommunicationBarringSPEntry OBJECT-TYPE
    SYNTAX      BwCommunicationBarringSPEntry
    MAX-ACCESS  not-accessible
    STATUS      current
    DESCRIPTION 
        "Each row contains the service counters for the Communication Barring service for each service provider in the system"
    INDEX       { bwCommunicationBarringSPIndex }
    ::= { bwCommunicationBarringSPTable 1 }

  BwCommunicationBarringSPEntry ::= SEQUENCE {
    bwCommunicationBarringSPIndex                   Unsigned32,
    bwCommunicationBarringSPID                      DisplayString,
    bwCommunicationBarringSPBlockedTreatment        Counter32,
    bwCommunicationBarringSPBlockedTransfer         Counter32,
    bwCommunicationBarringSPPromptedPIN             Counter32,
    bwCommunicationBarringSPFailedPIN               Counter32,
    bwCommunicationBarringSPCallDurationExceeded    Counter32,
    bwCommunicationBarringSPPhoneActivations        Counter32,
    bwCommunicationBarringSPPhoneDeactivations      Counter32,
    bwCommunicationBarringSPPhoneQueries            Counter32,
    bwCommunicationBarringSPErroneousPinAttempts    Counter32,
    bwCommunicationBarringSPLockouts                Counter32
  }

  bwCommunicationBarringSPIndex OBJECT-TYPE
    SYNTAX      Unsigned32
    MAX-ACCESS  read-only
    STATUS      current
    DESCRIPTION 
        "This column represents the index of the Service Provider in the system."
    ::= { bwCommunicationBarringSPEntry 1 }

  bwCommunicationBarringSPID OBJECT-TYPE
    SYNTAX      DisplayString
    MAX-ACCESS  read-only
    STATUS      current
    DESCRIPTION 
        "This string represents a Service Provider ID."
    ::= { bwCommunicationBarringSPEntry 2 }

  bwCommunicationBarringSPBlockedTreatment OBJECT-TYPE
    SYNTAX      Counter32
    MAX-ACCESS  read-write
    STATUS      current
    DESCRIPTION 
        "This is the number of times a call is blocked by the Communication Barring service with an action of Block or Treatment.  There is one instance of this counter for each service provider or enterprise defined in the system."
    ::= { bwCommunicationBarringSPEntry 3 }

  bwCommunicationBarringSPBlockedTransfer OBJECT-TYPE
    SYNTAX      Counter32
    MAX-ACCESS  read-write
    STATUS      current
    DESCRIPTION 
        "This is the number of times a call is blocked by the Communication Barring service with an action of Transfer.  There is one instance of this counter for each service provider or enterprise defined in the system."
    ::= { bwCommunicationBarringSPEntry 4 }

  bwCommunicationBarringSPPromptedPIN OBJECT-TYPE
    SYNTAX      Counter32
    MAX-ACCESS  read-write
    STATUS      current
    DESCRIPTION 
        "This is the number of times a subscriber is prompted for a PIN by the Communication Barring service.  There is one instance of this counter for each service provider or enterprise defined in the system."
    ::= { bwCommunicationBarringSPEntry 5 }

  bwCommunicationBarringSPFailedPIN OBJECT-TYPE
    SYNTAX      Counter32
    MAX-ACCESS  read-write
    STATUS      current
    DESCRIPTION 
        "This is the number of times a subscriber fails to enter a valid PIN required by the Communication Barring service.  There is one instance of this counter for each service provider or enterprise defined in the system."
    ::= { bwCommunicationBarringSPEntry 6 }

  bwCommunicationBarringSPCallDurationExceeded OBJECT-TYPE
    SYNTAX      Counter32
    MAX-ACCESS  read-write
    STATUS      current
    DESCRIPTION 
        "This is the number of times the call duration exceeds the maximum allowed duration specified by the Allow Timed or Authorization Code Timed action of Communication Barring service.  There is one instance of this counter for each service provider or enterprise defined in the system."
    ::= { bwCommunicationBarringSPEntry 7 }

  bwCommunicationBarringSPPhoneActivations  OBJECT-TYPE
    SYNTAX      Counter32
    MAX-ACCESS  read-write
    STATUS      current
    DESCRIPTION
        "This is the number of times the Communication Barring User-Control service is activated with a FAC.  There is one instance of this counter for each service provider or enterprise defined in the system."
    ::= { bwCommunicationBarringSPEntry 8 }

  bwCommunicationBarringSPPhoneDeactivations  OBJECT-TYPE
    SYNTAX      Counter32
    MAX-ACCESS  read-write
    STATUS      current
    DESCRIPTION
        "This is the number of times the Communication Barring User-Control service is deactivated with a FAC.  There is one instance of this counter for each service provider or enterprise defined in the system."
    ::= { bwCommunicationBarringSPEntry 9 }

  bwCommunicationBarringSPPhoneQueries  OBJECT-TYPE
    SYNTAX      Counter32
    MAX-ACCESS  read-write
    STATUS      current
    DESCRIPTION
        "This is the number of times the Communication Barring User-Control service status is queried with a FAC.  There is one instance of this counter for each service provider or enterprise defined in the system."
    ::= { bwCommunicationBarringSPEntry 10 }

  bwCommunicationBarringSPErroneousPinAttempts  OBJECT-TYPE
    SYNTAX      Counter32
    MAX-ACCESS  read-write
    STATUS      current
    DESCRIPTION
        "This is the number of times an attempt to activate or deactivate the Communication Barring User-Control service is made with an invalid PIN code or without a PIN.  There is one instance of this counter for each service provider or enterprise defined in the system."
    ::= { bwCommunicationBarringSPEntry 11 }

  bwCommunicationBarringSPLockouts  OBJECT-TYPE
    SYNTAX      Counter32
    MAX-ACCESS  read-write
    STATUS      current
    DESCRIPTION
        "This is the number of times a user is locked out of the activation and deactivation FAC access to the Communication Barring User-Control service.  There is one instance of this counter for each service provider or enterprise defined in the system."
    ::= { bwCommunicationBarringSPEntry 12 }

  bwCommunicationBarringGroupTable OBJECT-TYPE
    SYNTAX      SEQUENCE OF BwCommunicationBarringGroupEntry
    MAX-ACCESS  not-accessible
    STATUS      current
    DESCRIPTION 
        "Each row contains the service counters for the Communication Barring service for each group in the system"
    ::= { communicationBarring 6 }

  bwCommunicationBarringGroupEntry OBJECT-TYPE
    SYNTAX      BwCommunicationBarringGroupEntry
    MAX-ACCESS  not-accessible
    STATUS      current
    DESCRIPTION 
        "Each row contains the service counters for the Communication Barring service for each group in the system"
    INDEX       { bwCommunicationBarringGroupIndex }
    ::= { bwCommunicationBarringGroupTable 1 }

  BwCommunicationBarringGroupEntry ::= SEQUENCE {
    bwCommunicationBarringGroupIndex                    Unsigned32,
    bwCommunicationBarringGroupID                       DisplayString,
    bwCommunicationBarringGroupBlockedTreatment         Counter32,
    bwCommunicationBarringGroupBlockedTransfer          Counter32,
    bwCommunicationBarringGroupPromptedPIN              Counter32,
    bwCommunicationBarringGroupFailedPIN                Counter32,
    bwCommunicationBarringGroupCallDurationExceeded     Counter32,
    bwCommunicationBarringGroupPhoneActivations         Counter32,
    bwCommunicationBarringGroupPhoneDeactivations       Counter32,
    bwCommunicationBarringGroupPhoneQueries             Counter32,
    bwCommunicationBarringGroupErroneousPinAttempts     Counter32,
    bwCommunicationBarringGroupLockouts                 Counter32
  }

  bwCommunicationBarringGroupIndex OBJECT-TYPE
    SYNTAX      Unsigned32
    MAX-ACCESS  read-only
    STATUS      current
    DESCRIPTION 
        "This column represents the index of the Group in the system."
    ::= { bwCommunicationBarringGroupEntry 1 }

  bwCommunicationBarringGroupID OBJECT-TYPE
    SYNTAX      DisplayString
    MAX-ACCESS  read-only
    STATUS      current
    DESCRIPTION 
        "This string represents a Group ID."
    ::= { bwCommunicationBarringGroupEntry 2 }

  bwCommunicationBarringGroupBlockedTreatment OBJECT-TYPE
    SYNTAX      Counter32
    MAX-ACCESS  read-write
    STATUS      current
    DESCRIPTION 
        "This is the number of times a call is blocked by the Communication Barring service with an action of Block or Treatment.  There is one instance of this counter for each group defined in the system."
    ::= { bwCommunicationBarringGroupEntry 3 }

  bwCommunicationBarringGroupBlockedTransfer OBJECT-TYPE
    SYNTAX      Counter32
    MAX-ACCESS  read-write
    STATUS      current
    DESCRIPTION 
        "This is the number of times a call is blocked by the Communication Barring service with an action of Transfer.  There is one instance of this counter for each group defined in the system."
    ::= { bwCommunicationBarringGroupEntry 4 }

  bwCommunicationBarringGroupPromptedPIN OBJECT-TYPE
    SYNTAX      Counter32
    MAX-ACCESS  read-write
    STATUS      current
    DESCRIPTION 
        "This is the number of times a subscriber is prompted for a PIN by the Communication Barring service.  There is one instance of this counter for each group defined in the system."
    ::= { bwCommunicationBarringGroupEntry 5 }

  bwCommunicationBarringGroupFailedPIN OBJECT-TYPE
    SYNTAX      Counter32
    MAX-ACCESS  read-write
    STATUS      current
    DESCRIPTION 
        "This is the number of times a subscriber fails to enter a valid PIN required by the Communication Barring service.  There is one instance of this counter for each group defined in the system."
    ::= { bwCommunicationBarringGroupEntry 6 }

  bwCommunicationBarringGroupCallDurationExceeded OBJECT-TYPE
    SYNTAX      Counter32
    MAX-ACCESS  read-write
    STATUS      current
    DESCRIPTION 
        "This is the number of times the call duration exceeds the maximum allowed duration specified by the Allow Timed or Authorization Code Timed action of Communication Barring service.  There is one instance of this counter for each group defined in the system."
    ::= { bwCommunicationBarringGroupEntry 7 }

  bwCommunicationBarringCallDurationExceeded OBJECT-TYPE
    SYNTAX      Counter32
    MAX-ACCESS  read-write
    STATUS      current
    DESCRIPTION 
        "This is the number of times the call duration exceeds the maximum allowed duration specified by the Allow Timed or Authorization Code Timed action of Communication Barring service."
    ::= { communicationBarring 7 }

  bwCommunicationBarringGroupPhoneActivations OBJECT-TYPE
    SYNTAX      Counter32
    MAX-ACCESS  read-write
    STATUS      current
    DESCRIPTION
        "This is the number of times the Communication Barring User-Control service is activated with a FAC.  There is one instance of this counter for each group defined in the system."
    ::= { bwCommunicationBarringGroupEntry 8 }

  bwCommunicationBarringGroupPhoneDeactivations OBJECT-TYPE
    SYNTAX      Counter32
    MAX-ACCESS  read-write
    STATUS      current
    DESCRIPTION
        "This is the number of times the Communication Barring User-Control service is deactivated with a FAC.  There is one instance of this counter for each group defined in the system."
    ::= { bwCommunicationBarringGroupEntry 9 }

  bwCommunicationBarringGroupPhoneQueries OBJECT-TYPE
    SYNTAX      Counter32
    MAX-ACCESS  read-write
    STATUS      current
    DESCRIPTION
        "This is the number of times the Communication Barring User-Control service status is queried with a FAC.  There is one instance of this counter for each group defined in the system."
    ::= { bwCommunicationBarringGroupEntry 10 }

  bwCommunicationBarringGroupErroneousPinAttempts OBJECT-TYPE
    SYNTAX      Counter32
    MAX-ACCESS  read-write
    STATUS      current
    DESCRIPTION
        "This is the number of times an attempt to activate or deactivate the Communication Barring User-Control service is made with an invalid PIN code or without a PIN.  There is one instance of this counter for each group defined in the system."
    ::= { bwCommunicationBarringGroupEntry 11 }

  bwCommunicationBarringGroupLockouts OBJECT-TYPE
    SYNTAX      Counter32
    MAX-ACCESS  read-write
    STATUS      current
    DESCRIPTION
        "This is the number of times a user is locked out of the activation and deactivation FAC access to the Communication Barring User-Control service.  There is one instance of this counter for each group defined in the system."
    ::= { bwCommunicationBarringGroupEntry 12 }

  bwCommunicationBarringPhoneActivations OBJECT-TYPE
    SYNTAX      Counter32
    MAX-ACCESS  read-write
    STATUS      current
    DESCRIPTION
        "This is the number of times the Communication Barring User-Control service is activated with a FAC."
    ::= { communicationBarring 8 }

  bwCommunicationBarringPhoneDeactivations OBJECT-TYPE
    SYNTAX      Counter32
    MAX-ACCESS  read-write
    STATUS      current
    DESCRIPTION
        "This is the number of times the Communication Barring User-Control service is deactivated with a FAC."
    ::= { communicationBarring 9 }

  bwCommunicationBarringPhoneQueries OBJECT-TYPE
    SYNTAX      Counter32
    MAX-ACCESS  read-write
    STATUS      current
    DESCRIPTION
        "This is the number of times the Communication Barring User-Control service status is queried with a FAC."
    ::= { communicationBarring 10 }

  bwCommunicationBarringErroneousPinAttempts OBJECT-TYPE
    SYNTAX      Counter32
    MAX-ACCESS  read-write
    STATUS      current
    DESCRIPTION
        "This is the number of times an attempt to activate or deactivate the Communication Barring User-Control service is made with an invalid PIN code or without a PIN."
    ::= { communicationBarring 11 }

  bwCommunicationBarringLockouts OBJECT-TYPE
    SYNTAX      Counter32
    MAX-ACCESS  read-write
    STATUS      current
    DESCRIPTION
        "This is the number of times a user is locked out of the activation and deactivation FAC access to the Communication Barring User-Control service."
    ::= { communicationBarring 12 }

  bwCallBridgeSuccess OBJECT-TYPE
    SYNTAX      Counter32
    MAX-ACCESS  read-write
    STATUS      current
    DESCRIPTION 
        "This is the number of times a user successfully initiates/join a SCA-Bridge using the Call Retrieve feature."
    ::= { callBridge 1 }

  bwCallBridgeSPTable OBJECT-TYPE
    SYNTAX      SEQUENCE OF BwCallBridgeSPEntry
    MAX-ACCESS  not-accessible
    STATUS      current
    DESCRIPTION 
        "Each row contains the service counters for the Call Bridge service for each service provider in the system"
    ::= { callBridge 2 }

  bwCallBridgeSPEntry OBJECT-TYPE
    SYNTAX      BwCallBridgeSPEntry
    MAX-ACCESS  not-accessible
    STATUS      current
    DESCRIPTION 
        "Each row contains the service counters for the Communication Barring service for each service provider in the system"
    INDEX       { bwCallBridgeSPIndex }
    ::= { bwCallBridgeSPTable 1 }

  BwCallBridgeSPEntry ::= SEQUENCE {
    bwCallBridgeSPIndex     Unsigned32,
    bwCallBridgeSPID        DisplayString,
    bwCallBridgeSPSuccess   Counter32
  }

  bwCallBridgeSPIndex OBJECT-TYPE
    SYNTAX      Unsigned32
    MAX-ACCESS  read-only
    STATUS      current
    DESCRIPTION 
        "This column represents the index of the Service Provider in the system."
    ::= { bwCallBridgeSPEntry 1 }

  bwCallBridgeSPID OBJECT-TYPE
    SYNTAX      DisplayString
    MAX-ACCESS  read-only
    STATUS      current
    DESCRIPTION 
        "This string represents a Service Provider ID."
    ::= { bwCallBridgeSPEntry 2 }

  bwCallBridgeSPSuccess OBJECT-TYPE
    SYNTAX      Counter32
    MAX-ACCESS  read-write
    STATUS      current
    DESCRIPTION 
        "The number of times a user successfully initiates/join a SCA-Bridge using the Call Bridge feature.  There is one instance of this counter for each service provider defined in the system."
    ::= { bwCallBridgeSPEntry 3 }

  bwCallBridgeGroupTable OBJECT-TYPE
    SYNTAX      SEQUENCE OF BwCallBridgeGroupEntry
    MAX-ACCESS  not-accessible
    STATUS      current
    DESCRIPTION 
        "Each row contains the service counters for the Call Bridge service for each group in the system"
    ::= { callBridge 3 }

  bwCallBridgeGroupEntry OBJECT-TYPE
    SYNTAX      BwCallBridgeGroupEntry
    MAX-ACCESS  not-accessible
    STATUS      current
    DESCRIPTION 
        "Each row contains the service counters for the Communication Barring service for each group in the system"
    INDEX       { bwCallBridgeGroupIndex }
    ::= { bwCallBridgeGroupTable 1 }

  BwCallBridgeGroupEntry ::= SEQUENCE {
    bwCallBridgeGroupIndex      Unsigned32,
    bwCallBridgeGroupID         DisplayString,
    bwCallBridgeGroupSuccess    Counter32
  }

  bwCallBridgeGroupIndex OBJECT-TYPE
    SYNTAX      Unsigned32
    MAX-ACCESS  read-only
    STATUS      current
    DESCRIPTION 
        "This column represents the index of the Group in the system."
    ::= { bwCallBridgeGroupEntry 1 }

  bwCallBridgeGroupID OBJECT-TYPE
    SYNTAX      DisplayString
    MAX-ACCESS  read-only
    STATUS      current
    DESCRIPTION 
        "This string represents a Group ID."
    ::= { bwCallBridgeGroupEntry 2 }

  bwCallBridgeGroupSuccess OBJECT-TYPE
    SYNTAX      Counter32
    MAX-ACCESS  read-write
    STATUS      current
    DESCRIPTION 
        "The number of times a user successfully initiates/join a SCA-Bridge using the Call Bridge feature.  There is one instance of this counter for each group defined in the system."
    ::= { bwCallBridgeGroupEntry 3 }

  bwDirectoryNumberHuntingIncomingCalls OBJECT-TYPE
    SYNTAX      Counter32
    MAX-ACCESS  read-write
    STATUS      current
    DESCRIPTION 
        "This is the number of calls to an agent belonging to Directory Number Hunting groups."
    ::= { directoryNumberHunting 1 }

  bwDirectoryNumberHuntingSPTable OBJECT-TYPE
    SYNTAX      SEQUENCE OF BwDirectoryNumberHuntingSPEntry
    MAX-ACCESS  not-accessible
    STATUS      current
    DESCRIPTION 
        "Each row contains the service counters for the Directory Number Hunting service for each service provider in the system"
    ::= { directoryNumberHunting 2 }

  bwDirectoryNumberHuntingSPEntry OBJECT-TYPE
    SYNTAX      BwDirectoryNumberHuntingSPEntry
    MAX-ACCESS  not-accessible
    STATUS      current
    DESCRIPTION 
        "Each row contains the service counters for the Directory Number Hunting service for each service provider in the system"
    INDEX       { bwDirectoryNumberHuntingSPIndex }
    ::= { bwDirectoryNumberHuntingSPTable 1 }

  BwDirectoryNumberHuntingSPEntry ::= SEQUENCE {
    bwDirectoryNumberHuntingSPIndex             Unsigned32,
    bwDirectoryNumberHuntingSPID                DisplayString,
    bwDirectoryNumberHuntingSPIncomingCalls     Counter32
  }

  bwDirectoryNumberHuntingSPIndex OBJECT-TYPE
    SYNTAX      Unsigned32
    MAX-ACCESS  read-only
    STATUS      current
    DESCRIPTION 
        "This column represents the index of the Service Provider in the system."
    ::= { bwDirectoryNumberHuntingSPEntry 1 }

  bwDirectoryNumberHuntingSPID OBJECT-TYPE
    SYNTAX      DisplayString
    MAX-ACCESS  read-only
    STATUS      current
    DESCRIPTION 
        "This string represents a Service Provider ID."
    ::= { bwDirectoryNumberHuntingSPEntry 2 }

  bwDirectoryNumberHuntingSPIncomingCalls OBJECT-TYPE
    SYNTAX      Counter32
    MAX-ACCESS  read-write
    STATUS      current
    DESCRIPTION 
        "This is the number of calls to an agent belonging to Directory Number Hunting groups.  There is one instance of this counter for each service provider defined in the system."
    ::= { bwDirectoryNumberHuntingSPEntry 3 }

  bwDirectoryNumberHuntingGroupTable OBJECT-TYPE
    SYNTAX      SEQUENCE OF BwDirectoryNumberHuntingGroupEntry
    MAX-ACCESS  not-accessible
    STATUS      current
    DESCRIPTION 
        "Each row contains the service counters for the Directory Number Hunting service for each group in the system"
    ::= { directoryNumberHunting 3 }

  bwDirectoryNumberHuntingGroupEntry OBJECT-TYPE
    SYNTAX      BwDirectoryNumberHuntingGroupEntry
    MAX-ACCESS  not-accessible
    STATUS      current
    DESCRIPTION 
        "Each row contains the service counters for the Directory Number Hunting service for each group in the system"
    INDEX       { bwDirectoryNumberHuntingGroupIndex }
    ::= { bwDirectoryNumberHuntingGroupTable 1 }

  BwDirectoryNumberHuntingGroupEntry ::= SEQUENCE {
    bwDirectoryNumberHuntingGroupIndex          Unsigned32,
    bwDirectoryNumberHuntingGroupID             DisplayString,
    bwDirectoryNumberHuntingGroupIncomingCalls  Counter32
  }

  bwDirectoryNumberHuntingGroupIndex OBJECT-TYPE
    SYNTAX      Unsigned32
    MAX-ACCESS  read-only
    STATUS      current
    DESCRIPTION 
        "This column represents the index of the Group in the system."
    ::= { bwDirectoryNumberHuntingGroupEntry 1 }

  bwDirectoryNumberHuntingGroupID OBJECT-TYPE
    SYNTAX      DisplayString
    MAX-ACCESS  read-only
    STATUS      current
    DESCRIPTION 
        "This string represents a Group ID."
    ::= { bwDirectoryNumberHuntingGroupEntry 2 }

  bwDirectoryNumberHuntingGroupIncomingCalls OBJECT-TYPE
    SYNTAX      Counter32
    MAX-ACCESS  read-write
    STATUS      current
    DESCRIPTION 
        "This is the number of calls to an agent belonging to Directory Number Hunting groups.  There is one instance of this counter for each group defined in the system."
    ::= { bwDirectoryNumberHuntingGroupEntry 3 }

  bwAoCIncompatibleTariff OBJECT-TYPE
    SYNTAX      Counter32
    MAX-ACCESS  read-write
    STATUS      current
    DESCRIPTION 
        "This is the number of times an active Advice of Charge service receives a tariff update that is incompatible with the current active charge."
    ::= { adviceOfCharge 1 }

  bwAoCIncompatibleAoC OBJECT-TYPE
    SYNTAX      Counter32
    MAX-ACCESS  read-write
    STATUS      current
    DESCRIPTION 
        "This is the number of times an active Advice of charge Service receives an incoming advice of charge body that is incompatible with the current active charge."
    ::= { adviceOfCharge 2 }

  bwAoCUnsupportedCostUnit OBJECT-TYPE
    SYNTAX      Counter32
    MAX-ACCESS  read-write
    STATUS      current
    DESCRIPTION 
        "This is the number of times an active Advice of Charge service receives an unsupported cost-unit in a Cost-Information CCA from the OCS."
    ::= { adviceOfCharge 3 }

  bwAoCActivation OBJECT-TYPE
    SYNTAX      Counter32
    MAX-ACCESS  read-write
    STATUS      current
    DESCRIPTION 
        "This is the number of times an active Advice of Charge service triggers an activation for the next call using the associated FAC."
    ::= { adviceOfCharge 4 }

  bwAoCSPTable OBJECT-TYPE
    SYNTAX      SEQUENCE OF BwAoCSPEntry
    MAX-ACCESS  not-accessible
    STATUS      current
    DESCRIPTION 
        "Each row contains the service counters for the Advice of Charge service for each service provider in the system"
    ::= { adviceOfCharge 5 }

  bwAoCSPEntry OBJECT-TYPE
    SYNTAX      BwAoCSPEntry
    MAX-ACCESS  not-accessible
    STATUS      current
    DESCRIPTION 
        "Each row contains the service counters for the Advice of Charge service for each service provider in the system"
    INDEX       { bwAoCSPIndex }
    ::= { bwAoCSPTable 1 }

  BwAoCSPEntry ::= SEQUENCE {
    bwAoCSPIndex                Unsigned32,
    bwAoCSPID                   DisplayString,
    bwAoCSPIncompatibleTariff   Counter32,
    bwAoCSPIncompatibleAoC      Counter32,
    bwAoCSPActivation           Counter32
  }

  bwAoCSPIndex OBJECT-TYPE
    SYNTAX      Unsigned32
    MAX-ACCESS  read-only
    STATUS      current
    DESCRIPTION 
        "This column represents the index of the Service Provider in the system."
    ::= { bwAoCSPEntry 1 }

  bwAoCSPID OBJECT-TYPE
    SYNTAX      DisplayString
    MAX-ACCESS  read-only
    STATUS      current
    DESCRIPTION 
        "This string represents a Service Provider ID."
    ::= { bwAoCSPEntry 2 }

  bwAoCSPIncompatibleTariff OBJECT-TYPE
    SYNTAX      Counter32
    MAX-ACCESS  read-write
    STATUS      current
    DESCRIPTION 
        "This is the number of times an active Advice of Charge service receives a tariff update that is incompatible with the current active charge within a service provider."
    ::= { bwAoCSPEntry 3 }

  bwAoCSPIncompatibleAoC OBJECT-TYPE
    SYNTAX      Counter32
    MAX-ACCESS  read-write
    STATUS      current
    DESCRIPTION 
        "This is the number of times an active Advice of Charge service receives an incoming advice of charge body that is incompatible with the current active charge within a service provider."
    ::= { bwAoCSPEntry 4 }

  bwAoCSPActivation OBJECT-TYPE
    SYNTAX      Counter32
    MAX-ACCESS  read-write
    STATUS      current
    DESCRIPTION 
        "This is the number of times an active Advice of Charge service triggers an activation for the next call using the associated FAC a service provider or enterprise."
    ::= { bwAoCSPEntry 5 }

  bwAoCGroupTable OBJECT-TYPE
    SYNTAX      SEQUENCE OF BwAoCGroupEntry
    MAX-ACCESS  not-accessible
    STATUS      current
    DESCRIPTION 
        "Each row contains the service counters for the Advice of Charge service for each group in the system"
    ::= { adviceOfCharge 6 }

  bwAoCGroupEntry OBJECT-TYPE
    SYNTAX      BwAoCGroupEntry
    MAX-ACCESS  not-accessible
    STATUS      current
    DESCRIPTION 
        "Each row contains the service counters for the Advice of Charge service for each group in the system"
    INDEX       { bwAoCGroupIndex }
    ::= { bwAoCGroupTable 1 }

  BwAoCGroupEntry ::= SEQUENCE {
    bwAoCGroupIndex                 Unsigned32,
    bwAoCGroupID                    DisplayString,
    bwAoCGroupIncompatibleTariff    Counter32,
    bwAoCGroupIncompatibleAoC       Counter32,
    bwAoCGroupActivation            Counter32
  }

  bwAoCGroupIndex OBJECT-TYPE
    SYNTAX      Unsigned32
    MAX-ACCESS  read-only
    STATUS      current
    DESCRIPTION 
        "This column represents the index of the Group in the system."
    ::= { bwAoCGroupEntry 1 }

  bwAoCGroupID OBJECT-TYPE
    SYNTAX      DisplayString
    MAX-ACCESS  read-only
    STATUS      current
    DESCRIPTION 
        "This string represents a Group ID."
    ::= { bwAoCGroupEntry 2 }

  bwAoCGroupIncompatibleTariff OBJECT-TYPE
    SYNTAX      Counter32
    MAX-ACCESS  read-write
    STATUS      current
    DESCRIPTION 
        "This is the number of times an active Advice of Charge service receives a tariff update that is incompatible with the current active charge within a group."
    ::= { bwAoCGroupEntry 3 }

  bwAoCGroupIncompatibleAoC OBJECT-TYPE
    SYNTAX      Counter32
    MAX-ACCESS  read-write
    STATUS      current
    DESCRIPTION 
        "This is the number of times an active Advice of Charge service receives an incoming advice of charge body that is incompatible with the current active charge within a group."
    ::= { bwAoCGroupEntry 4 }

  bwAoCGroupActivation OBJECT-TYPE
    SYNTAX      Counter32
    MAX-ACCESS  read-write
    STATUS      current
    DESCRIPTION 
        "This is the number of times an active Advice of Charge service triggers an activation for the next call using the associated FAC within a group."
    ::= { bwAoCGroupEntry 5 }

-- Service : Session Admission Control .....................................
  bwSACSessionCreationAttempts OBJECT-TYPE
    SYNTAX     Counter32
    MAX-ACCESS read-write
    STATUS     current
    DESCRIPTION 
        "This is the number of times a session creation, as defined by the SAC feature, is attempted in the system.  This counter is increased only if SAC restrictions apply to the session."
    ::= { sessionAdmissionControl 1 }

  bwSACSessionCreationExceeded OBJECT-TYPE
    SYNTAX     Counter32
    MAX-ACCESS read-write
    STATUS    current
    DESCRIPTION
        "This is the number of times a session, as defined by the SAC feature, is denied creation."
    ::= { sessionAdmissionControl 2 }

  bwSACSPTable OBJECT-TYPE
    SYNTAX      SEQUENCE OF BwSACSPEntry
    MAX-ACCESS  not-accessible
    STATUS      current
    DESCRIPTION 
        "Each row contains the service counters for the Session Admission Control service for each service provider in the system"
    ::= { sessionAdmissionControl 3 }

  bwSACGroupTable OBJECT-TYPE
    SYNTAX      SEQUENCE  OF  BwSACGroupEntry
    MAX-ACCESS  not-accessible
    STATUS      current
    DESCRIPTION "Each row contains the service counters for the Session Admission Control service for each group in the system"
    ::= { sessionAdmissionControl 4 }

  bwSACSessionGroupTable OBJECT-TYPE
    SYNTAX      SEQUENCE OF BwSACSessionGroupEntry
    MAX-ACCESS  not-accessible
    STATUS      current
    DESCRIPTION 
        "Each row contains the service counters for the Session Admission Control service for each SAC group in the system"
    ::= { sessionAdmissionControl 5 }

-- Service : Session Admission Control SP Table.....................................
  bwSACSPEntry OBJECT-TYPE
    SYNTAX      BwSACSPEntry
    MAX-ACCESS  not-accessible
    STATUS      current
    DESCRIPTION
        "Each row contains the service counters for the Session Admission Control service for each service provider in the system"
    INDEX { bwSACSPIndex }
    ::= { bwSACSPTable 1 }

  BwSACSPEntry ::= SEQUENCE {
    bwSACSPIndex                   Unsigned32,
    bwSACSPID                      DisplayString,
    bwSACSPSessionCreationAttempts Counter32,
    bwSACSPSessionCreationExceeded Counter32 }

 bwSACSPIndex OBJECT-TYPE
    SYNTAX       Unsigned32
    MAX-ACCESS   read-only
    STATUS       current
    DESCRIPTION  
        "This column represents the index of the Service Provider in the system."
    ::= { bwSACSPEntry 1 }

  bwSACSPID OBJECT-TYPE
    SYNTAX       DisplayString
    MAX-ACCESS   read-only
    STATUS       current
    DESCRIPTION  
        "This string represents a Service Provider ID."
    ::= { bwSACSPEntry 2 }

  bwSACSPSessionCreationAttempts OBJECT-TYPE
    SYNTAX     Counter32
    MAX-ACCESS read-write
    STATUS     current
    DESCRIPTION 
        "This is the number of times a session creation, as defined by the SAC feature, is attempted in the in the context of the service provider.  This counter is increased only if SAC restrictions apply to the session."
    ::= { bwSACSPEntry 3 }

  bwSACSPSessionCreationExceeded OBJECT-TYPE
    SYNTAX      Counter32
    MAX-ACCESS  read-write
    STATUS      current
    DESCRIPTION 
        "This is the number of times a session, as defined by the SAC feature, is denied creation inside the service provider."
    ::= { bwSACSPEntry 4 }

-- Service : Session Admission Control Group Table.....................................
  bwSACGroupEntry OBJECT-TYPE
    SYNTAX        BwSACGroupEntry
    MAX-ACCESS    not-accessible
    STATUS        current
    DESCRIPTION
        "Each row contains the service counters for the Session Admission Control service for each service provider in the system"
    INDEX { bwSACGroupIndex }
    ::= { bwSACGroupTable 1 }

  BwSACGroupEntry ::= SEQUENCE {
    bwSACGroupIndex                   Unsigned32,
    bwSACGroupID                      DisplayString,
    bwSACGroupSessionCreationAttempts Counter32,
    bwSACGroupSessionCreationExceeded Counter32 }

 bwSACGroupIndex OBJECT-TYPE
    SYNTAX       Unsigned32
    MAX-ACCESS   read-only
    STATUS       current
    DESCRIPTION  
        "This column represents the index of the Group in the system."
    ::= { bwSACGroupEntry 1 }

  bwSACGroupID OBJECT-TYPE
    SYNTAX       DisplayString
    MAX-ACCESS   read-only
    STATUS       current
    DESCRIPTION  
        "This string represents a Group ID."
    ::= { bwSACGroupEntry 2 }

  bwSACGroupSessionCreationAttempts OBJECT-TYPE
    SYNTAX      Counter32
    MAX-ACCESS  read-write
    STATUS      current
    DESCRIPTION 
        "This is the number of times a session creation, as defined by the SAC feature, is attempted in the in the context of the customer group.  This counter is increased only if SAC restrictions apply to the session."
    ::= { bwSACGroupEntry 3 }

  bwSACGroupSessionCreationExceeded OBJECT-TYPE
    SYNTAX      Counter32
    MAX-ACCESS  read-write
    STATUS      current
    DESCRIPTION 
        "This is the number of times a session, as defined by the SAC feature, is denied creation within the context of a group."
    ::= { bwSACGroupEntry 4 }

-- Service : Session Admission Control Session Group Table.....................................
  bwSACSessionGroupEntry  OBJECT-TYPE
    SYNTAX          BwSACSessionGroupEntry
    MAX-ACCESS      not-accessible
    STATUS          current
    DESCRIPTION
        "Each row contains the service counters for the Session Admission Control service for each service provider in the system"
    INDEX { bwSACSessionGroupIndex }
    ::= { bwSACSessionGroupTable 1 }

  BwSACSessionGroupEntry ::= SEQUENCE {
    bwSACSessionGroupIndex Unsigned32,
    bwSACSessionGroupID    DisplayString,
    bwSACSessionGroupSessionCreationAttempts Counter32,
    bwSACSessionGroupSessionCreationExceeded Counter32 }

 bwSACSessionGroupIndex  OBJECT-TYPE
    SYNTAX       Unsigned32
    MAX-ACCESS   read-only
    STATUS       current
    DESCRIPTION  
        "This column represents the index of the SAC Session Group in the system."
    ::= { bwSACSessionGroupEntry 1 }

  bwSACSessionGroupID OBJECT-TYPE
    SYNTAX       DisplayString
    MAX-ACCESS   read-only
    STATUS       current
    DESCRIPTION  
        "This string represents a SAC Session Group ID."
    ::= { bwSACSessionGroupEntry 2 }

  bwSACSessionGroupSessionCreationAttempts OBJECT-TYPE
    SYNTAX     Counter32
    MAX-ACCESS read-write
    STATUS     current
    DESCRIPTION 
        "This is the number of times a session creation, as defined by the SAC feature, is attempted in the in the context of the SAC Group.  This counter is increased only if SAC restrictions apply to the session."
    ::= { bwSACSessionGroupEntry 3 }

  bwSACSessionGroupSessionCreationExceeded OBJECT-TYPE
    SYNTAX      Counter32
    MAX-ACCESS  read-write
    STATUS      current
    DESCRIPTION 
        "This is the number of times a session, as defined by the SAC feature, is denied creation within the context of a given SAC group."
    ::= { bwSACSessionGroupEntry 4 }

-- Service : Virtual On Net .....................................
  bwVirtualOnNetOriginationAttempts OBJECT-TYPE
    SYNTAX     Counter32
    MAX-ACCESS read-write
    STATUS     current
    DESCRIPTION 
        "This is the number of call attempts made by a BroadWorks user or virtual user to a Virtual On-Net user."
    ::= { virtualOnNet 1 }

  bwVirtualOnNetTerminationAttempts OBJECT-TYPE
    SYNTAX     Counter32
    MAX-ACCESS read-write
    STATUS    current
    DESCRIPTION
        "This is the number of termination attempts to a BroadWorks user or virtual user from a Virtual On-Net user."
    ::= { virtualOnNet 2 }

  bwVirtualOnNetSPTable OBJECT-TYPE
    SYNTAX      SEQUENCE OF BwVirtualOnNetSPEntry
    MAX-ACCESS  not-accessible
    STATUS      current
    DESCRIPTION 
        "Each row contains the service counters for the Virtual On Net service for each service provider in the system"
    ::= { virtualOnNet 3 }

  bwVirtualOnNetGroupTable OBJECT-TYPE
    SYNTAX      SEQUENCE  OF  BwVirtualOnNetGroupEntry
    MAX-ACCESS  not-accessible
    STATUS      current
    DESCRIPTION "Each row contains the service counters for the Virtual On Net service for each group in the system"
    ::= { virtualOnNet 4 }

-- Service : Virtual On Net SP Table.....................................
  bwVirtualOnNetSPEntry OBJECT-TYPE
    SYNTAX      BwVirtualOnNetSPEntry
    MAX-ACCESS  not-accessible
    STATUS      current
    DESCRIPTION
        "Each row contains the service counters for the Virtual On Net service for each service provider in the system"
    INDEX { bwVirtualOnNetSPIndex }
    ::= { bwVirtualOnNetSPTable 1 }

  BwVirtualOnNetSPEntry ::= SEQUENCE {
    bwVirtualOnNetSPIndex               Unsigned32,
    bwVirtualOnNetSPID                  DisplayString,
    bwVirtualOnNetSPOriginationAttempts Counter32,
    bwVirtualOnNetSPTerminationAttempts Counter32 }

 bwVirtualOnNetSPIndex OBJECT-TYPE
    SYNTAX       Unsigned32
    MAX-ACCESS   read-only
    STATUS       current
    DESCRIPTION  
        "This column represents the index of the Service Provider in the system."
    ::= { bwVirtualOnNetSPEntry 1 }

  bwVirtualOnNetSPID OBJECT-TYPE
    SYNTAX       DisplayString
    MAX-ACCESS   read-only
    STATUS       current
    DESCRIPTION  
        "This string represents a Service Provider ID."
    ::= { bwVirtualOnNetSPEntry 2 }

  bwVirtualOnNetSPOriginationAttempts OBJECT-TYPE
    SYNTAX     Counter32
    MAX-ACCESS read-write
    STATUS     current
    DESCRIPTION 
        "This is the number of call attempts made by a BroadWorks user or virtual user to a Virtual On-Net user.  There is one instance of this counter for each service provider or enterprise defined in the system."
    ::= { bwVirtualOnNetSPEntry 3 }

  bwVirtualOnNetSPTerminationAttempts OBJECT-TYPE
    SYNTAX     Counter32
    MAX-ACCESS read-write
    STATUS     current
    DESCRIPTION 
        "This is the number of termination attempts to a BroadWorks user or virtual user from a Virtual On-Net user.  There is one instance of this counter for each service provider or enterprise defined in the system."
    ::= { bwVirtualOnNetSPEntry 4 }

-- Service : Virtual On Net Group Table.....................................
  bwVirtualOnNetGroupEntry OBJECT-TYPE
    SYNTAX      BwVirtualOnNetGroupEntry
    MAX-ACCESS  not-accessible
    STATUS      current
    DESCRIPTION
        "Each row contains the service counters for the Virtual On Net service for each service provider in the system"
    INDEX { bwVirtualOnNetGroupIndex }
    ::= { bwVirtualOnNetGroupTable 1 }

  BwVirtualOnNetGroupEntry ::= SEQUENCE {
    bwVirtualOnNetGroupIndex               Unsigned32,
    bwVirtualOnNetGroupID                  DisplayString,
    bwVirtualOnNetGroupOriginationAttempts Counter32,
    bwVirtualOnNetGroupTerminationAttempts Counter32 }

 bwVirtualOnNetGroupIndex OBJECT-TYPE
    SYNTAX       Unsigned32
    MAX-ACCESS   read-only
    STATUS       current
    DESCRIPTION  
        "This column represents the index of the Service Provider in the system."
    ::= { bwVirtualOnNetGroupEntry 1 }

  bwVirtualOnNetGroupID OBJECT-TYPE
    SYNTAX       DisplayString
    MAX-ACCESS   read-only
    STATUS       current
    DESCRIPTION  
        "This string represents a Service Provider ID."
    ::= { bwVirtualOnNetGroupEntry 2 }

  bwVirtualOnNetGroupOriginationAttempts OBJECT-TYPE
    SYNTAX     Counter32
    MAX-ACCESS read-write
    STATUS     current
    DESCRIPTION 
        "This is the number of call attempts made by a BroadWorks user or virtual user to a Virtual On-Net user.  There is one instance of this counter for each group defined in the system."
    ::= { bwVirtualOnNetGroupEntry 3 }

  bwVirtualOnNetGroupTerminationAttempts OBJECT-TYPE
    SYNTAX     Counter32
    MAX-ACCESS read-write
    STATUS     current
    DESCRIPTION 
        "This is the number of termination attempts to a BroadWorks user or virtual user from a Virtual On-Net user.  There is one instance of this counter for each group defined in the system."
    ::= { bwVirtualOnNetGroupEntry 4 }

-- Service : preAlertingAnnouncement  ...........................................

  bwPreAlertingAnnouncementNumAttempts OBJECT-TYPE
    SYNTAX     Counter32
    MAX-ACCESS read-write
    STATUS     current
    DESCRIPTION 
        "Number of Pre-Alerting Announcements attempted."
    ::= { preAlertingAnnouncement 1 }

  bwPreAlertingAnnouncementSPTable OBJECT-TYPE
    SYNTAX      SEQUENCE OF BwPreAlertingAnnouncementSPEntry
    MAX-ACCESS  not-accessible
    STATUS      current
    DESCRIPTION 
        "Each row contains the service counters for the pre alerting announcement service for each service provider in the system"
    ::= { preAlertingAnnouncement 2 }

  bwPreAlertingAnnouncementGroupTable OBJECT-TYPE
    SYNTAX      SEQUENCE  OF  BwPreAlertingAnnouncementGroupEntry
    MAX-ACCESS  not-accessible
    STATUS      current
    DESCRIPTION "Each row contains the service counters for the pre alerting announcement service for each group in the system"
    ::= { preAlertingAnnouncement 3 }

-- Service : preAlertingAnnouncement SP ...........................................

  bwPreAlertingAnnouncementSPEntry OBJECT-TYPE
    SYNTAX      BwPreAlertingAnnouncementSPEntry
    MAX-ACCESS  not-accessible
    STATUS      current
    DESCRIPTION
        "Each row contains the service counters for the pre alerting announcement service for each service provider in the system"
    INDEX { bwPreAlertingAnnouncementSPIndex }
    ::= { bwPreAlertingAnnouncementSPTable 1 }

  BwPreAlertingAnnouncementSPEntry ::= SEQUENCE {
    bwPreAlertingAnnouncementSPIndex       Unsigned32,
    bwPreAlertingAnnouncementSPID          DisplayString,
    bwPreAlertingAnnouncementSPNumAttempts Counter32}

 bwPreAlertingAnnouncementSPIndex OBJECT-TYPE
    SYNTAX       Unsigned32
    MAX-ACCESS   read-only
    STATUS       current
    DESCRIPTION  
        "This column represents the index of the Service Provider in the system."
    ::= { bwPreAlertingAnnouncementSPEntry 1 }

  bwPreAlertingAnnouncementSPID OBJECT-TYPE
    SYNTAX       DisplayString
    MAX-ACCESS   read-only
    STATUS       current
    DESCRIPTION  
        "This string represents a Service Provider ID."
    ::= { bwPreAlertingAnnouncementSPEntry 2 }

  bwPreAlertingAnnouncementSPNumAttempts OBJECT-TYPE
    SYNTAX     Counter32
    MAX-ACCESS read-write
    STATUS     current
    DESCRIPTION 
        "Number of Pre-Alerting Announcements for users in a given service provider."
    ::= { bwPreAlertingAnnouncementSPEntry 3 }

-- Service : preAlertingAnnouncement Group ...........................................

  bwPreAlertingAnnouncementGroupEntry OBJECT-TYPE
    SYNTAX      BwPreAlertingAnnouncementGroupEntry
    MAX-ACCESS  not-accessible
    STATUS      current
    DESCRIPTION
        "Each row contains the service counters for the pre alerting announcement service for each group in the system"
    INDEX { bwPreAlertingAnnouncementGroupIndex }
    ::= { bwPreAlertingAnnouncementGroupTable 1 }

  BwPreAlertingAnnouncementGroupEntry ::= SEQUENCE {
    bwPreAlertingAnnouncementGroupIndex          Unsigned32,
    bwPreAlertingAnnouncementGroupID             DisplayString,
    bwPreAlertingAnnouncementGroupNumAttempts Counter32 }

 bwPreAlertingAnnouncementGroupIndex OBJECT-TYPE
    SYNTAX       Unsigned32
    MAX-ACCESS   read-only
    STATUS       current
    DESCRIPTION  
        "This column represents the index of the group in the system."
    ::= { bwPreAlertingAnnouncementGroupEntry 1 }

  bwPreAlertingAnnouncementGroupID OBJECT-TYPE
    SYNTAX       DisplayString
    MAX-ACCESS   read-only
    STATUS       current
    DESCRIPTION  
        "This string represents a group ID."
    ::= { bwPreAlertingAnnouncementGroupEntry 2 }

  bwPreAlertingAnnouncementGroupNumAttempts OBJECT-TYPE
    SYNTAX     Counter32
    MAX-ACCESS read-write
    STATUS     current
    DESCRIPTION 
        "Number of Pre-Alerting Announcements for user in a given group."
    ::= { bwPreAlertingAnnouncementGroupEntry 3 }

-- Service : locationCallingRestrictions  ...........................................

  bwLocationCallingRestrictionsOfficeZoneOriginations OBJECT-TYPE
    SYNTAX      Counter32
    MAX-ACCESS  read-write
    STATUS      current
    DESCRIPTION 
        "Counts the number of calls originated by subscribers from within their office zone."
    ::= { locationCallingRestrictions 1 }

  bwLocationCallingRestrictionsOfficeZoneTerminations OBJECT-TYPE
    SYNTAX      Counter32
    MAX-ACCESS  read-write
    STATUS      current
    DESCRIPTION 
        "Counts the number of calls received by subscribers from within their office zone."
    ::= { locationCallingRestrictions 2 }

  bwLocationCallingRestrictionsPrimaryZoneOriginations OBJECT-TYPE
    SYNTAX      Counter32
    MAX-ACCESS  read-write
    STATUS      current
    DESCRIPTION 
        "Counts the number of calls originated by subscribers from within their primary zone."
    ::= { locationCallingRestrictions 3 }

  bwLocationCallingRestrictionsPrimaryZoneTerminations OBJECT-TYPE
    SYNTAX      Counter32
    MAX-ACCESS  read-write
    STATUS      current
    DESCRIPTION 
        "Counts the number of calls received by subscribers from within their primary zone."
    ::= { locationCallingRestrictions 4 }

  bwLocationCallingRestrictionsRoamingOriginations OBJECT-TYPE
    SYNTAX      Counter32
    MAX-ACCESS  read-write
    STATUS      current
    DESCRIPTION 
        "Counts the number of calls originated by subscribers when they are roaming outside their home network."
    ::= { locationCallingRestrictions 5 }

  bwLocationCallingRestrictionsRoamingTerminations OBJECT-TYPE
    SYNTAX      Counter32
    MAX-ACCESS  read-write
    STATUS      current
    DESCRIPTION 
        "Counts the number of calls received by subscribers when they are roaming outside their home network."
    ::= { locationCallingRestrictions 6 }

  bwLocationCallingRestrictionsSPTable OBJECT-TYPE
    SYNTAX      SEQUENCE OF BwLocationCallingRestrictionsSPEntry
    MAX-ACCESS  not-accessible
    STATUS      current
    DESCRIPTION 
        "Each row contains the service counters for the location calling restrictions service for each service provider in the system"
    ::= { locationCallingRestrictions 7 }

-- Service : locationCallingRestrictions  SP ...........................................

  bwLocationCallingRestrictionsSPEntry OBJECT-TYPE
    SYNTAX      BwLocationCallingRestrictionsSPEntry
    MAX-ACCESS  not-accessible
    STATUS      current
    DESCRIPTION
        "Each row contains the service counters for the pre alerting announcement service for each service provider in the system"
    INDEX { bwLocationCallingRestrictionsSPIndex }
    ::= { bwLocationCallingRestrictionsSPTable 1 }

  BwLocationCallingRestrictionsSPEntry ::= SEQUENCE {
    bwLocationCallingRestrictionsSPIndex                   Unsigned32,
    bwLocationCallingRestrictionsSPID                      DisplayString,
    bwLocationCallingRestrictionsSPOfficeZoneOriginations  Counter32,
    bwLocationCallingRestrictionsSPOfficeZoneTerminations  Counter32,
    bwLocationCallingRestrictionsSPPrimaryZoneOriginations Counter32,
    bwLocationCallingRestrictionsSPPrimaryZoneTerminations Counter32,
    bwLocationCallingRestrictionsSPRoamingOriginations     Counter32,
    bwLocationCallingRestrictionsSPRoamingTerminations     Counter32 }

 bwLocationCallingRestrictionsSPIndex OBJECT-TYPE
    SYNTAX       Unsigned32
    MAX-ACCESS   read-only
    STATUS       current
    DESCRIPTION  
        "This column represents the index of the Service Provider in the system."
    ::= { bwLocationCallingRestrictionsSPEntry 1 }

  bwLocationCallingRestrictionsSPID OBJECT-TYPE
    SYNTAX       DisplayString
    MAX-ACCESS   read-only
    STATUS       current
    DESCRIPTION  
        "This string represents a Service Provider ID."
    ::= { bwLocationCallingRestrictionsSPEntry 2 }

  bwLocationCallingRestrictionsSPOfficeZoneOriginations OBJECT-TYPE
    SYNTAX     Counter32
    MAX-ACCESS read-write
    STATUS     current
    DESCRIPTION 
        "Counts the number of calls originated by subscribers from within their office zone.  There is on instance of this counter for each service provider defined in the system."
    ::= { bwLocationCallingRestrictionsSPEntry 3 }

  bwLocationCallingRestrictionsSPOfficeZoneTerminations OBJECT-TYPE
    SYNTAX     Counter32
    MAX-ACCESS read-write
    STATUS     current
    DESCRIPTION 
        "Counts the number of calls received by subscribers from within their office zone.  There is on instance of this counter for each service provider defined in the system."
    ::= { bwLocationCallingRestrictionsSPEntry 4 }

  bwLocationCallingRestrictionsSPPrimaryZoneOriginations OBJECT-TYPE
    SYNTAX     Counter32
    MAX-ACCESS read-write
    STATUS     current
    DESCRIPTION 
        "Counts the number of calls originated by subscribers from within their primary zone.  There is on instance of this counter for each service provider defined in the system."
    ::= { bwLocationCallingRestrictionsSPEntry 5 }

  bwLocationCallingRestrictionsSPPrimaryZoneTerminations OBJECT-TYPE
    SYNTAX     Counter32
    MAX-ACCESS read-write
    STATUS     current
    DESCRIPTION 
        "Counts the number of calls received by subscribers from within their primary zone.  There is on instance of this counter for each service provider defined in the system."
    ::= { bwLocationCallingRestrictionsSPEntry 6 }

  bwLocationCallingRestrictionsSPRoamingOriginations OBJECT-TYPE
    SYNTAX     Counter32
    MAX-ACCESS read-write
    STATUS     current
    DESCRIPTION 
        "Counts the number of calls originated by subscribers when they are roaming outside their home network.  There is on instance of this counter for each service provider defined in the system."
    ::= { bwLocationCallingRestrictionsSPEntry 7 }

  bwLocationCallingRestrictionsSPRoamingTerminations OBJECT-TYPE
    SYNTAX     Counter32
    MAX-ACCESS read-write
    STATUS     current
    DESCRIPTION 
        "Counts the number of calls received by subscribers when they are roaming outside their home network.  There is on instance of this counter for each service provider defined in the system."
    ::= { bwLocationCallingRestrictionsSPEntry 8 }

-- Service : routePoint  ...........................................

  bwRoutePointNumInboundCalls OBJECT-TYPE
    SYNTAX      Counter32
    MAX-ACCESS  read-write
    STATUS      current
    DESCRIPTION 
        "This is the number of inbound calls received by a Route Point."
    ::= { routePoint 1 }

  bwRoutePointNumOutboundCalls OBJECT-TYPE
    SYNTAX      Counter32
    MAX-ACCESS  read-write
    STATUS      current
    DESCRIPTION 
        "This is the number of outbound calls made from a Route Point."
    ::= { routePoint 2 }

  bwRoutePointNumSizeOverflow OBJECT-TYPE
    SYNTAX      Counter32
    MAX-ACCESS  read-write
    STATUS      current
    DESCRIPTION 
        "This is the number of inbound calls to a Route Point that overflow based on the queue size."
    ::= { routePoint 3 }

  bwRoutePointNumTimeOverflow OBJECT-TYPE
    SYNTAX      Counter32
    MAX-ACCESS  read-write
    STATUS      current
    DESCRIPTION 
        "This is the number of inbound calls to a Route Point or outbound calls from a Route Point that overflow based on time."
    ::= { routePoint 4 }

  bwRoutePointNumBouncedCalls OBJECT-TYPE
    SYNTAX      Counter32
    MAX-ACCESS  read-write
    STATUS      current
    DESCRIPTION 
        "This is the number of Route Point calls (inbound and outbound) offered to an agent which are bounced."
    ::= { routePoint 5 }

  bwRoutePointNumNightServiceMessage OBJECT-TYPE
    SYNTAX      Counter32
    MAX-ACCESS  read-write
    STATUS      current
    DESCRIPTION 
        "This is the number of times that the Night Service message is played for an inbound call to a Route Point."
    ::= { routePoint 6 }

  bwRoutePointNumManualNightServiceMessage OBJECT-TYPE
    SYNTAX      Counter32
    MAX-ACCESS  read-write
    STATUS      current
    DESCRIPTION 
        "This is the number of times that the manual Night Service message is played for an inbound call to a Route Point."
    ::= { routePoint 7 }

  bwRoutePointNumHolidayServiceMessage OBJECT-TYPE
    SYNTAX      Counter32
    MAX-ACCESS  read-write
    STATUS      current
    DESCRIPTION 
        "This is the number of times that the Holiday Service message is played for an inbound call to a Route Point."
    ::= { routePoint 8 }

  bwRoutePointNumForcedForwardingMessage OBJECT-TYPE
    SYNTAX      Counter32
    MAX-ACCESS  read-write
    STATUS      current
    DESCRIPTION 
        "This is the number of times that the Forced Forwarding message is played for an inbound call to a Route Point."
    ::= { routePoint 9 }

  bwRoutePointNumOverflowMessage OBJECT-TYPE
    SYNTAX      Counter32
    MAX-ACCESS  read-write
    STATUS      current
    DESCRIPTION 
        "This is the number of times that the Overflow message is played for an inbound call to a Route Point."
    ::= { routePoint 10 }

  bwRoutePointNumExternalSystemFailure OBJECT-TYPE
    SYNTAX      Counter32
    MAX-ACCESS  read-write
    STATUS      current
    DESCRIPTION 
        "This is the number of time the Route Point transits from 'normal' state to 'failed' state."
    ::= { routePoint 11 }

  bwRoutePointNumCallsFailed OBJECT-TYPE
    SYNTAX      Counter32
    MAX-ACCESS  read-write
    STATUS      current
    DESCRIPTION 
        "This is the number of calls which have been marked as failed."
    ::= { routePoint 12 }

  bwRoutePointSPTable OBJECT-TYPE
    SYNTAX      SEQUENCE  OF  BwRoutePointSPEntry
    MAX-ACCESS  not-accessible
    STATUS      current
    DESCRIPTION "Each row contains the service counters for the route point service for each group in the system"
    ::= { routePoint 13 }

  bwRoutePointGroupTable OBJECT-TYPE
    SYNTAX      SEQUENCE  OF  BwRoutePointGroupEntry
    MAX-ACCESS  not-accessible
    STATUS      current
    DESCRIPTION "Each row contains the service counters for the route point service for each group in the system"
    ::= { routePoint 14 }

  bwRoutePointNumWhisperMessage OBJECT-TYPE
    SYNTAX      Counter32
    MAX-ACCESS  read-write
    STATUS      current
    DESCRIPTION 
        "This is the number of times that the whisper message is triggered to be played for a call to a Route Point."
    ::= { routePoint 15 }

  bwRoutePointNumSilenceMessage OBJECT-TYPE
    SYNTAX      Counter32
    MAX-ACCESS  read-write
    STATUS      current
    DESCRIPTION 
        "This is the number of times that the silence is triggered to be played for a call to a Route Point."
    ::= { routePoint 16 }

  bwRoutePointNumBusyMessage OBJECT-TYPE
    SYNTAX      Counter32
    MAX-ACCESS  read-write
    STATUS      current
    DESCRIPTION 
        "This is the number of times that the busy is triggered to be played for a call to a Route Point."
    ::= { routePoint 17 }

  bwRoutePointNumRingbackMessage OBJECT-TYPE
    SYNTAX      Counter32
    MAX-ACCESS  read-write
    STATUS      current
    DESCRIPTION 
        "This is the number of times that the ringback is triggered to be played for a call to a Route Point."
    ::= { routePoint 18 }

  bwRoutePointNumMusicMessage OBJECT-TYPE
    SYNTAX      Counter32
    MAX-ACCESS  read-write
    STATUS      current
    DESCRIPTION 
        "This is the number of times that the music on hold is triggered to be played for a call to a Route Point"
    ::= { routePoint 19 }

  bwRoutePointNumTreatmentMessage OBJECT-TYPE
    SYNTAX      Counter32
    MAX-ACCESS  read-write
    STATUS      current
    DESCRIPTION 
        "This is the number of times that the treatment is triggered to be played for a call to a Route Point."
    ::= { routePoint 20 }

-- Service : routePoint SP ...........................................
  bwRoutePointSPEntry OBJECT-TYPE
    SYNTAX      BwRoutePointSPEntry
    MAX-ACCESS  not-accessible
    STATUS      current
    DESCRIPTION
        "Each row contains the service counters for the route point service for each service provider in the system"
    INDEX { bwRoutePointSPIndex }
    ::= { bwRoutePointSPTable 1 }

  BwRoutePointSPEntry ::= SEQUENCE {
    bwRoutePointSPIndex                        Unsigned32,
    bwRoutePointSPID                           DisplayString,
    bwRoutePointSPNumInboundCalls              Counter32,
    bwRoutePointSPNumOutboundCalls             Counter32,
    bwRoutePointSPNumSizeOverflow              Counter32,
    bwRoutePointSPNumTimeOverflow              Counter32,
    bwRoutePointSPNumBouncedCalls              Counter32,
    bwRoutePointSPNumNightServiceMessage       Counter32,
    bwRoutePointSPNumManualNightServiceMessage Counter32,
    bwRoutePointSPNumHolidayServiceMessage     Counter32,
    bwRoutePointSPNumForcedForwardingMessage   Counter32,
    bwRoutePointSPNumOverflowMessage           Counter32,
    bwRoutePointSPNumExternalSystemFailure     Counter32,
    bwRoutePointSPNumCallsFailed               Counter32,
    bwRoutePointSPNumWhisperMessage            Counter32,
    bwRoutePointSPNumSilenceMessage            Counter32,
    bwRoutePointSPNumBusyMessage               Counter32,
    bwRoutePointSPNumRingbackMessage           Counter32,
    bwRoutePointSPNumMusicMessage              Counter32,
    bwRoutePointSPNumTreatmentMessage          Counter32 }

 bwRoutePointSPIndex OBJECT-TYPE
    SYNTAX       Unsigned32
    MAX-ACCESS   read-only
    STATUS       current
    DESCRIPTION  
        "This column represents the index of the Service Provider in the system."
    ::= { bwRoutePointSPEntry 1 }

  bwRoutePointSPID OBJECT-TYPE
    SYNTAX       DisplayString
    MAX-ACCESS   read-only
    STATUS       current
    DESCRIPTION  
        "This string represents a Service Provider ID."
    ::= { bwRoutePointSPEntry 2 }

  bwRoutePointSPNumInboundCalls OBJECT-TYPE
    SYNTAX     Counter32
    MAX-ACCESS read-write
    STATUS     current
    DESCRIPTION 
        "This is the number of inbound calls received by a Route Point.  There is one instance of this counter for each service provider or enterprise defined in the system."
    ::= { bwRoutePointSPEntry 3 }

  bwRoutePointSPNumOutboundCalls OBJECT-TYPE
    SYNTAX     Counter32
    MAX-ACCESS read-write
    STATUS     current
    DESCRIPTION 
        "This is the number of outbound calls made from a Route Point.  There is one instance of this counter for each service provider or enterprise defined in the system."
    ::= { bwRoutePointSPEntry 4 }

  bwRoutePointSPNumSizeOverflow OBJECT-TYPE
    SYNTAX     Counter32
    MAX-ACCESS read-write
    STATUS     current
    DESCRIPTION 
        "This is the number of inbound calls to a Route Point that overflow based on the queue size.  There is one instance of this counter for each service provider or enterprise defined in the system."
    ::= { bwRoutePointSPEntry 5 }

  bwRoutePointSPNumTimeOverflow OBJECT-TYPE
    SYNTAX     Counter32
    MAX-ACCESS read-write
    STATUS     current
    DESCRIPTION 
        "This is the number of inbound calls to a Route Point or outbound calls from a Route Point that overflow based on time.  There is one instance of this counter for each service provider or enterprise defined in the system."
    ::= { bwRoutePointSPEntry 6 }

  bwRoutePointSPNumBouncedCalls OBJECT-TYPE
    SYNTAX     Counter32
    MAX-ACCESS read-write
    STATUS     current
    DESCRIPTION 
        "This is the number of Route Point calls (inbound and outbound) offered to an agent which are bounced.  There is one instance of this counter for each service provider or enterprise defined in the system."
    ::= { bwRoutePointSPEntry 7 }

  bwRoutePointSPNumNightServiceMessage OBJECT-TYPE
    SYNTAX     Counter32
    MAX-ACCESS read-write
    STATUS     current
    DESCRIPTION 
        "This is the number of times that the Night Service message is played for an inbound call to a Route Point.  There is one instance of this counter for each service provider or enterprise defined in the system."
    ::= { bwRoutePointSPEntry 8 }

  bwRoutePointSPNumManualNightServiceMessage OBJECT-TYPE
    SYNTAX     Counter32
    MAX-ACCESS read-write
    STATUS     current
    DESCRIPTION 
        "This is the number of times that the manual Night Service message is played for an inbound call to a Route Point.  There is one instance of this counter for each service provider or enterprise defined in the system."
    ::= { bwRoutePointSPEntry 9 }

  bwRoutePointSPNumHolidayServiceMessage OBJECT-TYPE
    SYNTAX     Counter32
    MAX-ACCESS read-write
    STATUS     current
    DESCRIPTION 
        "This is the number of times that the Holiday Service message is played for an inbound call to a Route Point.  There is one instance of this counter for each service provider or enterprise defined in the system."
    ::= { bwRoutePointSPEntry 10 }

  bwRoutePointSPNumForcedForwardingMessage OBJECT-TYPE
    SYNTAX     Counter32
    MAX-ACCESS read-write
    STATUS     current
    DESCRIPTION 
        "This is the number of times that the Forced Forwarding message is played for an inbound call to a Route Point.  There is one instance of this counter for each service provider or enterprise defined in the system."
    ::= { bwRoutePointSPEntry 11 }

  bwRoutePointSPNumOverflowMessage OBJECT-TYPE
    SYNTAX     Counter32
    MAX-ACCESS read-write
    STATUS     current
    DESCRIPTION 
        "This is the number of times that the Overflow message is played for an inbound call to a Route Point.  There is one instance of this counter for each service provider or enterprise defined in the system."
    ::= { bwRoutePointSPEntry 12 }

  bwRoutePointSPNumExternalSystemFailure OBJECT-TYPE
    SYNTAX     Counter32
    MAX-ACCESS read-write
    STATUS     current
    DESCRIPTION 
        "This is the number of time the Route Point transits from 'normal' state to 'failed' state.  There is one instance of this counter for each service provider or enterprise defined in the system."
    ::= { bwRoutePointSPEntry 13 }

  bwRoutePointSPNumCallsFailed OBJECT-TYPE
    SYNTAX     Counter32
    MAX-ACCESS read-write
    STATUS     current
    DESCRIPTION 
        "This is the number of calls which have been marked as failed.  There is one instance of this counter for each service provider or enterprise defined in the system."
    ::= { bwRoutePointSPEntry 14 }

  bwRoutePointSPNumWhisperMessage OBJECT-TYPE
    SYNTAX     Counter32
    MAX-ACCESS read-write
    STATUS     current
    DESCRIPTION 
        "This is the number of times that the whisper message is triggered to be played to the agent of a route point.  There is one instance of this counter for each service provider defined in the system."
    ::= { bwRoutePointSPEntry 15 }

  bwRoutePointSPNumSilenceMessage OBJECT-TYPE
    SYNTAX     Counter32
    MAX-ACCESS read-write
    STATUS     current
    DESCRIPTION 
        "This is the number of times that the silence is triggered to be played for a call to a route point.  There is one instance of this counter for each service provider defined in the system."
    ::= { bwRoutePointSPEntry 16 }

  bwRoutePointSPNumBusyMessage OBJECT-TYPE
    SYNTAX     Counter32
    MAX-ACCESS read-write
    STATUS     current
    DESCRIPTION 
        "This is the number of times that the busy is triggered to be played for a call to a route point.  There is one instance of this counter for each service provider defined in the system."
    ::= { bwRoutePointSPEntry 17 }

  bwRoutePointSPNumRingbackMessage OBJECT-TYPE
    SYNTAX     Counter32
    MAX-ACCESS read-write
    STATUS     current
    DESCRIPTION 
        "This is the number of times that the ringback is triggered to be played for a call to a route point.  There is one instance of this counter for each service provider defined in the system."
    ::= { bwRoutePointSPEntry 18 }

  bwRoutePointSPNumMusicMessage OBJECT-TYPE
    SYNTAX     Counter32
    MAX-ACCESS read-write
    STATUS     current
    DESCRIPTION 
        "This is the number of times that the Music On Hold is triggered to be played for a call to a route point.  There is one instance of this counter for each service provider defined in the system."
    ::= { bwRoutePointSPEntry 19 }

  bwRoutePointSPNumTreatmentMessage OBJECT-TYPE
    SYNTAX     Counter32
    MAX-ACCESS read-write
    STATUS     current
    DESCRIPTION 
        "This is the number of times that the treatment is triggered to be played for a call to a route point.  There is one instance of this counter for each service provider defined in the system."
    ::= { bwRoutePointSPEntry 20 }

-- Service : routePoint Group ...........................................

  bwRoutePointGroupEntry OBJECT-TYPE
    SYNTAX      BwRoutePointGroupEntry
    MAX-ACCESS  not-accessible
    STATUS      current
    DESCRIPTION
        "Each row contains the service counters for the route point service for each group in the system"
    INDEX { bwRoutePointGroupIndex }
    ::= { bwRoutePointGroupTable 1 }

  BwRoutePointGroupEntry ::= SEQUENCE {
    bwRoutePointGroupIndex                        Unsigned32,
    bwRoutePointGroupID                           DisplayString,
    bwRoutePointGroupNumInboundCalls              Counter32,
    bwRoutePointGroupNumOutboundCalls             Counter32,
    bwRoutePointGroupNumSizeOverflow              Counter32,
    bwRoutePointGroupNumTimeOverflow              Counter32,
    bwRoutePointGroupNumBouncedCalls              Counter32,
    bwRoutePointGroupNumNightServiceMessage       Counter32,
    bwRoutePointGroupNumManualNightServiceMessage Counter32,
    bwRoutePointGroupNumHolidayServiceMessage     Counter32,
    bwRoutePointGroupNumForcedForwardingMessage   Counter32,
    bwRoutePointGroupNumOverflowMessage           Counter32,
    bwRoutePointGroupNumExternalSystemFailure     Counter32,
    bwRoutePointGroupNumCallsFailed               Counter32,
    bwRoutePointGroupNumWhisperMessage            Counter32, 
    bwRoutePointGroupNumSilenceMessage            Counter32,
    bwRoutePointGroupNumBusyMessage               Counter32,
    bwRoutePointGroupNumRingbackMessage           Counter32,
    bwRoutePointGroupNumMusicMessage              Counter32,
    bwRoutePointGroupNumTreatmentMessage          Counter32 }

 bwRoutePointGroupIndex OBJECT-TYPE
    SYNTAX       Unsigned32
    MAX-ACCESS   read-only
    STATUS       current
    DESCRIPTION  
        "This column represents the index of the group in the system."
    ::= { bwRoutePointGroupEntry 1 }

  bwRoutePointGroupID OBJECT-TYPE
    SYNTAX       DisplayString
    MAX-ACCESS   read-only
    STATUS       current
    DESCRIPTION  
        "This string represents a group ID."
    ::= { bwRoutePointGroupEntry 2 }

  bwRoutePointGroupNumInboundCalls OBJECT-TYPE
    SYNTAX     Counter32
    MAX-ACCESS read-write
    STATUS     current
    DESCRIPTION 
        "This is the number of inbound calls received by a Route Point.  There is one instance of this counter for each group defined in the system."
    ::= { bwRoutePointGroupEntry 3 }

  bwRoutePointGroupNumOutboundCalls OBJECT-TYPE
    SYNTAX     Counter32
    MAX-ACCESS read-write
    STATUS     current
    DESCRIPTION 
        "This is the number of outbound calls made from a Route Point.  There is one instance of this counter for each group defined in the system."
    ::= { bwRoutePointGroupEntry 4 }

  bwRoutePointGroupNumSizeOverflow OBJECT-TYPE
    SYNTAX     Counter32
    MAX-ACCESS read-write
    STATUS     current
    DESCRIPTION 
        "This is the number of inbound calls to a Route Point that overflow based on the queue size.  There is one instance of this counter for each group defined in the system."
    ::= { bwRoutePointGroupEntry 5 }

  bwRoutePointGroupNumTimeOverflow OBJECT-TYPE
    SYNTAX     Counter32
    MAX-ACCESS read-write
    STATUS     current
    DESCRIPTION 
        "This is the number of inbound calls to a Route Point or outbound calls from a Route Point that overflow based on time.  There is one instance of this counter for each group defined in the system."
    ::= { bwRoutePointGroupEntry 6 }

  bwRoutePointGroupNumBouncedCalls OBJECT-TYPE
    SYNTAX     Counter32
    MAX-ACCESS read-write
    STATUS     current
    DESCRIPTION 
        "This is the number of Route Point calls (inbound and outbound) offered to an agent which are bounced.  There is one instance of this counter for each group defined in the system."
    ::= { bwRoutePointGroupEntry 7 }

  bwRoutePointGroupNumNightServiceMessage OBJECT-TYPE
    SYNTAX     Counter32
    MAX-ACCESS read-write
    STATUS     current
    DESCRIPTION 
        "This is the number of times that the Night Service message is played for an inbound call to a Route Point.  There is one instance of this counter for each group defined in the system."
    ::= { bwRoutePointGroupEntry 8 }

  bwRoutePointGroupNumManualNightServiceMessage OBJECT-TYPE
    SYNTAX     Counter32
    MAX-ACCESS read-write
    STATUS     current
    DESCRIPTION 
        "This is the number of times that the manual Night Service message is played for an inbound call to a Route Point.  There is one instance of this counter for each group defined in the system."
    ::= { bwRoutePointGroupEntry 9 }

  bwRoutePointGroupNumHolidayServiceMessage OBJECT-TYPE
    SYNTAX     Counter32
    MAX-ACCESS read-write
    STATUS     current
    DESCRIPTION 
        "This is the number of times that the Holiday Service message is played for an inbound call to a Route Point.  There is one instance of this counter for each group defined in the system."
    ::= { bwRoutePointGroupEntry 10 }

  bwRoutePointGroupNumForcedForwardingMessage OBJECT-TYPE
    SYNTAX     Counter32
    MAX-ACCESS read-write
    STATUS     current
    DESCRIPTION 
        "This is the number of times that the Forced Forwarding message is played for an inbound call to a Route Point.  There is one instance of this counter for each group defined in the system."
    ::= { bwRoutePointGroupEntry 11 }

  bwRoutePointGroupNumOverflowMessage OBJECT-TYPE
    SYNTAX     Counter32
    MAX-ACCESS read-write
    STATUS     current
    DESCRIPTION 
        "This is the number of times that the Overflow message is played for an inbound call to a Route Point.  There is one instance of this counter for each group defined in the system."
    ::= { bwRoutePointGroupEntry 12 }

  bwRoutePointGroupNumExternalSystemFailure OBJECT-TYPE
    SYNTAX     Counter32
    MAX-ACCESS read-write
    STATUS     current
    DESCRIPTION 
        "This is the number of time the Route Point transits from 'normal' state to 'failed' state.  There is one instance of this counter for each group defined in the system."
    ::= { bwRoutePointGroupEntry 13 }

  bwRoutePointGroupNumCallsFailed OBJECT-TYPE
    SYNTAX     Counter32
    MAX-ACCESS read-write
    STATUS     current
    DESCRIPTION 
        "This is the number of calls which have been marked as failed.  There is one instance of this counter for each group defined in the system."
    ::= { bwRoutePointGroupEntry 14 }

  bwRoutePointGroupNumWhisperMessage OBJECT-TYPE
    SYNTAX     Counter32
    MAX-ACCESS read-write
    STATUS     current
    DESCRIPTION 
        "This is the number of times that the whisper message is triggered to be played to the agent of a route point.  There is one instance of this counter for each group defined in the system."
    ::= { bwRoutePointGroupEntry 15 }

  bwRoutePointGroupNumSilenceMessage OBJECT-TYPE
    SYNTAX     Counter32
    MAX-ACCESS read-write
    STATUS     current
    DESCRIPTION 
        "This is the number of times that the silence is triggered to be played for a call to a route point.  There is one instance of this counter for each group defined in the system."
    ::= { bwRoutePointGroupEntry 16 }

  bwRoutePointGroupNumBusyMessage OBJECT-TYPE
    SYNTAX     Counter32
    MAX-ACCESS read-write
    STATUS     current
    DESCRIPTION 
        "This is the number of times that the busy is triggered to be played for a call to a route point.  There is one instance of this counter for each group defined in the system."
    ::= { bwRoutePointGroupEntry 17 }

  bwRoutePointGroupNumRingbackMessage OBJECT-TYPE
    SYNTAX     Counter32
    MAX-ACCESS read-write
    STATUS     current
    DESCRIPTION 
        "This is the number of times that the ringback is triggered to be played for a call to a route point.  There is one instance of this counter for each group defined in the system."
    ::= { bwRoutePointGroupEntry 18 }

  bwRoutePointGroupNumMusicMessage OBJECT-TYPE
    SYNTAX     Counter32
    MAX-ACCESS read-write
    STATUS     current
    DESCRIPTION 
        "This is the number of times that the Music On Hold is triggered to be played for a call to a route point. There is one instance of this counter for each group defined in the system."
    ::= { bwRoutePointGroupEntry 19 }

  bwRoutePointGroupNumTreatmentMessage OBJECT-TYPE
    SYNTAX     Counter32
    MAX-ACCESS read-write
    STATUS     current
    DESCRIPTION 
        "This is the number of times that the treatment is triggered to be played for a call to a route point.  There is one instance of this counter for each group defined in the system."
    ::= { bwRoutePointGroupEntry 20 }

-- Service : groupPaging  ...........................................

  bwGroupPagingNumInvocations OBJECT-TYPE
    SYNTAX      Counter32
    MAX-ACCESS  read-write
    STATUS      current
    DESCRIPTION 
        "This is the number of times that a group page is initiated by an originator."
    ::= { groupPaging 1 }

  bwGroupPagingNumFailures OBJECT-TYPE
    SYNTAX      Counter32
    MAX-ACCESS  read-write
    STATUS      current
    DESCRIPTION 
        "This is the number of times that a group page initiated by an originator fails to be sent to the targets."
    ::= { groupPaging 2 }

  bwGroupPagingSPTable OBJECT-TYPE
    SYNTAX      SEQUENCE  OF  BwGroupPagingSPEntry
    MAX-ACCESS  not-accessible
    STATUS      current
    DESCRIPTION "Each row contains the service counters for the group paging service for each group in the system"
    ::= { groupPaging 3 }

  bwGroupPagingGroupTable OBJECT-TYPE
    SYNTAX      SEQUENCE  OF  BwGroupPagingGroupEntry
    MAX-ACCESS  not-accessible
    STATUS      current
    DESCRIPTION "Each row contains the service counters for the group paging service for each group in the system"
    ::= { groupPaging 4 }

-- Service : groupPaging SP ...........................................
  bwGroupPagingSPEntry OBJECT-TYPE
    SYNTAX      BwGroupPagingSPEntry
    MAX-ACCESS  not-accessible
    STATUS      current
    DESCRIPTION
        "Each row contains the service counters for the group paging service for each service provider in the system"
    INDEX { bwGroupPagingSPIndex }
    ::= { bwGroupPagingSPTable 1 }

  BwGroupPagingSPEntry ::= SEQUENCE {
    bwGroupPagingSPIndex                        Unsigned32,
    bwGroupPagingSPID                           DisplayString,
    bwGroupPagingSPNumInvocations               Counter32,
    bwGroupPagingSPNumFailures                  Counter32 }

 bwGroupPagingSPIndex OBJECT-TYPE
    SYNTAX       Unsigned32
    MAX-ACCESS   read-only
    STATUS       current
    DESCRIPTION  
        "This column represents the index of the Service Provider in the system."
    ::= { bwGroupPagingSPEntry 1 }

  bwGroupPagingSPID OBJECT-TYPE
    SYNTAX       DisplayString
    MAX-ACCESS   read-only
    STATUS       current
    DESCRIPTION  
        "This string represents a Service Provider ID."
    ::= { bwGroupPagingSPEntry 2 }

  bwGroupPagingSPNumInvocations OBJECT-TYPE
    SYNTAX     Counter32
    MAX-ACCESS read-write
    STATUS     current
    DESCRIPTION 
        "This is the number of times that a group page is initiated by an originator.  There is one instance of this counter for each service provider defined in the system."
    ::= { bwGroupPagingSPEntry 3 }

  bwGroupPagingSPNumFailures OBJECT-TYPE
    SYNTAX     Counter32
    MAX-ACCESS read-write
    STATUS     current
    DESCRIPTION 
        "This is the number of times that a group page initiated by an originator fails to be sent to the targets. There is one instance of this counter for each service provider defined in the system."
    ::= { bwGroupPagingSPEntry 4 }

-- Service : groupPaging Group ...........................................

  bwGroupPagingGroupEntry OBJECT-TYPE
    SYNTAX      BwGroupPagingGroupEntry
    MAX-ACCESS  not-accessible
    STATUS      current
    DESCRIPTION
        "Each row contains the service counters for the group Paging service for each group in the system"
    INDEX { bwGroupPagingGroupIndex }
    ::= { bwGroupPagingGroupTable 1 }

  BwGroupPagingGroupEntry ::= SEQUENCE {
    bwGroupPagingGroupIndex                        Unsigned32,
    bwGroupPagingGroupID                           DisplayString,
    bwGroupPagingGroupNumInvocations               Counter32,
    bwGroupPagingGroupNumFailures                  Counter32 }

 bwGroupPagingGroupIndex OBJECT-TYPE
    SYNTAX       Unsigned32
    MAX-ACCESS   read-only
    STATUS       current
    DESCRIPTION  
        "This column represents the index of the group in the system."
    ::= { bwGroupPagingGroupEntry 1 }

  bwGroupPagingGroupID OBJECT-TYPE
    SYNTAX       DisplayString
    MAX-ACCESS   read-only
    STATUS       current
    DESCRIPTION  
        "This string represents a group ID."
    ::= { bwGroupPagingGroupEntry 2 }

  bwGroupPagingGroupNumInvocations OBJECT-TYPE
    SYNTAX     Counter32
    MAX-ACCESS read-write
    STATUS     current
    DESCRIPTION 
        "This is the number of times that a group page is initiated by an originator. There is one instance of this counter for each group defined in the system."
    ::= { bwGroupPagingGroupEntry 3 }

  bwGroupPagingGroupNumFailures OBJECT-TYPE
    SYNTAX     Counter32
    MAX-ACCESS read-write
    STATUS     current
    DESCRIPTION 
        "This is the number of times that a group page initiated by an originator fails to be sent to the targets. There is one instance of this counter for each group defined in the system."
    ::= { bwGroupPagingGroupEntry 4 }

-- Service : meetmeConferencing  ...........................................

  bwMeetMeNumActiveConferences OBJECT-TYPE
    SYNTAX      Gauge32
    MAX-ACCESS  read-only
    STATUS      current
    DESCRIPTION
        "This is the number of conferences that are currently active."
    ::= { meetmeConferencing 1 }

  bwMeetMeTotalConferences OBJECT-TYPE
    SYNTAX      Counter32
    MAX-ACCESS  read-write
    STATUS      current
    DESCRIPTION
        "This is the total number of conferences that occurred on this server."
    ::= { meetmeConferencing 2 }

  bwMeetMeNumPortsInUse OBJECT-TYPE
    SYNTAX      Gauge32
    MAX-ACCESS  read-only
    STATUS      current
    DESCRIPTION
        "This is the number of conferences ports that are currently in use."
    ::= { meetmeConferencing 3 }

  bwMeetMeTotalParticipants OBJECT-TYPE
    SYNTAX      Counter32
    MAX-ACCESS  read-write
    STATUS      current
    DESCRIPTION
        "This is the total number of participants who joined a conference."
    ::= { meetmeConferencing 4 }

  bwMeetMeTotalConferenceDuration OBJECT-TYPE
    SYNTAX      Counter32
    MAX-ACCESS  read-write
    STATUS      current
    DESCRIPTION
        "This is the total duration of conferences (in seconds)."
    ::= { meetmeConferencing 5 }

  bwMeetMeNumJoinFailureLicensing OBJECT-TYPE
    SYNTAX      Counter32
    MAX-ACCESS  read-write
    STATUS      current
    DESCRIPTION
        "This counter is incremented whenever a participant tries to join a conference but fails because all licensed conference ports were already in use."
    ::= { meetmeConferencing 6 }

  bwMeetMeNumJoinFailureMaxBridgeCapacity OBJECT-TYPE
    SYNTAX      Counter32
    MAX-ACCESS  read-write
    STATUS      current
    DESCRIPTION
        "This is the total number of participants who could not join a conference because a maximum number of simultaneous ports were configured against a bridge and that limit was reached."
    ::= { meetmeConferencing 7 }

  bwMeetMeNumJoinFailureMediaServerBusy OBJECT-TYPE
    SYNTAX      Counter32
    MAX-ACCESS  read-write
    STATUS      current
    DESCRIPTION
        "This is the total number of participants who could not join a conference because all ports were busy on the Media Server."
    ::= { meetmeConferencing 8 }

  bwMeetMeNumJoinFailureInvalidConferenceId OBJECT-TYPE
    SYNTAX      Counter32
    MAX-ACCESS  read-write
    STATUS      current
    DESCRIPTION
        "This is the total number of participants who could not join a conference because an invalid conference ID was entered."
    ::= { meetmeConferencing 9 }

  bwMeetMeNumJoinFailureOthers OBJECT-TYPE
    SYNTAX      Counter32
    MAX-ACCESS  read-write
    STATUS      current
    DESCRIPTION
        "This is the total number of participants who could not join a conference due to other failures."
    ::= { meetmeConferencing 10 }

  bwMeetMeNumConferenceCreationFailure OBJECT-TYPE
    SYNTAX      Counter32
    MAX-ACCESS  read-write
    STATUS      current
    DESCRIPTION
        "This is the total number of conference failures."
    ::= { meetmeConferencing 11 }

  bwMeetMeNumOutdialFailure OBJECT-TYPE
    SYNTAX      Counter32
    MAX-ACCESS  read-write
    STATUS      current
    DESCRIPTION
        "This is the total number of conference outdial failures."
    ::= { meetmeConferencing 12 }

  bwMeetMeSPTable OBJECT-TYPE
    SYNTAX      SEQUENCE  OF  BwMeetMeSPEntry
    MAX-ACCESS  not-accessible
    STATUS      current
    DESCRIPTION "Each row contains the service counters for the Meet Me conferencing service for each group in the system"
    ::= { meetmeConferencing 13 }

  bwMeetMeGroupTable OBJECT-TYPE
    SYNTAX      SEQUENCE  OF  BwMeetMeGroupEntry
    MAX-ACCESS  not-accessible
    STATUS      current
    DESCRIPTION "Each row contains the service counters for the Meet Me Conferencing service for each group in the system"
    ::= { meetmeConferencing 14 }

-- Service : meetmeConferencing SP ...........................................

  bwMeetMeSPEntry OBJECT-TYPE
    SYNTAX      BwMeetMeSPEntry
    MAX-ACCESS  not-accessible
    STATUS      current
    DESCRIPTION
        "Each row contains the service counters for the Meet Me Conferencing service for each service provider in the system"
    INDEX { bwMeetMeSPIndex }
    ::= { bwMeetMeSPTable 1 }

  BwMeetMeSPEntry ::= SEQUENCE {
    bwMeetMeSPIndex                        Unsigned32,
    bwMeetMeSPID                           DisplayString,
    bwMeetMeSPNumActiveConferences         Gauge32,
    bwMeetMeSPNumPortsInUse                Gauge32 }

 bwMeetMeSPIndex OBJECT-TYPE
    SYNTAX       Unsigned32
    MAX-ACCESS   read-only
    STATUS       current
    DESCRIPTION  
        "This column represents the index of the Service Provider in the system."
    ::= { bwMeetMeSPEntry 1 }

  bwMeetMeSPID OBJECT-TYPE
    SYNTAX       DisplayString
    MAX-ACCESS   read-only
    STATUS       current
    DESCRIPTION  
        "This string represents a Service Provider ID."
    ::= { bwMeetMeSPEntry 2 }

 bwMeetMeSPNumActiveConferences OBJECT-TYPE
    SYNTAX       Gauge32
    MAX-ACCESS   read-only
    STATUS       current
    DESCRIPTION  
        "This is the number of conferences that are currently active."
    ::= { bwMeetMeSPEntry 3 }

 bwMeetMeSPNumPortsInUse OBJECT-TYPE
    SYNTAX       Gauge32
    MAX-ACCESS   read-only
    STATUS       current
    DESCRIPTION  
        "This is the number of conferences ports that are currently in use."
    ::= { bwMeetMeSPEntry 4 }

-- Service : meetmeConferencing Group ...........................................

  bwMeetMeGroupEntry OBJECT-TYPE
    SYNTAX      BwMeetMeGroupEntry
    MAX-ACCESS  not-accessible
    STATUS      current
    DESCRIPTION
        "Each row contains the service counters for the Meet Me Conferencing service for each service provider in the system"
    INDEX { bwMeetMeGroupIndex }
    ::= { bwMeetMeGroupTable 1 }

  BwMeetMeGroupEntry ::= SEQUENCE {
    bwMeetMeGroupIndex                        Unsigned32,
    bwMeetMeGroupID                           DisplayString,
    bwMeetMeGroupNumActiveConferences         Gauge32,
    bwMeetMeGroupNumPortsInUse                Gauge32 }

 bwMeetMeGroupIndex OBJECT-TYPE
    SYNTAX       Unsigned32
    MAX-ACCESS   read-only
    STATUS       current
    DESCRIPTION  
        "This column represents the index of the Service Provider in the system."
    ::= { bwMeetMeGroupEntry 1 }

  bwMeetMeGroupID OBJECT-TYPE
    SYNTAX       DisplayString
    MAX-ACCESS   read-only
    STATUS       current
    DESCRIPTION  
        "This string represents a Service Provider ID."
    ::= { bwMeetMeGroupEntry 2 }

 bwMeetMeGroupNumActiveConferences OBJECT-TYPE
    SYNTAX       Gauge32
    MAX-ACCESS   read-only
    STATUS       current
    DESCRIPTION  
        "This is the number of conferences that are currently active."
    ::= { bwMeetMeGroupEntry 3 }

 bwMeetMeGroupNumPortsInUse OBJECT-TYPE
    SYNTAX       Gauge32
    MAX-ACCESS   read-only
    STATUS       current
    DESCRIPTION  
        "This is the number of conferences ports that are currently in use."
    ::= { bwMeetMeGroupEntry 4 }

-- Service : shortMessageService  ...........................................

 bwShortMessageServiceOrigination OBJECT-TYPE
    SYNTAX      Counter32
    MAX-ACCESS  read-write
    STATUS      current
    DESCRIPTION
        "This is the number of times that a Short Message Service origination has been attempted by a BroadWorks subscriber."
    ::= { shortMessageService 1 }

 bwShortMessageServiceTermination OBJECT-TYPE
    SYNTAX      Counter32
    MAX-ACCESS  read-write
    STATUS      current
    DESCRIPTION
        "This is the number of times that a Short Message Service termination has been attempted to a BroadWorks subscriber."
    ::= { shortMessageService 2 }

  bwShortMessageServiceSPTable OBJECT-TYPE
    SYNTAX      SEQUENCE  OF  BwShortMessageServiceSPEntry
    MAX-ACCESS  not-accessible
    STATUS      current
    DESCRIPTION "Each row contains the service counters for the Short Message service for each service provider in the system"
    ::= { shortMessageService 3 }

  bwShortMessageServiceGroupTable OBJECT-TYPE
    SYNTAX      SEQUENCE  OF  BwShortMessageServiceGroupEntry
    MAX-ACCESS  not-accessible
    STATUS      current
    DESCRIPTION "Each row contains the service counters for the Short Message service for each group in the system"
    ::= { shortMessageService 4 }

-- Service : Short Message Service SP ...........................................

  bwShortMessageServiceSPEntry OBJECT-TYPE
    SYNTAX      BwShortMessageServiceSPEntry
    MAX-ACCESS  not-accessible
    STATUS      current
    DESCRIPTION
        "Each row contains the service counters for the Short Message service for each service provider in the system"
    INDEX { bwShortMessageServiceSPIndex }
    ::= { bwShortMessageServiceSPTable 1 }

  BwShortMessageServiceSPEntry ::= SEQUENCE {
    bwShortMessageServiceSPIndex       Unsigned32,
    bwShortMessageServiceSPID          DisplayString,
    bwShortMessageServiceSPOrigination Counter32,
    bwShortMessageServiceSPTermination Counter32
    }

 bwShortMessageServiceSPIndex OBJECT-TYPE
    SYNTAX       Unsigned32
    MAX-ACCESS   read-only
    STATUS       current
    DESCRIPTION  
        "This column represents the index of the Service Provider in the system."
    ::= { bwShortMessageServiceSPEntry 1 }

  bwShortMessageServiceSPID OBJECT-TYPE
    SYNTAX       DisplayString
    MAX-ACCESS   read-only
    STATUS       current
    DESCRIPTION  
        "This string represents a Service Provider ID."
    ::= { bwShortMessageServiceSPEntry 2 }

 bwShortMessageServiceSPOrigination OBJECT-TYPE
    SYNTAX       Counter32
    MAX-ACCESS   read-write
    STATUS       current
    DESCRIPTION  
        "This is the number of times that a Short Message Service origination has been attempted by a BroadWorks subscriber within this service provider.  There is one instance of this counter for each service provider defined in the system."
    ::= { bwShortMessageServiceSPEntry 3 }

 bwShortMessageServiceSPTermination OBJECT-TYPE
    SYNTAX       Counter32
    MAX-ACCESS   read-write
    STATUS       current
    DESCRIPTION  
        "This is the number of times that a Short Message Service termination has been attempted to a BroadWorks subscriber within this service provider.  There is one instance of this counter for each service provider defined in the system."
    ::= { bwShortMessageServiceSPEntry 4 }

-- Service : Short Message Service Group ...........................................

  bwShortMessageServiceGroupEntry OBJECT-TYPE
    SYNTAX      BwShortMessageServiceGroupEntry
    MAX-ACCESS  not-accessible
    STATUS      current
    DESCRIPTION
        "Each row contains the service counters for the Short Message Service service for each service provider in the system"
    INDEX { bwShortMessageGroupIndex }
    ::= { bwShortMessageServiceGroupTable 1 }

  BwShortMessageServiceGroupEntry ::= SEQUENCE {
    bwShortMessageGroupIndex               Unsigned32,
    bwShortMessageGroupID                  DisplayString,
    bwShortMessageServiceGroupOrigination  Counter32,
    bwShortMessageServiceGroupTermination  Counter32 }

 bwShortMessageGroupIndex OBJECT-TYPE
    SYNTAX       Unsigned32
    MAX-ACCESS   read-only
    STATUS       current
    DESCRIPTION  
        "This column represents the index of the Service Provider in the system."
    ::= { bwShortMessageServiceGroupEntry 1 }

  bwShortMessageGroupID OBJECT-TYPE
    SYNTAX       DisplayString
    MAX-ACCESS   read-only
    STATUS       current
    DESCRIPTION  
        "This string represents a Service Provider ID."
    ::= { bwShortMessageServiceGroupEntry 2 }

 bwShortMessageServiceGroupOrigination OBJECT-TYPE
    SYNTAX       Counter32
    MAX-ACCESS   read-write
    STATUS       current
    DESCRIPTION  
        "This is the number of times that a Short Message Service origination has been attempted by a BroadWorks subscriber within this group.  There is one instance of this counter for each group defined in the system."
    ::= { bwShortMessageServiceGroupEntry 3 }

 bwShortMessageServiceGroupTermination OBJECT-TYPE
    SYNTAX       Counter32
    MAX-ACCESS   read-write
    STATUS       current
    DESCRIPTION  
        "This is the number of times that a Short Message Service termination has been attempted to a BroadWorks subscriber within this group.  There is one instance of this counter for each group defined in the system."
    ::= { bwShortMessageServiceGroupEntry 4 }

-- Service : callMeNow  ...........................................

 bwCallMeNowNumRequests OBJECT-TYPE
    SYNTAX      Counter32
    MAX-ACCESS  read-write
    STATUS      current
    DESCRIPTION
        "Number of times a Call Me Now request has been received."
    ::= { callMeNow 1 }

 bwCallMeNowNumAttempts OBJECT-TYPE
    SYNTAX      Counter32
    MAX-ACCESS  read-write
    STATUS      current
    DESCRIPTION
        "Number of times a Call Me Now request passed screening and attempted to alert the external party."
    ::= { callMeNow 2 }

 bwCallMeNowNumSuccess OBJECT-TYPE
    SYNTAX      Counter32
    MAX-ACCESS  read-write
    STATUS      current
    DESCRIPTION
        "Number of times a Call Me Now request has been answered by the external party and passed any applicable answer confirmation."
    ::= { callMeNow 3 }

  bwCallMeNowSPTable OBJECT-TYPE
    SYNTAX      SEQUENCE  OF  BwCallMeNowSPEntry
    MAX-ACCESS  not-accessible
    STATUS      current
    DESCRIPTION "Each row contains the service counters for the Call Me Now service for each service provider in the system"
    ::= { callMeNow 4 }

  bwCallMeNowGroupTable OBJECT-TYPE
    SYNTAX      SEQUENCE  OF  BwCallMeNowGroupEntry
    MAX-ACCESS  not-accessible
    STATUS      current
    DESCRIPTION "Each row contains the service counters for the Call Me Now service for each group in the system"
    ::= { callMeNow 5 }

-- Service : Call Me Now SP ...........................................

  bwCallMeNowSPEntry OBJECT-TYPE
    SYNTAX      BwCallMeNowSPEntry
    MAX-ACCESS  not-accessible
    STATUS      current
    DESCRIPTION
        "Each row contains the service counters for the Call Me Now service for each service provider in the system"
    INDEX { bwCallMeNowSPIndex }
    ::= { bwCallMeNowSPTable 1 }

  BwCallMeNowSPEntry ::= SEQUENCE {
    bwCallMeNowSPIndex       Unsigned32,
    bwCallMeNowSPID          DisplayString,
    bwCallMeNowSPNumRequests Counter32,
    bwCallMeNowSPNumAttempts Counter32,
    bwCallMeNowSPNumSuccess  Counter32
    }

 bwCallMeNowSPIndex OBJECT-TYPE
    SYNTAX       Unsigned32
    MAX-ACCESS   read-only
    STATUS       current
    DESCRIPTION  
        "This column represents the index of the Service Provider in the system."
    ::= { bwCallMeNowSPEntry 1 }

  bwCallMeNowSPID OBJECT-TYPE
    SYNTAX       DisplayString
    MAX-ACCESS   read-only
    STATUS       current
    DESCRIPTION  
        "This string represents a Service Provider ID."
    ::= { bwCallMeNowSPEntry 2 }

 bwCallMeNowSPNumRequests OBJECT-TYPE
    SYNTAX       Counter32
    MAX-ACCESS   read-write
    STATUS       current
    DESCRIPTION  
        "Number of times a Call Me Now request has been received for users in a given service provider."
    ::= { bwCallMeNowSPEntry 3 }

 bwCallMeNowSPNumAttempts OBJECT-TYPE
    SYNTAX       Counter32
    MAX-ACCESS   read-write
    STATUS       current
    DESCRIPTION  
        "Number of times a Call Me Now request passed screening and attempted to alert the external party for users in a given service provider."
    ::= { bwCallMeNowSPEntry 4 }

 bwCallMeNowSPNumSuccess OBJECT-TYPE
    SYNTAX       Counter32
    MAX-ACCESS   read-write
    STATUS       current
    DESCRIPTION  
        "Number of times a Call Me Now request has been answered by the external party and passed any applicable answer confirmation for users in a given service provider."
    ::= { bwCallMeNowSPEntry 5 }

-- Service : Call Me Now Group ...........................................

  bwCallMeNowGroupEntry OBJECT-TYPE
    SYNTAX      BwCallMeNowGroupEntry
    MAX-ACCESS  not-accessible
    STATUS      current
    DESCRIPTION
        "Each row contains the service counters for the Call Me Now service for each group in the system"
    INDEX { bwCallMeNowGroupIndex }
    ::= { bwCallMeNowGroupTable 1 }

  BwCallMeNowGroupEntry ::= SEQUENCE {
    bwCallMeNowGroupIndex        Unsigned32,
    bwCallMeNowGroupID           DisplayString,
    bwCallMeNowGroupNumRequests  Counter32,
    bwCallMeNowGroupNumAttempts  Counter32,
    bwCallMeNowGroupNumSuccess   Counter32 }

 bwCallMeNowGroupIndex OBJECT-TYPE
    SYNTAX       Unsigned32
    MAX-ACCESS   read-only
    STATUS       current
    DESCRIPTION  
        "This column represents the index of the group in the system."
    ::= { bwCallMeNowGroupEntry 1 }

  bwCallMeNowGroupID OBJECT-TYPE
    SYNTAX       DisplayString
    MAX-ACCESS   read-only
    STATUS       current
    DESCRIPTION  
        "This string represents a Group ID."
    ::= { bwCallMeNowGroupEntry 2 }

  bwCallMeNowGroupNumRequests OBJECT-TYPE
    SYNTAX       Counter32
    MAX-ACCESS   read-write
    STATUS       current
    DESCRIPTION  
        "Number of times a Call Me Now request has been received for users in a given group."
    ::= { bwCallMeNowGroupEntry 3 }

  bwCallMeNowGroupNumAttempts OBJECT-TYPE
    SYNTAX       Counter32
    MAX-ACCESS   read-write
    STATUS       current
    DESCRIPTION  
        "Number of times a Call Me Now request passed screening and attempted to alert the external party for users in a given group."
    ::= { bwCallMeNowGroupEntry 4 }

  bwCallMeNowGroupNumSuccess OBJECT-TYPE
    SYNTAX       Counter32
    MAX-ACCESS   read-write
    STATUS       current
    DESCRIPTION  
        "Number of times a Call Me Now request has been answered by the external party and passed any applicable answer confirmation for users in a given group."
    ::= { bwCallMeNowGroupEntry 5 }

-- Service : CallLogs  ...........................................

 bwCallLogEventsReported OBJECT-TYPE
     SYNTAX      Counter32
     MAX-ACCESS  read-write
     STATUS      current
     DESCRIPTION
         "This counter represents the number of call log events reported by the Enhanced Call Logs service regardless of type.  Note that more specific counters can also be incremented."
     ::= { callLogQueue 1 }
 
  bwCallLogEventsIgnored OBJECT-TYPE
     SYNTAX      Counter32
     MAX-ACCESS  read-write
     STATUS      current
     DESCRIPTION
         "This counter represents the number of call log events reported by the Enhanced Call Logs service, which are ignored.  While events are not generally ignored, certain situations cause this to occur.  One example is when enhanced call log events are being reported but no database has been configured to receive the reported data."
     ::= { callLogQueue 2 }

  bwCallLogEventsFailed OBJECT-TYPE
     SYNTAX      Counter32
     MAX-ACCESS  read-write
     STATUS      current
     DESCRIPTION
         "This counter represents the number of call log events reported by the Enhanced Call Logs service, which failed to be recorded in the database.  One example of a failure is when events are reported while the database connection is down."
     ::= { callLogQueue 3 }

  bwCallLogDatabaseInserts OBJECT-TYPE
     SYNTAX      Counter32
     MAX-ACCESS  read-write
     STATUS      current
     DESCRIPTION
         "This counter represents the number of database insert operations performed while recording data reported by the Enhanced Call Logs service."
     ::= { callLogQueue 4 }

  bwCallLogDatabaseUpdates OBJECT-TYPE
     SYNTAX      Counter32
     MAX-ACCESS  read-write
     STATUS      current
     DESCRIPTION
         "This counter represents the number of database update operations performed while recording data reported by the Enhanced Call Logs service."
     ::= { callLogQueue 5 }

  bwCallLogDatabaseQueries OBJECT-TYPE
     SYNTAX      Counter32
     MAX-ACCESS  read-write
     STATUS      current
     DESCRIPTION
         "This counter represents the number of database select operations performed while recording data reported by the Enhanced Call Logs service."
     ::= { callLogQueue 6 }

  bwCallLogDatabaseDeletes OBJECT-TYPE
     SYNTAX      Counter32
     MAX-ACCESS  read-write
     STATUS      current
     DESCRIPTION
         "This counter represents the number of database delete operations performed while recording data reported by the Enhanced Call Logs service."
     ::= { callLogQueue 7 }

  bwCallLogDatabaseFailures OBJECT-TYPE
     SYNTAX      Counter32
     MAX-ACCESS  read-write
     STATUS      current
     DESCRIPTION
         "This counter represents the number of database failures that have occurred while recording data reported by the Enhanced Call Logs service."
     ::= { callLogQueue 8 }

  bwCallLogEventResets OBJECT-TYPE
     SYNTAX      Counter32
     MAX-ACCESS  read-write
     STATUS      current
     DESCRIPTION
         "When set to a value other than 0, all event statistics stored in the callLogEventTable are reset to 0."
     ::= { callLogQueue 9 }

   bwCallLogEventTable OBJECT-TYPE
     SYNTAX      SEQUENCE  OF  BwCallLogEventEntry
     MAX-ACCESS  not-accessible
     STATUS      current
     DESCRIPTION "Each row contains the number of occurence of a call log event."
     ::= { callLogQueue 10 }

   bwCallLogEventEntry OBJECT-TYPE
     SYNTAX      BwCallLogEventEntry
     MAX-ACCESS  not-accessible
     STATUS      current
     DESCRIPTION
         "Each row contains the number of occurence of a call log event."
     INDEX { bwCallLogEventIndex }
     ::= { bwCallLogEventTable 1 }

   BwCallLogEventEntry ::= SEQUENCE {
     bwCallLogEventIndex  Unsigned32,
     bwCallLogEventName   DisplayString,
     bwCallLogEventCount  Counter32 }

  bwCallLogEventIndex OBJECT-TYPE
     SYNTAX       Unsigned32
     MAX-ACCESS   read-only
     STATUS       current
     DESCRIPTION  
         "This is the index of the queue event table entry."
     ::= { bwCallLogEventEntry 1 }

  bwCallLogEventName OBJECT-TYPE
     SYNTAX       DisplayString
     MAX-ACCESS   read-only
     STATUS       current
     DESCRIPTION  
         "This displays the name of the call log event table entry."
     ::= { bwCallLogEventEntry 2 }

  bwCallLogEventCount OBJECT-TYPE
     SYNTAX       Counter32
     MAX-ACCESS   read-write
     STATUS       current
     DESCRIPTION  
         "This displays the number of events reported for the specific event table entry."
     ::= { bwCallLogEventEntry 3 }

  bwCallLogProcessorResets OBJECT-TYPE
     SYNTAX      Gauge32
     MAX-ACCESS  read-write
     STATUS      current
     DESCRIPTION
         "When set to a value other than '0', all processor statistics stored in the callLogProcessorTable are reset to '0'."
     ::= { callLogProcessors 1 }
 
   bwCallLogProcessorTable OBJECT-TYPE
     SYNTAX      SEQUENCE  OF  BwCallLogProcessorEntry
     MAX-ACCESS  not-accessible
     STATUS      current
     DESCRIPTION "Each row contains the number of occurence of a call log processor."
     ::= { callLogProcessors 2 }
 
   bwCallLogProcessorEntry OBJECT-TYPE
     SYNTAX      BwCallLogProcessorEntry
     MAX-ACCESS  not-accessible
     STATUS      current
     DESCRIPTION
         "Each row contains the number of occurence of a call log processor."
     INDEX { bwCallLogProcessorIndex }
     ::= { bwCallLogProcessorTable 1 }
 
   BwCallLogProcessorEntry ::= SEQUENCE {
     bwCallLogProcessorIndex       Unsigned32,
     bwCallLogProcessorEventCount  Counter32 }
 
  bwCallLogProcessorIndex OBJECT-TYPE
     SYNTAX       Unsigned32
     MAX-ACCESS   read-only
     STATUS       current
     DESCRIPTION  
         "This is the index of the processor table entry."
     ::= { bwCallLogProcessorEntry 1 }
 
  bwCallLogProcessorEventCount OBJECT-TYPE
     SYNTAX       Counter32
     MAX-ACCESS   read-write
     STATUS       current
     DESCRIPTION  
         "This is the number of events committed to the database by the processor table entry."
     ::= { bwCallLogProcessorEntry 2 }

-- Services :: Call Forwarding Froup Not Reachable  ...........................................

 bwCFGNRcForward OBJECT-TYPE
    SYNTAX      Counter32
    MAX-ACCESS  read-write
    STATUS      current
    DESCRIPTION
        "The number of times CFGNRc has forwarded the call to the external destination."
    ::= { callForwardingGroupNotReachable 1 }

 bwCFGNRcNoForward OBJECT-TYPE
    SYNTAX      Counter32
    MAX-ACCESS  read-write
    STATUS      current
    DESCRIPTION
        "The number of times CFGNRc fails to forward the call and given temporarily unavailable treatment."
    ::= { callForwardingGroupNotReachable 2 }

  bwCFGNRcSPTable OBJECT-TYPE
    SYNTAX      SEQUENCE  OF  BwCFGNRcSPEntry
    MAX-ACCESS  not-accessible
    STATUS      current
    DESCRIPTION "Each row contains the service counters for the Call Forwarding Not Reachable service for each service provider in the system"
    ::= { callForwardingGroupNotReachable 3 }

  bwCFGNRcGroupTable OBJECT-TYPE
    SYNTAX      SEQUENCE  OF  BwCFGNRcGroupEntry
    MAX-ACCESS  not-accessible
    STATUS      current
    DESCRIPTION "Each row contains the service counters for the Call Forwarding Not Reachable service for each group in the system"
    ::= { callForwardingGroupNotReachable 4 }

-- Service : Call Forwarding Froup Not Reachable SP ...........................................

  bwCFGNRcSPEntry OBJECT-TYPE
    SYNTAX      BwCFGNRcSPEntry
    MAX-ACCESS  not-accessible
    STATUS      current
    DESCRIPTION
        "Each row contains the service counters for the Call Forwarding Not Reachable service for each service provider in the system"
    INDEX { bwCFGNRcSPIndex }
    ::= { bwCFGNRcSPTable 1 }

  BwCFGNRcSPEntry ::= SEQUENCE {
    bwCFGNRcSPIndex       Unsigned32,
    bwCFGNRcSPID          DisplayString,
    bwCFGNRcSPForward     Counter32,
    bwCFGNRcSPNoForward   Counter32
    }

 bwCFGNRcSPIndex OBJECT-TYPE
    SYNTAX       Unsigned32
    MAX-ACCESS   read-only
    STATUS       current
    DESCRIPTION  
        "This column represents the index of the Service Provider in the system."
    ::= { bwCFGNRcSPEntry 1 }

  bwCFGNRcSPID OBJECT-TYPE
    SYNTAX       DisplayString
    MAX-ACCESS   read-only
    STATUS       current
    DESCRIPTION  
        "This string represents a Service Provider ID."
    ::= { bwCFGNRcSPEntry 2 }

 bwCFGNRcSPForward OBJECT-TYPE
    SYNTAX       Counter32
    MAX-ACCESS   read-write
    STATUS       current
    DESCRIPTION  
        "The number of times CFGNRc has forwarded the call to the external destination. There is one instance of this counter for each service provider defined in the system."
    ::= { bwCFGNRcSPEntry 3 }

 bwCFGNRcSPNoForward OBJECT-TYPE
    SYNTAX       Counter32
    MAX-ACCESS   read-write
    STATUS       current
    DESCRIPTION  
        "The number of times CFGNRc has forwarded the call to the external destination. There is one instance of this counter for each group defined in the system."
    ::= { bwCFGNRcSPEntry 4 }

-- Service : Call Forwarding Group Not Reachable Group ...........................................

  bwCFGNRcGroupEntry OBJECT-TYPE
    SYNTAX      BwCFGNRcGroupEntry
    MAX-ACCESS  not-accessible
    STATUS      current
    DESCRIPTION
        "Each row contains the service counters for the Call Forwarding Group Not Reachable service for each group in the system"
    INDEX { bwCFGNRcGroupIndex }
    ::= { bwCFGNRcGroupTable 1 }

  BwCFGNRcGroupEntry ::= SEQUENCE {
    bwCFGNRcGroupIndex        Unsigned32,
    bwCFGNRcGroupID           DisplayString,
    bwCFGNRcGroupForward      Counter32,
    bwCFGNRcGroupNoForward    Counter32 }

 bwCFGNRcGroupIndex OBJECT-TYPE
    SYNTAX       Unsigned32
    MAX-ACCESS   read-only
    STATUS       current
    DESCRIPTION  
        "This column represents the index of the group in the system."
    ::= { bwCFGNRcGroupEntry 1 }

  bwCFGNRcGroupID OBJECT-TYPE
    SYNTAX       DisplayString
    MAX-ACCESS   read-only
    STATUS       current
    DESCRIPTION  
        "This string represents a Group ID."
    ::= { bwCFGNRcGroupEntry 2 }

  bwCFGNRcGroupForward OBJECT-TYPE
    SYNTAX       Counter32
    MAX-ACCESS   read-write
    STATUS       current
    DESCRIPTION  
        "The number of times CFGNRc fails to forward the call and given temporarily unavailable treatment. There is one instance of this counter for each service provider defined in the system."
    ::= { bwCFGNRcGroupEntry 3 }

  bwCFGNRcGroupNoForward OBJECT-TYPE
    SYNTAX       Counter32
    MAX-ACCESS   read-write
    STATUS       current
    DESCRIPTION  
        "The number of times CFGNRc fails to forward the call and given temporarily unavailable treatment. There is one instance of this counter for each group defined in the system."
    ::= { bwCFGNRcGroupEntry 4 }

-- Services :: Call Recording  ...........................................

 bwCallRecordingAutoRecordings OBJECT-TYPE
    SYNTAX      Counter32
    MAX-ACCESS  read-write
    STATUS      current
    DESCRIPTION
        "Number of calls that are automatically recorded."
    ::= { callRecording 1 }

 bwCallRecordingOnDemandRecordings OBJECT-TYPE
    SYNTAX      Counter32
    MAX-ACCESS  read-write
    STATUS      current
    DESCRIPTION
        "Number of calls that are requested to be saved on an on-demand basis."
    ::= { callRecording 2 }

 bwCallRecordingOnDemandEnabled OBJECT-TYPE
    SYNTAX      Counter32
    MAX-ACCESS  read-write
    STATUS      current
    DESCRIPTION
        "Number of calls where on-demand recording is enabled, regardless whether the recordings are triggered to be saved."
    ::= { callRecording 3 }

 bwCallRecordingPaused OBJECT-TYPE
    SYNTAX      Counter32
    MAX-ACCESS  read-write
    STATUS      current
    DESCRIPTION
        "The number of times a call recording is paused."
    ::= { callRecording 6 }

 bwCallRecordingResumed OBJECT-TYPE
    SYNTAX      Counter32
    MAX-ACCESS  read-write
    STATUS      current
    DESCRIPTION
        "The number of times a call recording is resumed."
    ::= { callRecording 7 }

 bwCallRecordingVoicemailRecording OBJECT-TYPE
    SYNTAX      Counter32
    MAX-ACCESS  read-write
    STATUS      current
    DESCRIPTION
        "This counter tracks the number of times a voice mail recording starts"
-- @feature:170964
    ::= { callRecording 8 }

 bwCallRecordingVoicemailRecordingAbandoned OBJECT-TYPE
    SYNTAX      Counter32
    MAX-ACCESS  read-write
    STATUS      current
    DESCRIPTION
        "This counter tracks the number of times a voice mail recording is abandoned when a user accesses their voice portal during a voice message deposit."
-- @feature:170964
    ::= { callRecording 9 }

 bwCallRecordingVideoRecordings OBJECT-TYPE
    SYNTAX      Counter32
    MAX-ACCESS  read-write
    STATUS      current
    DESCRIPTION
        "The number of video calls that are recorded."
-- @feature:170973
    ::= { callRecording 10 }

 bwCallRecordingMSReconnected OBJECT-TYPE
    SYNTAX      Counter32
    MAX-ACCESS  read-write
    STATUS      current
    DESCRIPTION
        "The number of times a call recording is reconnected to a secondary Media Server."
-- @feature:184307
    ::= { callRecording 11 }

  bwCallRecordingSPTable OBJECT-TYPE
    SYNTAX      SEQUENCE  OF  BwCallRecordingSPEntry
    MAX-ACCESS  not-accessible
    STATUS      current
    DESCRIPTION "Each row contains the service counters for the Call Recording service for each service provider in the system"
    ::= { callRecording 4 }

  bwCallRecordingGroupTable OBJECT-TYPE
    SYNTAX      SEQUENCE  OF  BwCallRecordingGroupEntry
    MAX-ACCESS  not-accessible
    STATUS      current
    DESCRIPTION "Each row contains the service counters for the Call Recording service for each group in the system"
    ::= { callRecording 5 }

-- Services :: Call Recording  SP ...........................................

  bwCallRecordingSPEntry OBJECT-TYPE
    SYNTAX      BwCallRecordingSPEntry
    MAX-ACCESS  not-accessible
    STATUS      current
    DESCRIPTION
        "Each row contains the service counters for the Call Recording service for each service provider in the system"
    INDEX { bwCallRecordingSPIndex }
    ::= { bwCallRecordingSPTable 1 }

  BwCallRecordingSPEntry ::= SEQUENCE {
    bwCallRecordingSPIndex                       Unsigned32,
    bwCallRecordingSPID                          DisplayString,
    bwCallRecordingSPAutoRecordings              Counter32,
    bwCallRecordingSPOnDemandRecordings          Counter32,
    bwCallRecordingSPOnDemandEnabled             Counter32,
    bwCallRecordingSPPaused                      Counter32,
    bwCallRecordingSPResumed                     Counter32,
    bwCallRecordingSPVoicemailRecording          Counter32,
    bwCallRecordingSPVoicemailRecordingAbandoned Counter32,
    bwCallRecordingSPVideoRecordings             Counter32,
    bwCallRecordingSPMSReconnected               Counter32
    }

 bwCallRecordingSPIndex OBJECT-TYPE
    SYNTAX       Unsigned32
    MAX-ACCESS   read-only
    STATUS       current
    DESCRIPTION  
        "This column represents the index of the Service Provider in the system."
    ::= { bwCallRecordingSPEntry 1 }

  bwCallRecordingSPID OBJECT-TYPE
    SYNTAX       DisplayString
    MAX-ACCESS   read-only
    STATUS       current
    DESCRIPTION  
        "This string represents a Service Provider ID."
    ::= { bwCallRecordingSPEntry 2 }

 bwCallRecordingSPAutoRecordings OBJECT-TYPE
    SYNTAX       Counter32
    MAX-ACCESS   read-write
    STATUS       current
    DESCRIPTION  
        "Number of calls that are automatically recorded for user in the given service provider."
    ::= { bwCallRecordingSPEntry 3 }

 bwCallRecordingSPOnDemandRecordings OBJECT-TYPE
    SYNTAX       Counter32
    MAX-ACCESS   read-write
    STATUS       current
    DESCRIPTION  
        "Number of calls that are requested to be saved on an on-demand basis for users in the given service provider."
    ::= { bwCallRecordingSPEntry 4 }

 bwCallRecordingSPOnDemandEnabled OBJECT-TYPE
    SYNTAX       Counter32
    MAX-ACCESS   read-write
    STATUS       current
    DESCRIPTION  
        "Number of calls where on-demand recording is enabled, regardless whether the recordings are triggered to be saved for users in the given service provider."
    ::= { bwCallRecordingSPEntry 5 }

 bwCallRecordingSPPaused OBJECT-TYPE
    SYNTAX       Counter32
    MAX-ACCESS   read-write
    STATUS       current
    DESCRIPTION  
        "The number of times a call recording is paused for the users within a given service provider."
    ::= { bwCallRecordingSPEntry 6 }

 bwCallRecordingSPResumed OBJECT-TYPE
    SYNTAX       Counter32
    MAX-ACCESS   read-write
    STATUS       current
    DESCRIPTION  
        "The number of times a call recording is resumed for the users within a given service provider."
    ::= { bwCallRecordingSPEntry 7 }

 bwCallRecordingSPVoicemailRecording OBJECT-TYPE
    SYNTAX       Counter32
    MAX-ACCESS   read-write
    STATUS       current
    DESCRIPTION  
        "This counter tracks the number of times a voice mail recording starts for a user in the service provider."
-- @feature:170964
    ::= { bwCallRecordingSPEntry 8 }

 bwCallRecordingSPVoicemailRecordingAbandoned OBJECT-TYPE
    SYNTAX       Counter32
    MAX-ACCESS   read-write
    STATUS       current
    DESCRIPTION  
        "This counter tracks the number of times a voice mail recording is abandoned when a user in the service provider accesses their voice portal during a voice message deposit."
-- @feature:170964
    ::= { bwCallRecordingSPEntry 9 }

 bwCallRecordingSPVideoRecordings OBJECT-TYPE
    SYNTAX       Counter32
    MAX-ACCESS   read-write
    STATUS       current
    DESCRIPTION  
        "The number of video calls that are recorded for users in the given service provider"
-- @feature:170973
    ::= { bwCallRecordingSPEntry 10 }

 bwCallRecordingSPMSReconnected OBJECT-TYPE
    SYNTAX       Counter32
    MAX-ACCESS   read-write
    STATUS       current
    DESCRIPTION  
        "The number of times a call recording is reconnected to a secondary Media Server for a user in the service provider."
-- @feature:184307
    ::= { bwCallRecordingSPEntry 11 }

-- Services :: Call Recording  Group ...........................................

  bwCallRecordingGroupEntry OBJECT-TYPE
    SYNTAX      BwCallRecordingGroupEntry
    MAX-ACCESS  not-accessible
    STATUS      current
    DESCRIPTION
        "Each row contains the service counters for the Call Recording service for each group in the system"
    INDEX { bwCallRecordingGroupIndex }
    ::= { bwCallRecordingGroupTable 1 }

  BwCallRecordingGroupEntry ::= SEQUENCE {
    bwCallRecordingGroupIndex                       Unsigned32,
    bwCallRecordingGroupID                          DisplayString,
    bwCallRecordingGroupAutoRecordings              Counter32,
    bwCallRecordingGroupOnDemandRecordings          Counter32,
    bwCallRecordingGroupOnDemandEnabled             Counter32,
    bwCallRecordingGroupPaused                      Counter32,
    bwCallRecordingGroupResumed                     Counter32,
    bwCallRecordingGroupVoicemailRecording          Counter32,
    bwCallRecordingGroupVoicemailRecordingAbandoned Counter32,
    bwCallRecordingGroupVideoRecordings             Counter32,
    bwCallRecordingGroupMSReconnected               Counter32
    }

 bwCallRecordingGroupIndex OBJECT-TYPE
    SYNTAX       Unsigned32
    MAX-ACCESS   read-only
    STATUS       current
    DESCRIPTION  
        "This column represents the index of the group in the system."
    ::= { bwCallRecordingGroupEntry 1 }

  bwCallRecordingGroupID OBJECT-TYPE
    SYNTAX       DisplayString
    MAX-ACCESS   read-only
    STATUS       current
    DESCRIPTION  
        "This string represents a Group ID."
    ::= { bwCallRecordingGroupEntry 2 }

  bwCallRecordingGroupAutoRecordings OBJECT-TYPE
    SYNTAX       Counter32
    MAX-ACCESS   read-write
    STATUS       current
    DESCRIPTION  
        "Number of calls that are automatically recorded for users in the given group."
    ::= { bwCallRecordingGroupEntry 3 }

  bwCallRecordingGroupOnDemandRecordings OBJECT-TYPE
    SYNTAX       Counter32
    MAX-ACCESS   read-write
    STATUS       current
    DESCRIPTION  
        "Number of calls that are requested to be saved on an on-demand basis for users in the given group."
    ::= { bwCallRecordingGroupEntry 4 }

  bwCallRecordingGroupOnDemandEnabled OBJECT-TYPE
    SYNTAX       Counter32
    MAX-ACCESS   read-write
    STATUS       current
    DESCRIPTION  
        "Number of calls where on-demand recording is enabled, regardless whether the recordings are triggered to be saved for users in the given group."
    ::= { bwCallRecordingGroupEntry 5 }

  bwCallRecordingGroupPaused OBJECT-TYPE
    SYNTAX       Counter32
    MAX-ACCESS   read-write
    STATUS       current
    DESCRIPTION  
        "The number of times a call recording is paused for the users within a given group."
    ::= { bwCallRecordingGroupEntry 6 }

  bwCallRecordingGroupResumed OBJECT-TYPE
    SYNTAX       Counter32
    MAX-ACCESS   read-write
    STATUS       current
    DESCRIPTION  
        "The number of times a call recording is resumed for the users within a given group."
    ::= { bwCallRecordingGroupEntry 7 }

  bwCallRecordingGroupVoicemailRecording OBJECT-TYPE
    SYNTAX       Counter32
    MAX-ACCESS   read-write
    STATUS       current
    DESCRIPTION  
        "This counter tracks the number of times a voice mail recording starts for a user in the group."
-- @feature:170964
    ::= { bwCallRecordingGroupEntry 8 }

  bwCallRecordingGroupVoicemailRecordingAbandoned OBJECT-TYPE
    SYNTAX       Counter32
    MAX-ACCESS   read-write
    STATUS       current
    DESCRIPTION  
        "This counter tracks the number of times a voice mail recording is abandoned when a user  in the group accesses their voice portal during a voice message deposit."
-- @feature:170964
    ::= { bwCallRecordingGroupEntry 9 }

  bwCallRecordingGroupVideoRecordings OBJECT-TYPE
    SYNTAX       Counter32
    MAX-ACCESS   read-write
    STATUS       current
    DESCRIPTION  
        "The number of video calls that are recorded for users in the given group."
-- @feature:170973
    ::= { bwCallRecordingGroupEntry 10 }

  bwCallRecordingGroupMSReconnected OBJECT-TYPE
    SYNTAX       Counter32
    MAX-ACCESS   read-write
    STATUS       current
    DESCRIPTION  
        "The number of times a call recording is reconnected to a secondary Media Server for a user in the group."
-- @feature:184307
    ::= { bwCallRecordingGroupEntry 11 }

-- Services :: Find Me Follow Me  ...........................................

 bwFMFMCall OBJECT-TYPE
    SYNTAX      Counter32
    MAX-ACCESS  read-write
    STATUS      current
    DESCRIPTION
        "Number of times a call is made to an FMFM virtual user."
-- @feature:125258
    ::= { findMeFollowMe 1 }

 bwFMFMCallPush OBJECT-TYPE
    SYNTAX      Counter32
    MAX-ACCESS  read-write
    STATUS      current
    DESCRIPTION
        "Number of call push attempts."
-- @feature:125258
    ::= { findMeFollowMe 2 }

  bwFMFMSPTable OBJECT-TYPE
    SYNTAX      SEQUENCE  OF  BwFMFMSPEntry
    MAX-ACCESS  not-accessible
    STATUS      current
    DESCRIPTION "Each row contains the service counters for the Find Me Follow ME service for each service provider in the system"
-- @feature:125258
    ::= { findMeFollowMe 3 }

  bwFMFMGroupTable OBJECT-TYPE
    SYNTAX      SEQUENCE  OF  BwFMFMGroupEntry
    MAX-ACCESS  not-accessible
    STATUS      current
    DESCRIPTION "Each row contains the service counters for the Find Me Follow Me service for each group in the system"
-- @feature:125258
    ::= { findMeFollowMe 4 }

-- Services :: Find Me Follow Me Service Provider...........................................

  bwFMFMSPEntry OBJECT-TYPE
    SYNTAX      BwFMFMSPEntry
    MAX-ACCESS  not-accessible
    STATUS      current
    DESCRIPTION
        "Each row contains the service counters for the Find Me Follow Me service for each service provider in the system"
    INDEX { bwFMFMSPIndex }
-- @feature:125258
    ::= { bwFMFMSPTable 1 }

  BwFMFMSPEntry ::= SEQUENCE {
    bwFMFMSPIndex    Unsigned32,
    bwFMFMSPID       DisplayString,
    bwFMFMSPCall     Counter32,
    bwFMFMSPCallPush Counter32
    }

 bwFMFMSPIndex OBJECT-TYPE
    SYNTAX       Unsigned32
    MAX-ACCESS   read-only
    STATUS       current
    DESCRIPTION  
        "This column represents the index of the Service Provider in the system."
-- @feature:125258
    ::= { bwFMFMSPEntry 1 }

  bwFMFMSPID OBJECT-TYPE
    SYNTAX       DisplayString
    MAX-ACCESS   read-only
    STATUS       current
    DESCRIPTION  
        "This string represents a Service Provider ID."
-- @feature:125258
    ::= { bwFMFMSPEntry 2 }

 bwFMFMSPCall OBJECT-TYPE
    SYNTAX       Counter32
    MAX-ACCESS   read-write
    STATUS       current
    DESCRIPTION  
        "Number of times a call is made to an FMFM virtual user where the user belongs to given service provider."
-- @feature:125258
    ::= { bwFMFMSPEntry 3 }

 bwFMFMSPCallPush OBJECT-TYPE
    SYNTAX       Counter32
    MAX-ACCESS   read-write
    STATUS       current
    DESCRIPTION  
        "Number of call push attempts by users belonging to a given Service provider."
-- @feature:125258
    ::= { bwFMFMSPEntry 4 }

-- Services :: Find Me Follow Me Group ...........................................

  bwFMFMGroupEntry OBJECT-TYPE
    SYNTAX      BwFMFMGroupEntry
    MAX-ACCESS  not-accessible
    STATUS      current
    DESCRIPTION
        "Each row contains the service counters for the Find Me Follow Me service for each group in the system"
    INDEX { bwFMFMGroupIndex }
-- @feature:125258
    ::= { bwFMFMGroupTable 1 }

  BwFMFMGroupEntry ::= SEQUENCE {
    bwFMFMGroupIndex    Unsigned32,
    bwFMFMGroupID       DisplayString,
    bwFMFMGroupCall     Counter32,
    bwFMFMGroupCallPush Counter32
    }

 bwFMFMGroupIndex OBJECT-TYPE
    SYNTAX       Unsigned32
    MAX-ACCESS   read-only
    STATUS       current
    DESCRIPTION  
        "This column represents the index of the Group in the system."
-- @feature:125258
    ::= { bwFMFMGroupEntry 1 }

  bwFMFMGroupID OBJECT-TYPE
    SYNTAX       DisplayString
    MAX-ACCESS   read-only
    STATUS       current
    DESCRIPTION  
        "This string represents a Group ID."
-- @feature:125258
    ::= { bwFMFMGroupEntry 2 }

 bwFMFMGroupCall OBJECT-TYPE
    SYNTAX       Counter32
    MAX-ACCESS   read-write
    STATUS       current
    DESCRIPTION  
        "Number of times a call is made to an FMFM virtual user where the user belongs to given group."
-- @feature:125258
    ::= { bwFMFMGroupEntry 3 }

 bwFMFMGroupCallPush OBJECT-TYPE
    SYNTAX       Counter32
    MAX-ACCESS   read-write
    STATUS       current
    DESCRIPTION  
        "Number of call push attempts by users belonging to a given group."
-- @feature:125258
    ::= { bwFMFMGroupEntry 4 }

-- Services :: Group Night Forwarding  ...........................................

 bwGroupNightForwardingNumInvocations OBJECT-TYPE
    SYNTAX      Counter32
    MAX-ACCESS  read-write
    STATUS      current
    DESCRIPTION
        "This is the number of times that the Group Night Forwarding Service redirected a call."
-- @feature:155570
    ::= { groupNightForwarding 1 }

  bwGroupNightForwardingSPTable OBJECT-TYPE
    SYNTAX      SEQUENCE  OF  BwGroupNightForwardingSPEntry
    MAX-ACCESS  not-accessible
    STATUS      current
    DESCRIPTION "Each row contains the service counters for the Group Night Forwarding service for each service provider in the system"
-- @feature:155570
    ::= { groupNightForwarding 2 }

  bwGroupNightForwardingGroupTable OBJECT-TYPE
    SYNTAX      SEQUENCE  OF  BwGroupNightForwardingGroupEntry
    MAX-ACCESS  not-accessible
    STATUS      current
    DESCRIPTION "Each row contains the service counters for the Group Night Forwarding service for each group in the system"
-- @feature:155570
    ::= { groupNightForwarding 3 }

-- Services :: Group Night Forwarding Service Provider...........................................

  bwGroupNightForwardingSPEntry OBJECT-TYPE
    SYNTAX      BwGroupNightForwardingSPEntry
    MAX-ACCESS  not-accessible
    STATUS      current
    DESCRIPTION
        "Each row contains the service counters for the Group Night Forwarding service for each service provider in the system"
    INDEX { bwGroupNightForwardingSPIndex }
-- @feature:155570
    ::= { bwGroupNightForwardingSPTable 1 }

  BwGroupNightForwardingSPEntry ::= SEQUENCE {
    bwGroupNightForwardingSPIndex          Unsigned32,
    bwGroupNightForwardingSPID             DisplayString,
    bwGroupNightForwardingSPNumInvocations Counter32
    }

 bwGroupNightForwardingSPIndex OBJECT-TYPE
    SYNTAX       Unsigned32
    MAX-ACCESS   read-only
    STATUS       current
    DESCRIPTION  
        "This column represents the index of the Service Provider in the system."
-- @feature:155570
    ::= { bwGroupNightForwardingSPEntry 1 }

  bwGroupNightForwardingSPID OBJECT-TYPE
    SYNTAX       DisplayString
    MAX-ACCESS   read-only
    STATUS       current
    DESCRIPTION  
        "This string represents a Service Provider ID."
-- @feature:155570
    ::= { bwGroupNightForwardingSPEntry 2 }

 bwGroupNightForwardingSPNumInvocations OBJECT-TYPE
    SYNTAX       Counter32
    MAX-ACCESS   read-write
    STATUS       current
    DESCRIPTION  
        "This is the number of times that the Group Night ForwardingService redirected a call.  There is one instance of this counter for each service provider defined in the system."
-- @feature:155570
    ::= { bwGroupNightForwardingSPEntry 3 }

-- Services :: Group Night Forwarding Group ...........................................

  bwGroupNightForwardingGroupEntry OBJECT-TYPE
    SYNTAX      BwGroupNightForwardingGroupEntry
    MAX-ACCESS  not-accessible
    STATUS      current
    DESCRIPTION
        "Each row contains the service counters for the Group Night Forwarding for each group in the system"
    INDEX { bwGroupNightForwardingGroupIndex }
-- @feature:155570
    ::= { bwGroupNightForwardingGroupTable 1 }

  BwGroupNightForwardingGroupEntry ::= SEQUENCE {
    bwGroupNightForwardingGroupIndex          Unsigned32,
    bwGroupNightForwardingGroupID             DisplayString,
    bwGroupNightForwardingGroupNumInvocations Counter32
    }

 bwGroupNightForwardingGroupIndex OBJECT-TYPE
    SYNTAX       Unsigned32
    MAX-ACCESS   read-only
    STATUS       current
    DESCRIPTION  
        "This column represents the index of the Group in the system."
-- @feature:155570
    ::= { bwGroupNightForwardingGroupEntry 1 }

  bwGroupNightForwardingGroupID OBJECT-TYPE
    SYNTAX       DisplayString
    MAX-ACCESS   read-only
    STATUS       current
    DESCRIPTION  
        "This string represents a Group ID."
-- @feature:155570
    ::= { bwGroupNightForwardingGroupEntry 2 }

 bwGroupNightForwardingGroupNumInvocations OBJECT-TYPE
    SYNTAX       Counter32
    MAX-ACCESS   read-write
    STATUS       current
    DESCRIPTION  
        "This is the number of times that the Group Night ForwardingService redirected a call. There is one instance of this counter for each group defined in the system."
-- @feature:155570
    ::= { bwGroupNightForwardingGroupEntry 3 }

-- Services :: Executive  ...........................................

 bwExecutiveNumCallsFiltered OBJECT-TYPE
    SYNTAX      Counter32
    MAX-ACCESS  read-write
    STATUS      current
    DESCRIPTION
        "The number of times a call has been filtered by the Executive service."
-- @feature:160554
    ::= { executive 1 }

  bwExecutiveSPTable OBJECT-TYPE
    SYNTAX      SEQUENCE  OF  BwExecutiveSPEntry
    MAX-ACCESS  not-accessible
    STATUS      current
    DESCRIPTION "Each row contains the service counters for the Executive service for each service provider in the system"
-- @feature:160554
    ::= { executive 2 }

  bwExecutiveGroupTable OBJECT-TYPE
    SYNTAX      SEQUENCE  OF  BwExecutiveGroupEntry
    MAX-ACCESS  not-accessible
    STATUS      current
    DESCRIPTION "Each row contains the service counters for the Executive service for each group in the system"
-- @feature:160554
    ::= { executive 3 }

-- Services :: Executive Service Provider...........................................

  bwExecutiveSPEntry OBJECT-TYPE
    SYNTAX      BwExecutiveSPEntry
    MAX-ACCESS  not-accessible
    STATUS      current
    DESCRIPTION
        "Each row contains the service counters for the Executive service for each service provider in the system"
    INDEX { bwExecutiveSPIndex }
-- @feature:160554
    ::= { bwExecutiveSPTable 1 }

  BwExecutiveSPEntry ::= SEQUENCE {
    bwExecutiveSPIndex            Unsigned32,
    bwExecutiveSPID               DisplayString,
    bwExecutiveSPNumCallsFiltered Counter32
    }

 bwExecutiveSPIndex OBJECT-TYPE
    SYNTAX       Unsigned32
    MAX-ACCESS   read-only
    STATUS       current
    DESCRIPTION  
        "This column represents the index of the Service Provider in the system."
-- @feature:160554
    ::= { bwExecutiveSPEntry 1 }

  bwExecutiveSPID OBJECT-TYPE
    SYNTAX       DisplayString
    MAX-ACCESS   read-only
    STATUS       current
    DESCRIPTION  
        "This string represents a Service Provider ID."
-- @feature:160554
    ::= { bwExecutiveSPEntry 2 }

 bwExecutiveSPNumCallsFiltered OBJECT-TYPE
    SYNTAX       Counter32
    MAX-ACCESS   read-write
    STATUS       current
    DESCRIPTION  
        "The number of times a call has been filtered by the Executive service for users within the service provider."
-- @feature:160554
    ::= { bwExecutiveSPEntry 3 }

-- Services :: Executive Group ...........................................

  bwExecutiveGroupEntry OBJECT-TYPE
    SYNTAX      BwExecutiveGroupEntry
    MAX-ACCESS  not-accessible
    STATUS      current
    DESCRIPTION
        "Each row contains the service counters for the Executive service for each group in the system"
    INDEX { bwExecutiveGroupIndex }
-- @feature:160554
    ::= { bwExecutiveGroupTable 1 }

  BwExecutiveGroupEntry ::= SEQUENCE {
    bwExecutiveGroupIndex            Unsigned32,
    bwExecutiveGroupID               DisplayString,
    bwExecutiveGroupNumCallsFiltered Counter32
    }

 bwExecutiveGroupIndex OBJECT-TYPE
    SYNTAX       Unsigned32
    MAX-ACCESS   read-only
    STATUS       current
    DESCRIPTION  
        "This column represents the index of the Group in the system."
-- @feature:160554
    ::= { bwExecutiveGroupEntry 1 }

  bwExecutiveGroupID OBJECT-TYPE
    SYNTAX       DisplayString
    MAX-ACCESS   read-only
    STATUS       current
    DESCRIPTION  
        "This string represents a Group ID."
-- @feature:160554
    ::= { bwExecutiveGroupEntry 2 }

 bwExecutiveGroupNumCallsFiltered OBJECT-TYPE
    SYNTAX       Counter32
    MAX-ACCESS   read-write
    STATUS       current
    DESCRIPTION  
        "The number of times a call has been filtered by the Executive service for users within the group."
-- @feature:160554
    ::= { bwExecutiveGroupEntry 3 }

-- Services :: Flexible Seating  ...........................................

 bwFlexibleSeatingAssociate OBJECT-TYPE
    SYNTAX      Counter32
    MAX-ACCESS  read-write
    STATUS      current
    DESCRIPTION
        "This counter tracks the number of times a flexible seating guest user associates with a flexible seating host."
-- @feature:114601
    ::= { flexibleseating 1 }

 bwFlexibleSeatingDisassociate OBJECT-TYPE
    SYNTAX      Counter32
    MAX-ACCESS  read-write
    STATUS      current
    DESCRIPTION
        "This counter tracks the number of times a flexible seating guest user disassociates from a flexible seating host."
-- @feature:114601
    ::= { flexibleseating 2 }

 bwFlexibleSeatingTimeout OBJECT-TYPE
    SYNTAX      Counter32
    MAX-ACCESS  read-write
    STATUS      current
    DESCRIPTION
        "This counter tracks the number of times an association between a flexible seating host and a flexible seating guest terminates due to a timeout."
-- @feature:114601
    ::= { flexibleseating 3 }

  bwFlexibleSeatingSPTable OBJECT-TYPE
    SYNTAX      SEQUENCE  OF  BwFlexibleSeatingSPEntry
    MAX-ACCESS  not-accessible
    STATUS      current
    DESCRIPTION "Each row contains the service counters for the Flexible Seating service for each service provider in the system"
-- @feature:114601
    ::= { flexibleseating 4 }

  bwFlexibleSeatingGroupTable OBJECT-TYPE
    SYNTAX      SEQUENCE  OF  BwFlexibleSeatingGroupEntry
    MAX-ACCESS  not-accessible
    STATUS      current
    DESCRIPTION "Each row contains the service counters for the Flexible Seating service for each group in the system"
-- @feature:114601
    ::= { flexibleseating 5 }

-- Services :: Flexible Seating Service Provider...........................................

  bwFlexibleSeatingSPEntry OBJECT-TYPE
    SYNTAX      BwFlexibleSeatingSPEntry
    MAX-ACCESS  not-accessible
    STATUS      current
    DESCRIPTION
        "Each row contains the service counters for the Flexible Seating service for each service provider in the system"
    INDEX { bwFlexibleSeatingSPIndex }
-- @feature:114601
    ::= { bwFlexibleSeatingSPTable 1 }

  BwFlexibleSeatingSPEntry ::= SEQUENCE {
    bwFlexibleSeatingSPIndex        Unsigned32,
    bwFlexibleSeatingSPID           DisplayString,
    bwFlexibleSeatingSPAssociate    Counter32,
    bwFlexibleSeatingSPDisassociate Counter32,
    bwFlexibleSeatingSPTimeout      Counter32
    }

 bwFlexibleSeatingSPIndex OBJECT-TYPE
    SYNTAX       Unsigned32
    MAX-ACCESS   read-only
    STATUS       current
    DESCRIPTION  
        "This column represents the index of the Service Provider in the system."
-- @feature:114601
    ::= { bwFlexibleSeatingSPEntry 1 }

  bwFlexibleSeatingSPID OBJECT-TYPE
    SYNTAX       DisplayString
    MAX-ACCESS   read-only
    STATUS       current
    DESCRIPTION  
        "This string represents a Service Provider ID."
-- @feature:114601
    ::= { bwFlexibleSeatingSPEntry 2 }

 bwFlexibleSeatingSPAssociate OBJECT-TYPE
    SYNTAX       Counter32
    MAX-ACCESS   read-write
    STATUS       current
    DESCRIPTION  
        "This counter tracks the number of times a flexible seating guest user associates with a flexible seating host within the service provider."
-- @feature:114601
    ::= { bwFlexibleSeatingSPEntry 3 }

 bwFlexibleSeatingSPDisassociate OBJECT-TYPE
    SYNTAX       Counter32
    MAX-ACCESS   read-write
    STATUS       current
    DESCRIPTION  
        "This counter tracks the number of times a flexible seating guest user disassociates from a flexible seating host within the service provider."
-- @feature:114601
    ::= { bwFlexibleSeatingSPEntry 4 }

 bwFlexibleSeatingSPTimeout OBJECT-TYPE
    SYNTAX       Counter32
    MAX-ACCESS   read-write
    STATUS       current
    DESCRIPTION  
        "This counter tracks the number of times an association between a flexible seating host and a flexible seating guest user terminates due to a timeout within the service provider."
-- @feature:114601
    ::= { bwFlexibleSeatingSPEntry 5 }

-- Services :: Flexible Seating Group ...........................................

  bwFlexibleSeatingGroupEntry OBJECT-TYPE
    SYNTAX      BwFlexibleSeatingGroupEntry
    MAX-ACCESS  not-accessible
    STATUS      current
    DESCRIPTION
        "Each row contains the service counters for the Flexible Seating service for each group in the system"
    INDEX { bwFlexibleSeatingGroupIndex }
-- @feature:114601
    ::= { bwFlexibleSeatingGroupTable 1 }

  BwFlexibleSeatingGroupEntry ::= SEQUENCE {
    bwFlexibleSeatingGroupIndex        Unsigned32,
    bwFlexibleSeatingGroupID           DisplayString,
    bwFlexibleSeatingGroupAssociate    Counter32,
    bwFlexibleSeatingGroupDisassociate Counter32,
    bwFlexibleSeatingGroupTimeout      Counter32
    }

 bwFlexibleSeatingGroupIndex OBJECT-TYPE
    SYNTAX       Unsigned32
    MAX-ACCESS   read-only
    STATUS       current
    DESCRIPTION  
        "This column represents the index of the Group in the system."
-- @feature:114601
    ::= { bwFlexibleSeatingGroupEntry 1 }

  bwFlexibleSeatingGroupID OBJECT-TYPE
    SYNTAX       DisplayString
    MAX-ACCESS   read-only
    STATUS       current
    DESCRIPTION  
        "This string represents a Group ID."
-- @feature:114601
    ::= { bwFlexibleSeatingGroupEntry 2 }

 bwFlexibleSeatingGroupAssociate OBJECT-TYPE
    SYNTAX       Counter32
    MAX-ACCESS   read-write
    STATUS       current
    DESCRIPTION  
        "This counter tracks the number of times a flexible seating guest user associates with a flexible seating guest host.  The counter tracks associations by the guest user's group."
-- @feature:114601
    ::= { bwFlexibleSeatingGroupEntry 3 }

 bwFlexibleSeatingGroupDisassociate OBJECT-TYPE
    SYNTAX       Counter32
    MAX-ACCESS   read-write
    STATUS       current
    DESCRIPTION  
        "This counter tracks the number of times a flexible seating guest user disassociates with a flexible seating guest host.  The counter tracks disassociations by the guest user's group."
-- @feature:114601
    ::= { bwFlexibleSeatingGroupEntry 4 }

 bwFlexibleSeatingGroupTimeout OBJECT-TYPE
    SYNTAX       Counter32
    MAX-ACCESS   read-write
    STATUS       current
    DESCRIPTION  
        "This counter tracks the number of times an association between a flexible seating host and a flexible seating guest user terminates due to a timeout within the guest user's group."
-- @feature:114601
    ::= { bwFlexibleSeatingGroupEntry 5 }

-- Services :: Number Portability  ...........................................

 bwNumberPortabilityDatabaseQueries OBJECT-TYPE
    SYNTAX      Counter32
    MAX-ACCESS  read-write
    STATUS      current
    DESCRIPTION
        "This counter tracks the number of times BroadWorks performs an off board number portability database query."
-- @feature:193116
    ::= { numberPortability 1 }

 bwNumberPortabilityDatabaseQueriesForOutboundCalls OBJECT-TYPE
    SYNTAX      Counter32
    MAX-ACCESS  read-write
    STATUS      current
    DESCRIPTION
        "This counter tracks the number of times BroadWorks performs an off board number portability database query for outbound calls."
-- @feature:193116
    ::= { numberPortability 2 }

 bwNumberPortabilityDatabaseQueriesForInboundCalls OBJECT-TYPE
    SYNTAX      Counter32
    MAX-ACCESS  read-write
    STATUS      current
    DESCRIPTION
        "This counter tracks the number of times BroadWorks performs an off board number portability database query for inbound calls."
-- @feature:193116
    ::= { numberPortability 3 }

 bwNumberPortabilityDatabaseResponses OBJECT-TYPE
    SYNTAX      Counter32
    MAX-ACCESS  read-write
    STATUS      current
    DESCRIPTION
        "This counter tracks the number of times BroadWorks receives a successful off board number portability database query success response."
-- @feature:193116
    ::= { numberPortability 4 }

 bwNumberPortabilityDatabaseQueriesTimeout OBJECT-TYPE
    SYNTAX      Counter32
    MAX-ACCESS  read-write
    STATUS      current
    DESCRIPTION
        "This counter tracks the number of number portability queries that have timed out."
-- @feature:193116
    ::= { numberPortability 5 }

 bwNumberPortabilityDatabaseQueriesFailure OBJECT-TYPE
    SYNTAX      Counter32
    MAX-ACCESS  read-write
    STATUS      current
    DESCRIPTION
        "This counter tracks the number of number portability queries that have failed."
-- @feature:193116
    ::= { numberPortability 6 }

-- Services :: Number Portability Announcement ...........................................

 bwNumberPortabilityAnncPhoneActivations OBJECT-TYPE
    SYNTAX      Counter32
    MAX-ACCESS  read-write
    STATUS      current
    DESCRIPTION
        "This is the number of times the Number Portability Announcement service is activated with an FAC."
-- @feature:193116
    ::= { numberPortabilityAnnc 1 }

 bwNumberPortabilityAnncPhoneDeactivations OBJECT-TYPE
    SYNTAX      Counter32
    MAX-ACCESS  read-write
    STATUS      current
    DESCRIPTION
        "This is the number of times the Number Portability Announcement service is deactivated with an FAC."
-- @feature:193116
    ::= { numberPortabilityAnnc 2 }

  bwNumberPortabilityAnncSPTable OBJECT-TYPE
    SYNTAX      SEQUENCE  OF  BwNumberPortabilityAnncSPEntry
    MAX-ACCESS  not-accessible
    STATUS      current
    DESCRIPTION "Each row contains the service counters for the Number Portability Announcement each service provider in the system"
-- @feature:193116
    ::= { numberPortabilityAnnc 3 }

  bwNumberPortabilityAnncGroupTable OBJECT-TYPE
    SYNTAX      SEQUENCE  OF  BwNumberPortabilityAnncGroupEntry
    MAX-ACCESS  not-accessible
    STATUS      current
    DESCRIPTION "Each row contains the service counters for the Number Portability Announcement for each group in the system"
-- @feature:193116
    ::= { numberPortabilityAnnc 4 }

-- Services :: Number Portability Announcement Service Provider...........................................

  bwNumberPortabilityAnncSPEntry OBJECT-TYPE
    SYNTAX      BwNumberPortabilityAnncSPEntry
    MAX-ACCESS  not-accessible
    STATUS      current
    DESCRIPTION
        "Each row contains the service counters for the Number Portability Announcement service for each service provider in the system"
    INDEX { bwNumberPortabilityAnncSPIndex }
-- @feature:193116
    ::= { bwNumberPortabilityAnncSPTable 1 }

  BwNumberPortabilityAnncSPEntry ::= SEQUENCE {
    bwNumberPortabilityAnncSPIndex              Unsigned32,
    bwNumberPortabilityAnncSPID                 DisplayString,
    bwNumberPortabilityAnncSPPhoneActivations   Counter32,
    bwNumberPortabilityAnncSPPhoneDeactivations Counter32
    }

 bwNumberPortabilityAnncSPIndex OBJECT-TYPE
    SYNTAX       Unsigned32
    MAX-ACCESS   read-only
    STATUS       current
    DESCRIPTION  
        "This column represents the index of the Service Provider in the system."
-- @feature:193116
    ::= { bwNumberPortabilityAnncSPEntry 1 }

  bwNumberPortabilityAnncSPID OBJECT-TYPE
    SYNTAX       DisplayString
    MAX-ACCESS   read-only
    STATUS       current
    DESCRIPTION  
        "This string represents a Service Provider ID."
-- @feature:193116
    ::= { bwNumberPortabilityAnncSPEntry 2 }

  bwNumberPortabilityAnncSPPhoneActivations OBJECT-TYPE
    SYNTAX       Counter32
    MAX-ACCESS   read-write
    STATUS       current
    DESCRIPTION  
        "This is the number of times the Number Portability Announcement service is activated with an FAC.  There is one instance of this counter for each service provider or enterprise defined in the system."
-- @feature:193116
    ::= { bwNumberPortabilityAnncSPEntry 3 }

  bwNumberPortabilityAnncSPPhoneDeactivations OBJECT-TYPE
    SYNTAX       Counter32
    MAX-ACCESS   read-write
    STATUS       current
    DESCRIPTION  
        "This is the number of times the Number Portability Announcement service is deactivated with an FAC.  There is one instance of this counter for each service provider or enterprise defined in the system."
-- @feature:193116
    ::= { bwNumberPortabilityAnncSPEntry 4 }

-- Services :: Number Portability Announcement Group ...........................................

  bwNumberPortabilityAnncGroupEntry OBJECT-TYPE
    SYNTAX      BwNumberPortabilityAnncGroupEntry
    MAX-ACCESS  not-accessible
    STATUS      current
    DESCRIPTION
        "Each row contains the service counters for the Number Portability Announcement service for each group in the system"
    INDEX { bwNumberPortabilityAnncGroupIndex }
-- @feature:193116
    ::= { bwNumberPortabilityAnncGroupTable 1 }

  BwNumberPortabilityAnncGroupEntry ::= SEQUENCE {
    bwNumberPortabilityAnncGroupIndex              Unsigned32,
    bwNumberPortabilityAnncGroupID                 DisplayString,
    bwNumberPortabilityAnncGroupPhoneActivations   Counter32,
    bwNumberPortabilityAnncGroupPhoneDeactivations Counter32
    }

 bwNumberPortabilityAnncGroupIndex OBJECT-TYPE
    SYNTAX       Unsigned32
    MAX-ACCESS   read-only
    STATUS       current
    DESCRIPTION  
        "This column represents the index of the Group in the system."
-- @feature:193116
    ::= { bwNumberPortabilityAnncGroupEntry 1 }

  bwNumberPortabilityAnncGroupID OBJECT-TYPE
    SYNTAX       DisplayString
    MAX-ACCESS   read-only
    STATUS       current
    DESCRIPTION  
        "This string represents a Group ID."
-- @feature:193116
    ::= { bwNumberPortabilityAnncGroupEntry 2 }

 bwNumberPortabilityAnncGroupPhoneActivations OBJECT-TYPE
    SYNTAX       Counter32
    MAX-ACCESS   read-write
    STATUS       current
    DESCRIPTION  
        "This is the number of times the Number Portability Announcement service is activated with an FAC.  There is one instance of this counter for each group defined in the system."
-- @feature:193116
    ::= { bwNumberPortabilityAnncGroupEntry 3 }

 bwNumberPortabilityAnncGroupPhoneDeactivations OBJECT-TYPE
    SYNTAX       Counter32
    MAX-ACCESS   read-write
    STATUS       current
    DESCRIPTION  
        "This is the number of times the Number Portability Announcement service is deactivated with an FAC.  There is one instance of this counter for each group defined in the system."
-- @feature:193116
    ::= { bwNumberPortabilityAnncGroupEntry 4 }

-- Services :: Personal Assistant ...........................................

 bwPersonalAssistantActivations OBJECT-TYPE
    SYNTAX      Counter32
    MAX-ACCESS  read-write
    STATUS      current
    DESCRIPTION
        "This counter tracks the number of times the Personal Assistant service was invoked for a given user."
-- @feature:204023
    ::= { personalAssistant 1 }

  bwPersonalAssistantSPTable OBJECT-TYPE
    SYNTAX      SEQUENCE  OF  BwPersonalAssistantSPEntry
    MAX-ACCESS  not-accessible
    STATUS      current
    DESCRIPTION "Each row contains the service counters for the Personal Assistant each service provider in the system"
-- @feature:204023
    ::= { personalAssistant 2 }

  bwPersonalAssistantGroupTable OBJECT-TYPE
    SYNTAX      SEQUENCE  OF  BwPersonalAssistantGroupEntry
    MAX-ACCESS  not-accessible
    STATUS      current
    DESCRIPTION "Each row contains the service counters for the Personal Assistant for each group in the system"
-- @feature:204023
    ::= { personalAssistant 3 }

-- Services :: Personal Assistant Service Provider ...........................................

  bwPersonalAssistantSPEntry OBJECT-TYPE
    SYNTAX      BwPersonalAssistantSPEntry
    MAX-ACCESS  not-accessible
    STATUS      current
    DESCRIPTION
        "Each row contains the service counters for the Personal Assistant service for each service provider in the system"
    INDEX { bwPersonalAssistantSPIndex }
-- @feature:204023
    ::= { bwPersonalAssistantSPTable 1 }

  BwPersonalAssistantSPEntry ::= SEQUENCE {
    bwPersonalAssistantSPIndex         Unsigned32,
    bwPersonalAssistantSPID            DisplayString,
    bwPersonalAssistantSPActivations   Counter32
    }

 bwPersonalAssistantSPIndex OBJECT-TYPE
    SYNTAX       Unsigned32
    MAX-ACCESS   read-only
    STATUS       current
    DESCRIPTION  
        "This column represents the index of the Service Provider in the system."
-- @feature:204023
    ::= { bwPersonalAssistantSPEntry 1 }

  bwPersonalAssistantSPID OBJECT-TYPE
    SYNTAX       DisplayString
    MAX-ACCESS   read-only
    STATUS       current
    DESCRIPTION  
        "This string represents a Service Provider ID."
-- @feature:204023
    ::= { bwPersonalAssistantSPEntry 2 }

  bwPersonalAssistantSPActivations OBJECT-TYPE
    SYNTAX       Counter32
    MAX-ACCESS   read-write
    STATUS       current
    DESCRIPTION  
        "This counter tracks the number of times the Personal Assistant service was invoked per service provider."
-- @feature:204023
    ::= { bwPersonalAssistantSPEntry 3 }

-- Services :: Personal Assistant Group ...........................................

  bwPersonalAssistantGroupEntry OBJECT-TYPE
    SYNTAX      BwPersonalAssistantGroupEntry
    MAX-ACCESS  not-accessible
    STATUS      current
    DESCRIPTION
        "Each row contains the service counters for the Personal Assistant service for each group in the system"
    INDEX { bwPersonalAssistantGroupIndex }
-- @feature:204023
    ::= { bwPersonalAssistantGroupTable 1 }

  BwPersonalAssistantGroupEntry ::= SEQUENCE {
    bwPersonalAssistantGroupIndex        Unsigned32,
    bwPersonalAssistantGroupID           DisplayString,
    bwPersonalAssistantGroupActivations  Counter32
    }

 bwPersonalAssistantGroupIndex OBJECT-TYPE
    SYNTAX       Unsigned32
    MAX-ACCESS   read-only
    STATUS       current
    DESCRIPTION  
        "This column represents the index of the Group in the system."
-- @feature:204023
    ::= { bwPersonalAssistantGroupEntry 1 }

  bwPersonalAssistantGroupID OBJECT-TYPE
    SYNTAX       DisplayString
    MAX-ACCESS   read-only
    STATUS       current
    DESCRIPTION  
        "This string represents a Group ID."
-- @feature:204023
    ::= { bwPersonalAssistantGroupEntry 2 }

 bwPersonalAssistantGroupActivations OBJECT-TYPE
    SYNTAX       Counter32
    MAX-ACCESS   read-write
    STATUS       current
    DESCRIPTION  
        "This counter tracks the number of times the Personal Assistant service was invoked per group."
-- @feature:204023
    ::= { bwPersonalAssistantGroupEntry 3 }

-- Services :: Collaborate ...........................................

 bwCollaborateNumActiveMyRooms OBJECT-TYPE
    SYNTAX      Gauge32
    MAX-ACCESS  read-only
    STATUS      current
    DESCRIPTION
        "This gauge tracks the number of active 'MyRoom'."
-- @feature:214095
    ::= { collaborate 1 }

 bwCollaborateNumActiveInstantRooms OBJECT-TYPE
    SYNTAX      Gauge32
    MAX-ACCESS  read-only
    STATUS      current
    DESCRIPTION
        "This gauge tracks the total number of active 'Instant Room(s)'."
-- @feature:214095
    ::= { collaborate 2 }

 bwCollaborateNumActiveProjectRooms OBJECT-TYPE
    SYNTAX      Gauge32
    MAX-ACCESS  read-only
    STATUS      current
    DESCRIPTION
        "This gauge tracks the total number of active 'ProjectRoom(s)'."
-- @feature:214095
    ::= { collaborate 3 }

 bwCollaborateNumActiveAudioPorts OBJECT-TYPE
    SYNTAX      Gauge32
    MAX-ACCESS  read-only
    STATUS      current
    DESCRIPTION
        "This gauge tracks the total number of active collaborate audio ports."
-- @feature:214095
    ::= { collaborate 4 }

 bwCollaborateNumActiveVideoPorts OBJECT-TYPE
    SYNTAX      Gauge32
    MAX-ACCESS  read-only
    STATUS      current
    DESCRIPTION
        "This gauge tracks the total number of active collaborate video ports."
-- @feature:214095
    ::= { collaborate 5 }

 bwCollaborateTotalSessions OBJECT-TYPE
    SYNTAX      Counter32
    MAX-ACCESS  read-write
    STATUS      current
    DESCRIPTION
        "This counter tracks the number of times collaborate session is created."
-- @feature:214095
    ::= { collaborate 6 }

 bwCollaborateVideoEnabledSessions OBJECT-TYPE
    SYNTAX      Counter32
    MAX-ACCESS  read-write
    STATUS      current
    DESCRIPTION
        "This counter tracks the number of times video enabled collaborate session is created. Video enabled collaborate sessions are session that owned by a subscriber who has 'collaborate-video' service."
-- @feature:214095
    ::= { collaborate 7 }

 bwCollaborateTotalDuration OBJECT-TYPE
    SYNTAX      Counter32
    MAX-ACCESS  read-write
    STATUS      current
    DESCRIPTION
        "This counter tracks the total duration (in seconds) of all collaborate sessions."
-- @feature:214095
    ::= { collaborate 8 }

 bwCollaborateNumVideoParticipantsDowngradedToAudio OBJECT-TYPE
    SYNTAX      Counter32
    MAX-ACCESS  read-write
    STATUS      current
    DESCRIPTION
        "This counter tracks the number of participant tries to join collaborate session with video but got downgraded to audio."
-- @feature:214095
    ::= { collaborate 9 }

 bwCollaborateNumInvalidRoomIDJoinFailures OBJECT-TYPE
    SYNTAX      Counter32
    MAX-ACCESS  read-write
    STATUS      current
    DESCRIPTION
        "This counter tracks the number of participants failed to join collaborate session due to invalid room ID."
-- @feature:214095
    ::= { collaborate 10 }

 bwCollaborateNumSessionCreationFailures OBJECT-TYPE
    SYNTAX      Counter32
    MAX-ACCESS  read-write
    STATUS      current
    DESCRIPTION
        "This counter tracks the number of times a conference session failed to be created."
-- @feature:214095
    ::= { collaborate 11 }

 bwCollaborateNumNoResourceJoinFailures OBJECT-TYPE
    SYNTAX      Counter32
    MAX-ACCESS  read-write
    STATUS      current
    DESCRIPTION
        "This counter tracks the number of times participant failed to be joined into collaborate session due to resource issues."
-- @feature:214095
    ::= { collaborate 12 }

 bwCollaborateNumOutDialFailures OBJECT-TYPE
    SYNTAX      Counter32
    MAX-ACCESS  read-write
    STATUS      current
    DESCRIPTION
        "This counter tracks the number failed out dial attempts."
-- @feature:214095
    ::= { collaborate 13 }

 bwCollaborateSPTable OBJECT-TYPE
    SYNTAX      SEQUENCE  OF  BwCollaborateSPEntry
    MAX-ACCESS  not-accessible
    STATUS      current
    DESCRIPTION "Each row contains the service counters for the Collaborate for each service provider in the system"
-- @feature:214095
    ::= { collaborate 14 }

  bwCollaborateGroupTable OBJECT-TYPE
    SYNTAX      SEQUENCE  OF  BwCollaborateGroupEntry
    MAX-ACCESS  not-accessible
    STATUS      current
    DESCRIPTION "Each row contains the service counters for the Collaborate for each group in the system"
-- @feature:214095
    ::= { collaborate 15 }

-- Services :: Personal Assistant Service Provider ...........................................

  bwCollaborateSPEntry OBJECT-TYPE
    SYNTAX      BwCollaborateSPEntry
    MAX-ACCESS  not-accessible
    STATUS      current
    DESCRIPTION
        "Each row contains the service counters for the Personal Assistant service for each service provider in the system"
    INDEX { bwCollaborateSPIndex }
-- @feature:214095
    ::= { bwCollaborateSPTable 1 }

  BwCollaborateSPEntry ::= SEQUENCE {
    bwCollaborateSPIndex                                 Unsigned32,
    bwCollaborateSPID                                    DisplayString,
    bwCollaborateSPNumActiveMyRooms                      Gauge32,
    bwCollaborateSPNumActiveInstantRooms                 Gauge32,
    bwCollaborateSPNumActiveProjectRooms                 Gauge32,
    bwCollaborateSPNumActiveAudioPorts                   Gauge32,
    bwCollaborateSPNumActiveVideoPorts                   Gauge32,
    bwCollaborateSPTotalSessions                         Counter32,
    bwCollaborateSPVideoEnabledSessions                  Counter32,
    bwCollaborateSPTotalDuration                         Counter32,
    bwCollaborateSPNumVideoParticipantsDowngradedToAudio Counter32,
    bwCollaborateSPNumInvalidRoomIDJoinFailures          Counter32,
    bwCollaborateSPNumSessionCreationFailures            Counter32,
    bwCollaborateSPNumNoResourceJoinFailures             Counter32,
    bwCollaborateSPNumOutDialFailures                    Counter32
    }

 bwCollaborateSPIndex OBJECT-TYPE
    SYNTAX       Unsigned32
    MAX-ACCESS   read-only
    STATUS       current
    DESCRIPTION  
        "This column represents the index of the Service Provider in the system."
-- @feature:214095
    ::= { bwCollaborateSPEntry 1 }

  bwCollaborateSPID OBJECT-TYPE
    SYNTAX       DisplayString
    MAX-ACCESS   read-only
    STATUS       current
    DESCRIPTION  
        "This string represents a Service Provider ID."
-- @feature:214095
    ::= { bwCollaborateSPEntry 2 }

  bwCollaborateSPNumActiveMyRooms OBJECT-TYPE
    SYNTAX       Gauge32
    MAX-ACCESS   read-only
    STATUS       current
    DESCRIPTION  
        "This gauge tracks the number of active 'MyRoom(s)' for a service provider."
-- @feature:214095
    ::= { bwCollaborateSPEntry 3 }

  bwCollaborateSPNumActiveInstantRooms OBJECT-TYPE
    SYNTAX       Gauge32
    MAX-ACCESS   read-only
    STATUS       current
    DESCRIPTION  
        "This gauge tracks the number of active 'Instant Room(s)' for a service provider."
-- @feature:214095
    ::= { bwCollaborateSPEntry 4 }

  bwCollaborateSPNumActiveProjectRooms OBJECT-TYPE
    SYNTAX       Gauge32
    MAX-ACCESS   read-only
    STATUS       current
    DESCRIPTION  
        "This gauge tracks the number of active 'ProjectRoom(s)' for a service provider."
-- @feature:214095
    ::= { bwCollaborateSPEntry 5 }

  bwCollaborateSPNumActiveAudioPorts OBJECT-TYPE
    SYNTAX       Gauge32
    MAX-ACCESS   read-only
    STATUS       current
    DESCRIPTION  
        "This gauge tracks the number of active collaborate audio ports for a service provider."
-- @feature:214095
    ::= { bwCollaborateSPEntry 6 }

  bwCollaborateSPNumActiveVideoPorts OBJECT-TYPE
    SYNTAX       Gauge32
    MAX-ACCESS   read-only
    STATUS       current
    DESCRIPTION  
        "This gauge tracks the number of active collaborate video ports for a service provider."
-- @feature:214095
    ::= { bwCollaborateSPEntry 7 }

  bwCollaborateSPTotalSessions OBJECT-TYPE
    SYNTAX       Counter32
    MAX-ACCESS   read-write
    STATUS       current
    DESCRIPTION  
        "This counter tracks the number of times collaborate session is created for a service provider."
-- @feature:214095
    ::= { bwCollaborateSPEntry 8 }

  bwCollaborateSPVideoEnabledSessions OBJECT-TYPE
    SYNTAX       Counter32
    MAX-ACCESS   read-write
    STATUS       current
    DESCRIPTION  
        "This counter tracks the number of times video enabled collaborate session is created a service provider. Video enabled collaborate sessions are session that owned by a subscriber who has 'collaborate-video' service."
-- @feature:214095
    ::= { bwCollaborateSPEntry 9 }

  bwCollaborateSPTotalDuration OBJECT-TYPE
    SYNTAX       Counter32
    MAX-ACCESS   read-write
    STATUS       current
    DESCRIPTION  
        "This counter tracks the total duration (in seconds) of all collaborate sessions for a service provider."
-- @feature:214095
    ::= { bwCollaborateSPEntry 10 }

  bwCollaborateSPNumVideoParticipantsDowngradedToAudio OBJECT-TYPE
    SYNTAX       Counter32
    MAX-ACCESS   read-write
    STATUS       current
    DESCRIPTION  
        "This counter tracks the number of participant tries to join collaborate session with video but got downgraded to audio for a service provider."
-- @feature:214095
    ::= { bwCollaborateSPEntry 11 }

  bwCollaborateSPNumInvalidRoomIDJoinFailures OBJECT-TYPE
    SYNTAX       Counter32
    MAX-ACCESS   read-write
    STATUS       current
    DESCRIPTION  
        "This counter tracks the number of participants failed to join collaborate session due to invalid room ID for a service provider."
-- @feature:214095
    ::= { bwCollaborateSPEntry 12 }

  bwCollaborateSPNumSessionCreationFailures OBJECT-TYPE
    SYNTAX       Counter32
    MAX-ACCESS   read-write
    STATUS       current
    DESCRIPTION  
        "This counter tracks the number of times a conference session failed to be created for a service provider."
-- @feature:214095
    ::= { bwCollaborateSPEntry 13 }

  bwCollaborateSPNumNoResourceJoinFailures OBJECT-TYPE
    SYNTAX       Counter32
    MAX-ACCESS   read-write
    STATUS       current
    DESCRIPTION  
        "This counter tracks the number of times participant failed to be joined into collaborate session due to resource issues for a service provider."
-- @feature:214095
    ::= { bwCollaborateSPEntry 14 }

  bwCollaborateSPNumOutDialFailures OBJECT-TYPE
    SYNTAX       Counter32
    MAX-ACCESS   read-write
    STATUS       current
    DESCRIPTION  
        "This counter tracks the number failed out dial attempts for a service provider."
-- @feature:214095
    ::= { bwCollaborateSPEntry 15 }

-- Services :: Personal Assistant Group ...........................................

  bwCollaborateGroupEntry OBJECT-TYPE
    SYNTAX      BwCollaborateGroupEntry
    MAX-ACCESS  not-accessible
    STATUS      current
    DESCRIPTION
        "Each row contains the service counters for the Collaborate service for each group in the system"
    INDEX { bwCollaborateGroupIndex }
-- @feature:214095
    ::= { bwCollaborateGroupTable 1 }

  BwCollaborateGroupEntry ::= SEQUENCE {
    bwCollaborateGroupIndex                                 Unsigned32,
    bwCollaborateGroupID                                    DisplayString,
    bwCollaborateGroupNumActiveMyRooms                      Gauge32,
    bwCollaborateGroupNumActiveInstantRooms                 Gauge32,
    bwCollaborateGroupNumActiveProjectRooms                 Gauge32,
    bwCollaborateGroupNumActiveAudioPorts                   Gauge32,
    bwCollaborateGroupNumActiveVideoPorts                   Gauge32,
    bwCollaborateGroupTotalSessions                         Counter32,
    bwCollaborateGroupVideoEnabledSessions                  Counter32,
    bwCollaborateGroupTotalDuration                         Counter32,
    bwCollaborateGroupNumVideoParticipantsDowngradedToAudio Counter32,
    bwCollaborateGroupNumInvalidRoomIDJoinFailures          Counter32,
    bwCollaborateGroupNumSessionCreationFailures            Counter32,
    bwCollaborateGroupNumNoResourceJoinFailures             Counter32,
    bwCollaborateGroupNumOutDialFailures                    Counter32
    }

 bwCollaborateGroupIndex OBJECT-TYPE
    SYNTAX       Unsigned32
    MAX-ACCESS   read-only
    STATUS       current
    DESCRIPTION  
        "This column represents the index of the Group in the system."
-- @feature:214095
    ::= { bwCollaborateGroupEntry 1 }

  bwCollaborateGroupID OBJECT-TYPE
    SYNTAX       DisplayString
    MAX-ACCESS   read-only
    STATUS       current
    DESCRIPTION  
        "This string represents a Group ID."
-- @feature:214095
    ::= { bwCollaborateGroupEntry 2 }

  bwCollaborateGroupNumActiveMyRooms OBJECT-TYPE
    SYNTAX       Gauge32
    MAX-ACCESS   read-only
    STATUS       current
    DESCRIPTION  
        "This gauge tracks the number of active 'MyRoom(s)' for a group."
-- @feature:214095
    ::= { bwCollaborateGroupEntry 3 }

  bwCollaborateGroupNumActiveInstantRooms OBJECT-TYPE
    SYNTAX       Gauge32
    MAX-ACCESS   read-only
    STATUS       current
    DESCRIPTION  
        "This gauge tracks the number of active 'Instant Room(s)' for a group."
-- @feature:214095
    ::= { bwCollaborateGroupEntry 4 }

  bwCollaborateGroupNumActiveProjectRooms OBJECT-TYPE
    SYNTAX       Gauge32
    MAX-ACCESS   read-only
    STATUS       current
    DESCRIPTION  
        "This gauge tracks the number of active 'ProjectRoom(s)' for a group."
-- @feature:214095
    ::= { bwCollaborateGroupEntry 5 }

  bwCollaborateGroupNumActiveAudioPorts OBJECT-TYPE
    SYNTAX       Gauge32
    MAX-ACCESS   read-only
    STATUS       current
    DESCRIPTION  
        "This gauge tracks the number of active collaborate audio ports for a group."
-- @feature:214095
    ::= { bwCollaborateGroupEntry 6 }

  bwCollaborateGroupNumActiveVideoPorts OBJECT-TYPE
    SYNTAX       Gauge32
    MAX-ACCESS   read-only
    STATUS       current
    DESCRIPTION  
        "This gauge tracks the number of active collaborate video ports for a group."
-- @feature:214095
    ::= { bwCollaborateGroupEntry 7 }

  bwCollaborateGroupTotalSessions OBJECT-TYPE
    SYNTAX       Counter32
    MAX-ACCESS   read-write
    STATUS       current
    DESCRIPTION  
        "This counter tracks the number of times collaborate session is created for a group."
-- @feature:214095
    ::= { bwCollaborateGroupEntry 8 }

  bwCollaborateGroupVideoEnabledSessions OBJECT-TYPE
    SYNTAX       Counter32
    MAX-ACCESS   read-write
    STATUS       current
    DESCRIPTION  
        "This counter tracks the number of times video enabled collaborate session is created a group. Video enabled collaborate sessions are session that owned by a subscriber who has 'collaborate-video' service."
-- @feature:214095
    ::= { bwCollaborateGroupEntry 9 }

  bwCollaborateGroupTotalDuration OBJECT-TYPE
    SYNTAX       Counter32
    MAX-ACCESS   read-write
    STATUS       current
    DESCRIPTION  
        "This counter tracks the total duration (in seconds) of all collaborate sessions for a group."
-- @feature:214095
    ::= { bwCollaborateGroupEntry 10 }

  bwCollaborateGroupNumVideoParticipantsDowngradedToAudio OBJECT-TYPE
    SYNTAX       Counter32
    MAX-ACCESS   read-write
    STATUS       current
    DESCRIPTION  
        "This counter tracks the number of participant tries to join collaborate session with video but got downgraded to audio for a group."
-- @feature:214095
    ::= { bwCollaborateGroupEntry 11 }

  bwCollaborateGroupNumInvalidRoomIDJoinFailures OBJECT-TYPE
    SYNTAX       Counter32
    MAX-ACCESS   read-write
    STATUS       current
    DESCRIPTION  
        "This counter tracks the number of participants failed to join collaborate session due to invalid room ID for a group."
-- @feature:214095
    ::= { bwCollaborateGroupEntry 12 }

  bwCollaborateGroupNumSessionCreationFailures OBJECT-TYPE
    SYNTAX       Counter32
    MAX-ACCESS   read-write
    STATUS       current
    DESCRIPTION  
        "This counter tracks the number of times a conference session failed to be created for a group."
-- @feature:214095
    ::= { bwCollaborateGroupEntry 13 }

  bwCollaborateGroupNumNoResourceJoinFailures OBJECT-TYPE
    SYNTAX       Counter32
    MAX-ACCESS   read-write
    STATUS       current
    DESCRIPTION  
        "This counter tracks the number of times participant failed to be joined into collaborate session due to resource issues for a group."
-- @feature:214095
    ::= { bwCollaborateGroupEntry 14 }

  bwCollaborateGroupNumOutDialFailures OBJECT-TYPE
    SYNTAX       Counter32
    MAX-ACCESS   read-write
    STATUS       current
    DESCRIPTION  
        "This counter tracks the number failed out dial attempts for a group."
-- @feature:214095
    ::= { bwCollaborateGroupEntry 15 }

-- Services :: Call Forwarding Always Secondary  ...........................................

  bwCFASNumForwarded OBJECT-TYPE
    SYNTAX      Counter32
    MAX-ACCESS  read-write
    STATUS      current
    DESCRIPTION 
        "This counter reflects the number of calls forwarded by Call Forwarding Always Secondary service."
    ::= { callForwardingAlwaysSecondary 1 }

  bwCallForwardingAlwaysSecondarySPTable OBJECT-TYPE
    SYNTAX      SEQUENCE OF BwCallForwardingAlwaysSecondarySPEntry
    MAX-ACCESS  not-accessible
    STATUS      current
    DESCRIPTION 
        "This table contains the counters for Call Forwarding Always Secondary service measurements for service providers"
    ::= { callForwardingAlwaysSecondary 2 }

  bwCallForwardingAlwaysSecondarySPEntry OBJECT-TYPE
    SYNTAX      BwCallForwardingAlwaysSecondarySPEntry
    MAX-ACCESS  not-accessible
    STATUS      current
    DESCRIPTION 
        "This row contains the counters for Call Forwarding Always Secondary service measurements for a service provider"
    INDEX       { bwCallForwardingAlwaysSecondarySPIndex }
    ::= { bwCallForwardingAlwaysSecondarySPTable 1 }

  BwCallForwardingAlwaysSecondarySPEntry ::= SEQUENCE {
    bwCallForwardingAlwaysSecondarySPIndex   Unsigned32,
    bwCallForwardingAlwaysSecondarySPID      DisplayString,
    bwCFASSPNumForwarded                     Counter32
  }

  bwCallForwardingAlwaysSecondarySPIndex OBJECT-TYPE
    SYNTAX      Unsigned32
    MAX-ACCESS  read-only
    STATUS      current
    DESCRIPTION 
        "This integer represents the a service provider index in the system"
    ::= { bwCallForwardingAlwaysSecondarySPEntry 1 }

  bwCallForwardingAlwaysSecondarySPID OBJECT-TYPE
    SYNTAX      DisplayString
    MAX-ACCESS  read-only
    STATUS      current
    DESCRIPTION 
        "This string represents a service provider ID"
    ::= { bwCallForwardingAlwaysSecondarySPEntry 2 }

  bwCFASSPNumForwarded OBJECT-TYPE
    SYNTAX      Counter32
    MAX-ACCESS  read-write
    STATUS      current
    DESCRIPTION 
        "This counter reflects the number of calls forwarded by Call Forwarding Always Secondary service for a service provider."
    ::= { bwCallForwardingAlwaysSecondarySPEntry 3 }

  bwCallForwardingAlwaysSecondaryGroupTable OBJECT-TYPE
    SYNTAX      SEQUENCE OF BwCallForwardingAlwaysSecondaryGroupEntry
    MAX-ACCESS  not-accessible
    STATUS      current
    DESCRIPTION 
        "This table contains the counters for Call Forwarding Always Secondary service measurements for groups"
    ::= { callForwardingAlwaysSecondary 3 }

  bwCallForwardingAlwaysSecondaryGroupEntry OBJECT-TYPE
    SYNTAX      BwCallForwardingAlwaysSecondaryGroupEntry
    MAX-ACCESS  not-accessible
    STATUS      current
    DESCRIPTION 
        "This row contains the counters for Call Forwarding Always Secondary service measurements for a group"
    INDEX       { bwCallForwardingAlwaysSecondaryGroupIndex }
    ::= { bwCallForwardingAlwaysSecondaryGroupTable 1 }

  BwCallForwardingAlwaysSecondaryGroupEntry ::= SEQUENCE {
    bwCallForwardingAlwaysSecondaryGroupIndex    Unsigned32,
    bwCallForwardingAlwaysSecondaryGroupID       DisplayString,
    bwCFASGroupNumForwarded                      Counter32
  }

  bwCallForwardingAlwaysSecondaryGroupIndex OBJECT-TYPE
    SYNTAX      Unsigned32
    MAX-ACCESS  read-only
    STATUS      current
    DESCRIPTION 
        "This integer represents the a group index in the system"
    ::= { bwCallForwardingAlwaysSecondaryGroupEntry 1 }

  bwCallForwardingAlwaysSecondaryGroupID OBJECT-TYPE
    SYNTAX      DisplayString
    MAX-ACCESS  read-only
    STATUS      current
    DESCRIPTION 
        "This string represents a group ID"
    ::= { bwCallForwardingAlwaysSecondaryGroupEntry 2 }

  bwCFASGroupNumForwarded OBJECT-TYPE
    SYNTAX      Counter32
    MAX-ACCESS  read-write
    STATUS      current
    DESCRIPTION 
        "This counter reflects the number of calls forwarded by Call Forwarding Always Secondary service for a group."
    ::= { bwCallForwardingAlwaysSecondaryGroupEntry 3 }

-- Protocol :: MSS  ...........................................

bwNSqueryRequestsTransmitted OBJECT-TYPE
    SYNTAX      Counter32
    MAX-ACCESS  read-write
    STATUS      current
    DESCRIPTION
        "incremented each time a Media Server selection query transmission is attempted toward a Network Server"
    ::= { mssStats 1 }

  bwNSqueryCommFailures OBJECT-TYPE
    SYNTAX      Counter32
    MAX-ACCESS  read-write
    STATUS      current
    DESCRIPTION
        "This counter is incremented when Media Server selection query has been transmitted toward all available Network Servers and no response has been received from any Network Server."
    ::= { mssStats 3 }

-- Protocol :: NRS  ...........................................

  bwNbInvalidMessagesReceived OBJECT-TYPE
    SYNTAX      Counter32
    MAX-ACCESS  read-write
    STATUS      current
    DESCRIPTION 
        "This counter is incremented when an invalid NRS message is received (either the header was valid but the body was not, or the message was pure junk)"
    ::= { nrsStats 6 }

  bwNbRequestsReceived OBJECT-TYPE
    SYNTAX      Counter32
    MAX-ACCESS  read-write
    STATUS      current
    DESCRIPTION 
        "This counter is incremented when a NRS request is received"
    ::= { nrsStats 7 }

  bwNbResponsesReceived OBJECT-TYPE
    SYNTAX      Counter32
    MAX-ACCESS  read-write
    STATUS      current
    DESCRIPTION 
        "This counter is incremented when a NRS response is received"
    ::= { nrsStats 8 }

  bwNbErrorsReceived OBJECT-TYPE
    SYNTAX      Counter32
    MAX-ACCESS  read-write
    STATUS      current
    DESCRIPTION 
        "This counter is incremented when a NRS error is received"
    ::= { nrsStats 9 }

  bwNbRequestsSent OBJECT-TYPE
    SYNTAX      Counter32
    MAX-ACCESS  read-write
    STATUS      current
    DESCRIPTION 
        "This counter is incremented when a NRS request is sent"
    ::= { nrsStats 10 }

  bwNbResponsesSent OBJECT-TYPE
    SYNTAX      Counter32
    MAX-ACCESS  read-write
    STATUS      current
    DESCRIPTION 
        "This counter is incremented when a NRS response is sent"
    ::= { nrsStats 11 }

  bwNbErrorsSent OBJECT-TYPE
    SYNTAX      Counter32
    MAX-ACCESS  read-write
    STATUS      current
    DESCRIPTION 
        "This counter is incremented when a NRS error is sent"
    ::= { nrsStats 12 }

  bwNbRequestsResent OBJECT-TYPE
    SYNTAX      Counter32
    MAX-ACCESS  read-write
    STATUS      current
    DESCRIPTION 
        "This counter is incremented when a NRS request is re-sent"
    ::= { nrsStats 13 }

  bwNbResponsesResent OBJECT-TYPE
    SYNTAX      Counter32
    MAX-ACCESS  read-write
    STATUS      current
    DESCRIPTION 
        "This counter is incremented when a NRS response is re-sent"
    ::= { nrsStats 14 }

  bwNbRequestsUnanswered OBJECT-TYPE
    SYNTAX      Counter32
    MAX-ACCESS  read-write
    STATUS      current
    DESCRIPTION 
        "This counter is incremented when a NRS request remains unanswered after a series of retries"
    ::= { nrsStats 15 }

  bwNRSStatsTable OBJECT-TYPE
    SYNTAX      SEQUENCE OF BwNRSStatsEntry
    MAX-ACCESS  not-accessible
    STATUS      current
    DESCRIPTION 
        "This table contains the counters for all NRS protocols"
    ::= { nrsStats 16 }

  bwNRSStatsEntry OBJECT-TYPE
    SYNTAX      BwNRSStatsEntry
    MAX-ACCESS  not-accessible
    STATUS      current
    DESCRIPTION 
        "This row contains information on a particular NRS protocol"
    INDEX       { bwNRSStatsTableIndex }
    ::= { bwNRSStatsTable 1 }

  BwNRSStatsEntry ::= SEQUENCE {
    bwNRSStatsTableIndex                    Unsigned32,
    bwNRSStatsTableProtocolName             DisplayString,
    bwNRSStatsTableNbRequestsReceived       Counter32,
    bwNRSStatsTableNbResponsesReceived      Counter32,
    bwNRSStatsTableNbErrorsReceived         Counter32,
    bwNRSStatsTableNbRequestsSent           Counter32,
    bwNRSStatsTableNbResponsesSent          Counter32,
    bwNRSStatsTableNbErrorsSent             Counter32,
    bwNRSStatsTableNbRequestsResent         Counter32,
    bwNRSStatsTableNbResponsesResent        Counter32,
    bwNRSStatsTableNbRequestsUnanswered     Counter32
  }

  bwNRSStatsTableIndex OBJECT-TYPE
    SYNTAX      Unsigned32
    MAX-ACCESS  not-accessible
    STATUS      current
    DESCRIPTION 
        "This integer represents a NRS protocol status code.  The rest of the information in this row is related to this value."
    ::= { bwNRSStatsEntry 1 }

  bwNRSStatsTableProtocolName OBJECT-TYPE
    SYNTAX      DisplayString
    MAX-ACCESS  read-only
    STATUS      current
    DESCRIPTION 
        "This string represents the NRS protocol name"
    ::= { bwNRSStatsEntry 2 }

  bwNRSStatsTableNbRequestsReceived OBJECT-TYPE
    SYNTAX      Counter32
    MAX-ACCESS  read-write
    STATUS      current
    DESCRIPTION 
        "This counter is incremented when a request is received"
    ::= { bwNRSStatsEntry 3 }

  bwNRSStatsTableNbResponsesReceived OBJECT-TYPE
    SYNTAX      Counter32
    MAX-ACCESS  read-write
    STATUS      current
    DESCRIPTION 
        "This counter is incremented when a response is received"
    ::= { bwNRSStatsEntry 4 }

  bwNRSStatsTableNbErrorsReceived OBJECT-TYPE
    SYNTAX      Counter32
    MAX-ACCESS  read-write
    STATUS      current
    DESCRIPTION 
        "This counter is incremented when an error is received"
    ::= { bwNRSStatsEntry 5 }

  bwNRSStatsTableNbRequestsSent OBJECT-TYPE
    SYNTAX      Counter32
    MAX-ACCESS  read-write
    STATUS      current
    DESCRIPTION 
        "This counter is incremented when a request is sent"
    ::= { bwNRSStatsEntry 6 }

  bwNRSStatsTableNbResponsesSent OBJECT-TYPE
    SYNTAX      Counter32
    MAX-ACCESS  read-write
    STATUS      current
    DESCRIPTION 
        "This counter is incremented when a response is sent"
    ::= { bwNRSStatsEntry 7 }

  bwNRSStatsTableNbErrorsSent OBJECT-TYPE
    SYNTAX      Counter32
    MAX-ACCESS  read-write
    STATUS      current
    DESCRIPTION 
        "This counter is incremented when an error is sent"
    ::= { bwNRSStatsEntry 8 }

  bwNRSStatsTableNbRequestsResent OBJECT-TYPE
    SYNTAX      Counter32
    MAX-ACCESS  read-write
    STATUS      current
    DESCRIPTION 
        "This counter is incremented when a request is re-sent"
    ::= { bwNRSStatsEntry 9 }

  bwNRSStatsTableNbResponsesResent OBJECT-TYPE
    SYNTAX      Counter32
    MAX-ACCESS  read-write
    STATUS      current
    DESCRIPTION 
        "This counter is incremented when a response is re-sent"
    ::= { bwNRSStatsEntry 10 }

  bwNRSStatsTableNbRequestsUnanswered OBJECT-TYPE
    SYNTAX      Counter32
    MAX-ACCESS  read-write
    STATUS      current
    DESCRIPTION 
        "This counter is incremented when a request remains unanswered after a series of retries"
    ::= { bwNRSStatsEntry 11 }

-- Protocol :: Protocol Monitor  ...........................................

  bwPMTNumMonitorsCreated OBJECT-TYPE
    SYNTAX      Counter32
    MAX-ACCESS  read-write
    STATUS      current
    DESCRIPTION 
        "This counter is incremented when a monitor is created"
    ::= { pmtStats 1 }

  bwPMTNumMonitorsOpen OBJECT-TYPE
    SYNTAX      Gauge32
    MAX-ACCESS  read-only
    STATUS      current
    DESCRIPTION 
        "Number of open monitors in the system"
    ::= { pmtStats 2 }

  bwPMTNumLoggerCreated OBJECT-TYPE
    SYNTAX      Counter32
    MAX-ACCESS  read-write
    STATUS      current
    DESCRIPTION 
        "This counter is incremented when a logger registers"
    ::= { pmtStats 3 }

  bwPMTNumLoggerOpen OBJECT-TYPE
    SYNTAX      Gauge32
    MAX-ACCESS  read-only
    STATUS      current
    DESCRIPTION 
        "The number of loggers registered in the system"
    ::= { pmtStats 4 }

-- system statistics ...........................................

  bwSystemName OBJECT-TYPE
    SYNTAX      DisplayString
    MAX-ACCESS  read-only
    STATUS      current
    DESCRIPTION 
        "Gives the BroadWorks system name"
    ::= { systemStats 1 }

  bwNumberOfUsers OBJECT-TYPE
    SYNTAX      Gauge32
    MAX-ACCESS  read-only
    STATUS      current
    DESCRIPTION 
        "Gives the total of users configured on the BroadWorks system"
    ::= { systemStats 2 }

  bwNumberOfGroups OBJECT-TYPE
    SYNTAX      Gauge32
    MAX-ACCESS  read-only
    STATUS      current
    DESCRIPTION 
        "Gives the total of groups configured on the BroadWorks system"
    ::= { systemStats 3 }

  bwNumberOfServProv OBJECT-TYPE
    SYNTAX      Gauge32
    MAX-ACCESS  read-only
    STATUS      current
    DESCRIPTION 
        "Gives the total of groups configured on the BroadWorks system"
    ::= { systemStats 4 }

  bwNumberOfDNDefined OBJECT-TYPE
    SYNTAX      Gauge32
    MAX-ACCESS  read-only
    STATUS      current
    DESCRIPTION 
        "Gives the total of phone numbers configured on the BroadWorks system"
    ::= { systemStats 5 }

  bwNumberOfDNAssigned OBJECT-TYPE
    SYNTAX      Gauge32
    MAX-ACCESS  read-only
    STATUS      current
    DESCRIPTION 
        "Gives the total of phone numbers assigned to service provivers on the BroadWorks system"
    ::= { systemStats 6 }

  bwNumberOfDeviceType OBJECT-TYPE
    SYNTAX      Gauge32
    MAX-ACCESS  read-only
    STATUS      current
    DESCRIPTION 
        "Gives the total of device types defined on the BroadWorks system"
    ::= { systemStats 7 }

  bwNumberOfServiceType OBJECT-TYPE
    SYNTAX      Gauge32
    MAX-ACCESS  read-only
    STATUS      current
    DESCRIPTION 
        "Gives the total of service types on the BroadWorks system"
    ::= { systemStats 8 }

  bwDeviceTypeSystemTable OBJECT-TYPE
    SYNTAX      SEQUENCE OF BwDeviceTypeSystemEntry
    MAX-ACCESS  not-accessible
    STATUS      current
    DESCRIPTION 
        "This table contains statistics for each device types supported on the BroadWorks system"
    ::= { systemStats 9 }

  bwDeviceTypeSystemEntry OBJECT-TYPE
    SYNTAX      BwDeviceTypeSystemEntry
    MAX-ACCESS  not-accessible
    STATUS      current
    DESCRIPTION 
        "This row contains the statistics for a given device type in the system"
    INDEX       { bwDeviceTypeSystemIndex }
    ::= { bwDeviceTypeSystemTable 1 }

  BwDeviceTypeSystemEntry ::= SEQUENCE {
    bwDeviceTypeSystemIndex     Unsigned32,
    bwDeviceTypeSystemID        DisplayString,
    bwNumberOfDeviceTypeSystem  Gauge32
  }

  bwDeviceTypeSystemIndex OBJECT-TYPE
    SYNTAX      Unsigned32
    MAX-ACCESS  read-only
    STATUS      current
    DESCRIPTION 
        "This integer represents a device type index in the system"
    ::= { bwDeviceTypeSystemEntry 1 }

  bwDeviceTypeSystemID OBJECT-TYPE
    SYNTAX      DisplayString
    MAX-ACCESS  read-only
    STATUS      current
    DESCRIPTION 
        "This string represents a device type ID"
    ::= { bwDeviceTypeSystemEntry 2 }

  bwNumberOfDeviceTypeSystem OBJECT-TYPE
    SYNTAX      Gauge32
    MAX-ACCESS  read-only
    STATUS      current
    DESCRIPTION 
        "Gives the total of number of a device type defined in the system"
    ::= { bwDeviceTypeSystemEntry 3 }

  bwServiceTypeSystemTable OBJECT-TYPE
    SYNTAX      SEQUENCE OF BwServiceTypeSystemEntry
    MAX-ACCESS  not-accessible
    STATUS      current
    DESCRIPTION 
        "This table contains statistics for each service types supported on the BroadWorks system"
    ::= { systemStats 10 }

  bwServiceTypeSystemEntry OBJECT-TYPE
    SYNTAX      BwServiceTypeSystemEntry
    MAX-ACCESS  not-accessible
    STATUS      current
    DESCRIPTION 
        "This row contains the statistics for a given service type in the system"
    INDEX       { bwServiceTypeSystemIndex }
    ::= { bwServiceTypeSystemTable 1 }

  BwServiceTypeSystemEntry ::= SEQUENCE {
    bwServiceTypeSystemIndex                Unsigned32,
    bwServiceTypeSystemID                   DisplayString,
    bwNumberOfServiceTypeAssignedSystem     Gauge32
  }

  bwServiceTypeSystemIndex OBJECT-TYPE
    SYNTAX      Unsigned32
    MAX-ACCESS  read-only
    STATUS      current
    DESCRIPTION 
        "This integer represents a service type index in the system"
    ::= { bwServiceTypeSystemEntry 1 }

  bwServiceTypeSystemID OBJECT-TYPE
    SYNTAX      DisplayString
    MAX-ACCESS  read-only
    STATUS      current
    DESCRIPTION 
        "This string represents a service type ID"
    ::= { bwServiceTypeSystemEntry 2 }

  bwNumberOfServiceTypeAssignedSystem OBJECT-TYPE
    SYNTAX      Gauge32
    MAX-ACCESS  read-only
    STATUS      current
    DESCRIPTION 
        "Gives the total of number of a service type assigned in the system"
    ::= { bwServiceTypeSystemEntry 3 }

  bwSystemSPTable OBJECT-TYPE
    SYNTAX      SEQUENCE OF BwSystemSPEntry
    MAX-ACCESS  not-accessible
    STATUS      current
    DESCRIPTION 
        "This table contains system level statistics for each groups on the BroadWorks system"
    ::= { systemStats 11 }

  bwSystemSPEntry OBJECT-TYPE
    SYNTAX      BwSystemSPEntry
    MAX-ACCESS  not-accessible
    STATUS      current
    DESCRIPTION 
        "This row contains the system statistics for a given service provider in the system"
    INDEX       { bwSystemSPIndex }
    ::= { bwSystemSPTable 1 }

  BwSystemSPEntry ::= SEQUENCE {
    bwSystemSPIndex         Unsigned32,
    bwSystemSPID            DisplayString,
    bwSystemSPName          DisplayString,
    bwNumberOfSPUsers       Gauge32,
    bwNumberOfSPGroups      Gauge32,
    bwNumberOfSPDNDefined   Gauge32,
    bwNumberOfSPDNAssigned  Gauge32,
    bwNumberOfSPDeviceType  Gauge32
  }

  bwSystemSPIndex OBJECT-TYPE
    SYNTAX      Unsigned32
    MAX-ACCESS  read-only
    STATUS      current
    DESCRIPTION 
        "This integer represents a service provider index in the system"
    ::= { bwSystemSPEntry 1 }

  bwSystemSPID OBJECT-TYPE
    SYNTAX      DisplayString
    MAX-ACCESS  read-only
    STATUS      current
    DESCRIPTION 
        "This string represents a service provider ID"
    ::= { bwSystemSPEntry 2 }

  bwSystemSPName OBJECT-TYPE
    SYNTAX      DisplayString
    MAX-ACCESS  read-only
    STATUS      current
    DESCRIPTION 
        "Gives the BroadWorks system name"
    ::= { bwSystemSPEntry 3 }

  bwNumberOfSPUsers OBJECT-TYPE
    SYNTAX      Gauge32
    MAX-ACCESS  read-only
    STATUS      current
    DESCRIPTION 
        "Gives the total of users configured for a service provider"
    ::= { bwSystemSPEntry 4 }

  bwNumberOfSPGroups OBJECT-TYPE
    SYNTAX      Gauge32
    MAX-ACCESS  read-only
    STATUS      current
    DESCRIPTION 
        "Gives the total of groups configured for a service provider"
    ::= { bwSystemSPEntry 5 }

  bwNumberOfSPDNDefined OBJECT-TYPE
    SYNTAX      Gauge32
    MAX-ACCESS  read-only
    STATUS      current
    DESCRIPTION 
        "Gives the total of phone numbers configured for a service provider"
    ::= { bwSystemSPEntry 6 }

  bwNumberOfSPDNAssigned OBJECT-TYPE
    SYNTAX      Gauge32
    MAX-ACCESS  read-only
    STATUS      current
    DESCRIPTION 
        "Gives the total of phone numbers assigned to groups by a service provider"
    ::= { bwSystemSPEntry 7 }

  bwNumberOfSPDeviceType OBJECT-TYPE
    SYNTAX      Gauge32
    MAX-ACCESS  read-only
    STATUS      current
    DESCRIPTION 
        "Gives the total of device types defined for a service provider"
    ::= { bwSystemSPEntry 8 }

  bwSystemGroupTable OBJECT-TYPE
    SYNTAX      SEQUENCE OF BwSystemGroupEntry
    MAX-ACCESS  not-accessible
    STATUS      current
    DESCRIPTION 
        "This table contains system level statistics for each groups on the BroadWorks system"
    ::= { systemStats 12 }

  bwSystemGroupEntry OBJECT-TYPE
    SYNTAX      BwSystemGroupEntry
    MAX-ACCESS  not-accessible
    STATUS      current
    DESCRIPTION 
        "This row contains the system statistics for a given group in the system"
    INDEX       { bwSystemGroupIndex }
    ::= { bwSystemGroupTable 1 }

  BwSystemGroupEntry ::= SEQUENCE {
    bwSystemGroupIndex          Unsigned32,
    bwSystemGroupSPID           DisplayString,
    bwSystemGroupID             DisplayString,
    bwSystemGroupName           DisplayString,
    bwNumberOfGroupUsers        Gauge32,
    bwNumberOfGroupDNDefined    Gauge32,
    bwNumberOfGroupDNAssigned   Gauge32,
    bwNumberOfGroupDeviceType   Gauge32
  }

  bwSystemGroupIndex OBJECT-TYPE
    SYNTAX      Unsigned32
    MAX-ACCESS  read-only
    STATUS      current
    DESCRIPTION 
        "This integer represents a group index in the system"
    ::= { bwSystemGroupEntry 1 }

  bwSystemGroupSPID OBJECT-TYPE
    SYNTAX      DisplayString
    MAX-ACCESS  read-only
    STATUS      current
    DESCRIPTION 
        "This string represents a service provider ID"
    ::= { bwSystemGroupEntry 2 }

  bwSystemGroupID OBJECT-TYPE
    SYNTAX      DisplayString
    MAX-ACCESS  read-only
    STATUS      current
    DESCRIPTION 
        "This string represents a group ID"
    ::= { bwSystemGroupEntry 3 }

  bwSystemGroupName OBJECT-TYPE
    SYNTAX      DisplayString
    MAX-ACCESS  read-only
    STATUS      current
    DESCRIPTION 
        "Gives the BroadWorks system name"
    ::= { bwSystemGroupEntry 4 }

  bwNumberOfGroupUsers OBJECT-TYPE
    SYNTAX      Gauge32
    MAX-ACCESS  read-only
    STATUS      current
    DESCRIPTION 
        "Gives the total of users configured in a group"
    ::= { bwSystemGroupEntry 5 }

  bwNumberOfGroupDNDefined OBJECT-TYPE
    SYNTAX      Gauge32
    MAX-ACCESS  read-only
    STATUS      current
    DESCRIPTION 
        "Gives the total of phone numbers configured for a group"
    ::= { bwSystemGroupEntry 6 }

  bwNumberOfGroupDNAssigned OBJECT-TYPE
    SYNTAX      Gauge32
    MAX-ACCESS  read-only
    STATUS      current
    DESCRIPTION 
        "Gives the total of phone numbers assigned to a group"
    ::= { bwSystemGroupEntry 7 }

  bwNumberOfGroupDeviceType OBJECT-TYPE
    SYNTAX      Gauge32
    MAX-ACCESS  read-only
    STATUS      current
    DESCRIPTION 
        "Gives the total of device types for a group"
    ::= { bwSystemGroupEntry 8 }

  bwNumberOfNonVirtualUsers OBJECT-TYPE
    SYNTAX      Gauge32
    MAX-ACCESS  read-only
    STATUS      current
    DESCRIPTION 
        "This is the number of actual users - excluding virtual users - on the BroadWorks system."
    ::= { systemStats 13 }

  bwNumberOfLicensedUsers OBJECT-TYPE
    SYNTAX      Gauge32
    MAX-ACCESS  read-only
    STATUS      current
    DESCRIPTION 
        "This is the number of licensed users on the BroadWorks system."
    ::= { systemStats 14 }

internalStats OBJECT IDENTIFIER
    ::= { systemModule 2 }

  bwSystemInternalQueueResets OBJECT-TYPE
    SYNTAX      Counter32
    MAX-ACCESS  read-write
    STATUS      current
    DESCRIPTION 
        "When set to a value other then 0, all the internal queue statistic stored under bwSystemInternalQueueTable are reset to 0."
    ::= { internalStats 1 }

  bwSystemInternalQueueTable OBJECT-TYPE
    SYNTAX      SEQUENCE OF BwSystemInternalQueueEntry
    MAX-ACCESS  not-accessible
    STATUS      current
    DESCRIPTION 
        "This table contains statistics about the BroadWorks internal queues"
    ::= { internalStats 2 }

  bwSystemInternalQueueEntry OBJECT-TYPE
    SYNTAX      BwSystemInternalQueueEntry
    MAX-ACCESS  not-accessible
    STATUS      current
    DESCRIPTION 
        "This row contains the statistics for a given internal queue in the system"
    INDEX       { bwSystemInternalQueueIndex }
    ::= { bwSystemInternalQueueTable 1 }

  BwSystemInternalQueueEntry ::= SEQUENCE {
    bwSystemInternalQueueIndex                  Unsigned32,
    bwSystemInternalQueueName                   DisplayString,
    bwSystemInternalQueueSize                   Counter32,
    bwSystemInternalQueueTimeAvg                Gauge32,
    bwSystemInternalQueueTimeMin                Gauge32,
    bwSystemInternalQueueTimeMax                Gauge32,
    bwSystemInternalQueueLengthCurrent          Gauge32,
    bwSystemInternalQueueLengthAvg              Gauge32,
    bwSystemInternalQueueLengthMax              Gauge32,
    bwSystemInternalQueueTimeMaxTimestampMSB    Gauge32,
    bwSystemInternalQueueLengthMaxTimestampMSB  Gauge32,
    bwSystemInternalQueueLengthMaxTimestampLSB  Gauge32,
    bwSystemInternalQueueTimeMaxTimestampLSB    Gauge32
  }

  bwSystemInternalQueueIndex OBJECT-TYPE
    SYNTAX      Unsigned32
    MAX-ACCESS  read-only
    STATUS      current
    DESCRIPTION 
        "This integer represents an index to an internal queue in the system."
    ::= { bwSystemInternalQueueEntry 1 }

  bwSystemInternalQueueName OBJECT-TYPE
    SYNTAX      DisplayString
    MAX-ACCESS  read-only
    STATUS      current
    DESCRIPTION 
        "This string represents the name of an internal queue."
    ::= { bwSystemInternalQueueEntry 2 }

  bwSystemInternalQueueSize OBJECT-TYPE
    SYNTAX      Counter32
    MAX-ACCESS  read-only
    STATUS      current
    DESCRIPTION 
        "The number of sample elements that the average, minimum and maximum holding time were calculated from."
    ::= { bwSystemInternalQueueEntry 3 }

  bwSystemInternalQueueTimeAvg OBJECT-TYPE
    SYNTAX      Gauge32
    MAX-ACCESS  read-only
    STATUS      current
    DESCRIPTION 
        "The average queue holding time. Note that this value is in 1/1000 of millisec, i.e. divide by 1000 to get the value in milliseconds."
    ::= { bwSystemInternalQueueEntry 4 }

  bwSystemInternalQueueTimeMin OBJECT-TYPE
    SYNTAX      Gauge32
    MAX-ACCESS  read-only
    STATUS      current
    DESCRIPTION 
        "The smallest queue sample holding time."
    ::= { bwSystemInternalQueueEntry 5 }

  bwSystemInternalQueueTimeMax OBJECT-TYPE
    SYNTAX      Gauge32
    MAX-ACCESS  read-only
    STATUS      current
    DESCRIPTION 
        "The biggest queue sample holding time."
    ::= { bwSystemInternalQueueEntry 6 }

  bwSystemInternalQueueLengthCurrent OBJECT-TYPE
    SYNTAX      Gauge32
    MAX-ACCESS  read-only
    STATUS      current
    DESCRIPTION 
        "The number of elements currently hold in the queue."
    ::= { bwSystemInternalQueueEntry 8 }

  bwSystemInternalQueueLengthAvg OBJECT-TYPE
    SYNTAX      Gauge32
    MAX-ACCESS  read-only
    STATUS      current
    DESCRIPTION 
        "The average number of elements simultaneously held in the queue multiple by 1000. Divide by 1000 to get the value in units."
    ::= { bwSystemInternalQueueEntry 9 }

  bwSystemInternalQueueLengthMax OBJECT-TYPE
    SYNTAX      Gauge32
    MAX-ACCESS  read-only
    STATUS      current
    DESCRIPTION 
        "The maximum number of elements simultaneously held in the queue multiple by 1000. Divide by 1000 to get the value in units."
    ::= { bwSystemInternalQueueEntry 10 }

  bwSystemInternalQueueTimeMaxTimestampMSB OBJECT-TYPE
    SYNTAX      Gauge32
    MAX-ACCESS  read-only
    STATUS      current
    DESCRIPTION 
        "The most significant part of the timestamp (4 most significant bytes) of when bwSystemInternalQueueTimeMax was obtained."
    ::= { bwSystemInternalQueueEntry 12 }

  bwSystemInternalQueueLengthMaxTimestampMSB OBJECT-TYPE
    SYNTAX      Gauge32
    MAX-ACCESS  read-only
    STATUS      current
    DESCRIPTION 
        "The most significant part of the timestamp (4 most significant bytes) of when bwSystemInternalQueueLengthMax was obtained."
    ::= { bwSystemInternalQueueEntry 13 }

  bwSystemInternalQueueLengthMaxTimestampLSB OBJECT-TYPE
    SYNTAX      Gauge32
    MAX-ACCESS  read-only
    STATUS      current
    DESCRIPTION 
        "The least significant part of the timestamp (4 least significant bytes) of when bwSystemInternalQueueLengthMax was obtained."
    ::= { bwSystemInternalQueueEntry 14 }

  bwSystemInternalQueueTimeMaxTimestampLSB OBJECT-TYPE
    SYNTAX      Gauge32
    MAX-ACCESS  read-only
    STATUS      current
    DESCRIPTION 
        "The least significant part of the timestamp (4 least significant bytes) of when bwSystemInternalQueueTimeMax was obtained."
    ::= { bwSystemInternalQueueEntry 15 }

overloadStats OBJECT IDENTIFIER
    ::= { systemModule 3 }

  bwCurrentCallOverloadZone OBJECT-TYPE
    SYNTAX      DisplayString
    MAX-ACCESS  read-only
    STATUS      current
    DESCRIPTION 
        "The current call related overload zone. Value is a string indicating Green, Yellow, or Red."
    ::= { overloadStats 4 }

  bwNumCallYellowZoneOverloadTrans OBJECT-TYPE
    SYNTAX      Counter32
    MAX-ACCESS  read-write
    STATUS      current
    DESCRIPTION 
        "The number of times that the server has transitioned to the call related yellow overload zone."
    ::= { overloadStats 5 }

  bwNumCallRedZoneOverloadTrans OBJECT-TYPE
    SYNTAX      Counter32
    MAX-ACCESS  read-write
    STATUS      current
    DESCRIPTION 
        "The number of times that the server has transitioned to the call related red overload zone."
    ::= { overloadStats 6 }

  bwCurrentNonCallOverloadZone OBJECT-TYPE
    SYNTAX      DisplayString
    MAX-ACCESS  read-only
    STATUS      current
    DESCRIPTION 
        "The current non-call related overload zone. Value is a string indicating Green, Yellow, or Red."
    ::= { overloadStats 7 }

  bwNumNonCallYellowZoneOverloadTrans OBJECT-TYPE
    SYNTAX      Counter32
    MAX-ACCESS  read-write
    STATUS      current
    DESCRIPTION 
        "The number of times that the server has transitioned to the non-call related yellow overload zone."
    ::= { overloadStats 8 }

  bwNumNonCallRedZoneOverloadTrans OBJECT-TYPE
    SYNTAX      Counter32
    MAX-ACCESS  read-write
    STATUS      current
    DESCRIPTION 
        "The number of times that the server has transitioned to the non-call related red overload zone."
    ::= { overloadStats 9 }

  bwNumDiscardedMessage OBJECT-TYPE
    SYNTAX      Counter32
    MAX-ACCESS  read-write
    STATUS      current
    DESCRIPTION 
        "The number of messages that were dropped from the SIP or MGCP decoder queues."
    ::= { overloadStats 10 }

  bwTimeLastDiscardedMessage OBJECT-TYPE
    SYNTAX      DisplayString
    MAX-ACCESS  read-write
    STATUS      current
    DESCRIPTION 
        "The last time a message was dropped from the SIP or MGCP decoded queues."
    ::= { overloadStats 11 }

  bwMemoryHighWaterMark OBJECT-TYPE
    SYNTAX      Gauge32
    MAX-ACCESS  read-only
    STATUS      current
    DESCRIPTION 
        "The high water mark for the heap size."
    ::= { overloadStats 12 }

  bwMemoryHighWaterMarkTimeMSB OBJECT-TYPE
    SYNTAX      Gauge32
    MAX-ACCESS  read-only
    STATUS      current
    DESCRIPTION 
        "The most significant part of the timestamp (4 most significant bytes) of when bwMemoryHighWaterMark was obtained."
    ::= { overloadStats 13 }

  bwMemoryHighWaterMarkTimeLSB OBJECT-TYPE
    SYNTAX      Gauge32
    MAX-ACCESS  read-only
    STATUS      current
    DESCRIPTION 
        "The least significant part of the timestamp (4 least significant bytes) of when bwMemoryHighWaterMark was obtained."
    ::= { overloadStats 14 }

  bwOverloadStatsReset OBJECT-TYPE
    SYNTAX      Counter32
    MAX-ACCESS  read-write
    STATUS      current
    DESCRIPTION 
        "When set to a value other then 0, all the statistics stored under bwOverloadSampledDelayTable are reset to 0."
    ::= { overloadStats 15 }

  bwOverloadStatsTable  OBJECT-TYPE
    SYNTAX      SEQUENCE OF BwOverloadStatsEntry
    MAX-ACCESS  not-accessible
    STATUS      current
    DESCRIPTION 
        "This table contains statistics about overload"
    ::= { overloadStats 16 }

  bwOverloadStatsEntry OBJECT-TYPE
    SYNTAX      BwOverloadStatsEntry
    MAX-ACCESS  not-accessible
    STATUS      current
    DESCRIPTION 
        "This row contains the statistics for a given overload sampled in the system"
    INDEX       { bwOverloadSampledDataIndex }
    ::= { bwOverloadStatsTable 1 }

  BwOverloadStatsEntry ::= SEQUENCE {
    bwOverloadSampledDataIndex               Unsigned32,
    bwOverloadSampledDataName                DisplayString,
    bwOverloadSampledDelayMin                Gauge32,
    bwOverloadSampledDelayAvg                Gauge32,
    bwOverloadSampledDelayMax                Gauge32,
    bwOverloadSampledDelayMaxTimeMSB         Gauge32,
    bwOverloadSampledDelayMaxTimeLSB         Gauge32,
    bwOverloadNumSamples                     Gauge32
  }

  bwOverloadSampledDataIndex OBJECT-TYPE
    SYNTAX      Unsigned32
    MAX-ACCESS  read-only
    STATUS      current
    DESCRIPTION 
        "This integer represents an index to an overload sample in the system."
    ::= { bwOverloadStatsEntry 1 }

  bwOverloadSampledDataName OBJECT-TYPE
    SYNTAX      DisplayString
    MAX-ACCESS  read-only
    STATUS      current
    DESCRIPTION 
        "This string represents the name of an overload sample."
    ::= { bwOverloadStatsEntry 2 }

  bwOverloadSampledDelayMin OBJECT-TYPE
    SYNTAX      Gauge32
    MAX-ACCESS  read-only
    STATUS      current
    DESCRIPTION 
        "This is the minimum sampled delay in milliseconds."
    ::= { bwOverloadStatsEntry 3 }

  bwOverloadSampledDelayAvg OBJECT-TYPE
    SYNTAX      Gauge32
    MAX-ACCESS  read-only
    STATUS      current
    DESCRIPTION 
        "This is the average sampled delay in microseconds."
    ::= { bwOverloadStatsEntry 4 }

  bwOverloadSampledDelayMax OBJECT-TYPE
    SYNTAX      Gauge32
    MAX-ACCESS  read-only
    STATUS      current
    DESCRIPTION 
        "This is the maximum sampled delay in milliseconds."
    ::= { bwOverloadStatsEntry 5 }

  bwOverloadSampledDelayMaxTimeMSB OBJECT-TYPE
    SYNTAX      Gauge32
    MAX-ACCESS  read-only
    STATUS      current
    DESCRIPTION 
        "The most significant part of the timestamp (4 most significant bytes) of when bwOverloadSampledDelayMax was obtained."
    ::= { bwOverloadStatsEntry 6 }

  bwOverloadSampledDelayMaxTimeLSB OBJECT-TYPE
    SYNTAX      Gauge32
    MAX-ACCESS  read-only
    STATUS      current
    DESCRIPTION 
        "The least significant part of the timestamp (4 least significant bytes) of when bwOverloadSampledDelayMax was obtained."
    ::= { bwOverloadStatsEntry 7 }

  bwOverloadNumSamples OBJECT-TYPE
    SYNTAX      Gauge32
    MAX-ACCESS  read-only
    STATUS      current
    DESCRIPTION 
        "The total number of overload samples processed."
    ::= { bwOverloadStatsEntry 8 }

-- Management module ...........................................

  resetAllCounters OBJECT-TYPE
    SYNTAX      Counter32
    MAX-ACCESS  read-write
    STATUS      current
    DESCRIPTION "When set to a value other then 0, all the counters in the system are reset to 0."
    ::= { management 1 }

-- Redundancy .................

  nbOfMigratedUsers OBJECT-TYPE
    SYNTAX      Gauge32
    MAX-ACCESS  read-only
    STATUS      current
    DESCRIPTION
        "This value represents the actual number of users migrated to the secondary application server"
    ::= { redundancyStats 1 }

-- Diameter .................

  bwInternalXSTransactionTable OBJECT-TYPE
    SYNTAX      SEQUENCE OF BwInternalXSTransactionEntry
    MAX-ACCESS  not-accessible
    STATUS      current
    DESCRIPTION 
        "This table contains statistics about the Diameter Stack internal transactions."
    ::= { diameterStats 1 }

  bwInternalXSTransactionEntry OBJECT-TYPE
    SYNTAX      BwInternalXSTransactionEntry
    MAX-ACCESS  not-accessible
    STATUS      current
    DESCRIPTION 
        "This row contains the statistics for a given internal Diameter transaction."
    INDEX       { bwInternalXSDiameterCommandCode }
    ::= { bwInternalXSTransactionTable 1 }

  BwInternalXSTransactionEntry ::= SEQUENCE {
    bwInternalXSDiameterCommandCode             Unsigned32,
    bwInternalXSDiameterRequestsOut             Counter32,
    bwInternalXSDiameterInformationalAnswersIn  Counter32,
    bwInternalXSDiameterSuccessAnswersIn        Counter32,
    bwInternalXSDiameterFailureAnswersIn        Counter32,
    bwInternalXSDiameterRequestTimeouts         Counter32,
    bwInternalXSDiameterRequestsIn              Counter32,
    bwInternalXSDiameterInformationalAnswersOut Counter32,
    bwInternalXSDiameterSuccessAnswersOut       Counter32,
    bwInternalXSDiameterFailureAnswersOut       Counter32
  }

  bwInternalXSDiameterCommandCode OBJECT-TYPE
    SYNTAX      Unsigned32
    MAX-ACCESS  read-only
    STATUS      current
    DESCRIPTION 
        "This is the Diameter message's command-code which indexes this table."
    ::= { bwInternalXSTransactionEntry 1 }

  bwInternalXSDiameterRequestsOut OBJECT-TYPE
    SYNTAX      Counter32
    MAX-ACCESS  read-only
    STATUS      current
    DESCRIPTION 
        "This is the number of request sent by the Diameter Stack. This includes both initial transmissions and retransmissions of the same request."
    ::= { bwInternalXSTransactionEntry 2 }

  bwInternalXSDiameterInformationalAnswersIn OBJECT-TYPE
    SYNTAX      Counter32
    MAX-ACCESS  read-only
    STATUS      current
    DESCRIPTION 
        "This is the number of answers containing an informational Result-Code (value 1xxx)."
    ::= { bwInternalXSTransactionEntry 3 }

  bwInternalXSDiameterSuccessAnswersIn OBJECT-TYPE
    SYNTAX      Counter32
    MAX-ACCESS  read-only
    STATUS      current
    DESCRIPTION 
        "This is the number of answers containing a successful Result-Code (value 2xxx)."
    ::= { bwInternalXSTransactionEntry 4 }

  bwInternalXSDiameterFailureAnswersIn OBJECT-TYPE
    SYNTAX      Counter32
    MAX-ACCESS  read-only
    STATUS      current
    DESCRIPTION 
        "This is the number of answers containing a failure Result-Code or Experimental-Result (value >= 3000), malformed answers or answers not matching any outstanding request. Malformed answers have inappropriate Diameter message header values or do not contain any Result-Code or Experimental-Result AVPs."
    ::= { bwInternalXSTransactionEntry 5 }

  bwInternalXSDiameterRequestTimeouts OBJECT-TYPE
    SYNTAX      Counter32
    MAX-ACCESS  read-only
    STATUS      current
    DESCRIPTION 
        "This is the number of requests for which no response has been received within the specified timeout. The timeout value is application-dependent. If an answer is received afterward, it is treated as an unmatched answer and the bwDiameterStatsFailureAnswersIn is incremented."
    ::= { bwInternalXSTransactionEntry 6 }

  bwInternalXSDiameterRequestsIn OBJECT-TYPE
    SYNTAX      Counter32
    MAX-ACCESS  read-only
    STATUS      current
    DESCRIPTION 
        "This is the number of received requests on the corresponding Diameter stack instance."
    ::= { bwInternalXSTransactionEntry 7 }

  bwInternalXSDiameterInformationalAnswersOut OBJECT-TYPE
    SYNTAX      Counter32
    MAX-ACCESS  read-only
    STATUS      current
    DESCRIPTION 
        "This is the number of informational answers (Result-Code value = 1xxx) sent by the corresponding Diameter stack instance."
    ::= { bwInternalXSTransactionEntry 8 }

  bwInternalXSDiameterSuccessAnswersOut OBJECT-TYPE
    SYNTAX      Counter32
    MAX-ACCESS  read-only
    STATUS      current
    DESCRIPTION 
        "This is the number of successful answers (Result-Code value = 2xxx) sent by the corresponding Diameter stack instance."
    ::= { bwInternalXSTransactionEntry 9 }

  bwInternalXSDiameterFailureAnswersOut OBJECT-TYPE
    SYNTAX      Counter32
    MAX-ACCESS  read-only
    STATUS      current
    DESCRIPTION 
        "This is the number of failure answers (Result-Code/Experimental-Result-Code value >= 3000) sent by the corresponding Diameter stack instance."
    ::= { bwInternalXSTransactionEntry 10 }

  bwExternalXSTransactionTable OBJECT-TYPE
    SYNTAX      SEQUENCE OF BwExternalXSTransactionEntry
    MAX-ACCESS  not-accessible
    STATUS      current
    DESCRIPTION 
        "This table contains statistics about the Diameter Stack external transactions."
    ::= { diameterStats 2 }

  bwExternalXSTransactionEntry OBJECT-TYPE
    SYNTAX      BwExternalXSTransactionEntry
    MAX-ACCESS  not-accessible
    STATUS      current
    DESCRIPTION 
        "This row contains the statistics for a given external Diameter transaction."
    INDEX       { bwExternalXSDiameterCommandCode }
    ::= { bwExternalXSTransactionTable 1 }

  BwExternalXSTransactionEntry ::= SEQUENCE {
    bwExternalXSDiameterCommandCode             Unsigned32,
    bwExternalXSDiameterRequestsOut             Counter32,
    bwExternalXSDiameterInformationalAnswersIn  Counter32,
    bwExternalXSDiameterSuccessAnswersIn        Counter32,
    bwExternalXSDiameterFailureAnswersIn        Counter32,
    bwExternalXSDiameterRequestTimeouts         Counter32,
    bwExternalXSDiameterRequestsIn              Counter32,
    bwExternalXSDiameterInformationalAnswersOut Counter32,
    bwExternalXSDiameterSuccessAnswersOut       Counter32,
    bwExternalXSDiameterFailureAnswersOut       Counter32
  }

  bwExternalXSDiameterCommandCode OBJECT-TYPE
    SYNTAX      Unsigned32
    MAX-ACCESS  read-only
    STATUS      current
    DESCRIPTION 
        "This is the Diameter message's command-code which indexes this table."
    ::= { bwExternalXSTransactionEntry 1 }

  bwExternalXSDiameterRequestsOut OBJECT-TYPE
    SYNTAX      Counter32
    MAX-ACCESS  read-only
    STATUS      current
    DESCRIPTION 
        "This is the number of request sent by the Diameter Stack. This includes both initial transmissions and retransmissions of the same request."
    ::= { bwExternalXSTransactionEntry 2 }

  bwExternalXSDiameterInformationalAnswersIn OBJECT-TYPE
    SYNTAX      Counter32
    MAX-ACCESS  read-only
    STATUS      current
    DESCRIPTION 
        "This is the number of answers containing an informational Result-Code (value 1xxx)."
    ::= { bwExternalXSTransactionEntry 3 }

  bwExternalXSDiameterSuccessAnswersIn OBJECT-TYPE
    SYNTAX      Counter32
    MAX-ACCESS  read-only
    STATUS      current
    DESCRIPTION 
        "This is the number of answers containing a successful Result-Code (value 2xxx)."
    ::= { bwExternalXSTransactionEntry 4 }

  bwExternalXSDiameterFailureAnswersIn OBJECT-TYPE
    SYNTAX      Counter32
    MAX-ACCESS  read-only
    STATUS      current
    DESCRIPTION 
        "This is the number of answers containing a failure Result-Code or Experimental-Result (value >= 3000), malformed answers or answers not matching any outstanding request. Malformed answers have inappropriate Diameter message header values or do not contain any Result-Code or Experimental-Result AVPs."
    ::= { bwExternalXSTransactionEntry 5 }

  bwExternalXSDiameterRequestTimeouts OBJECT-TYPE
    SYNTAX      Counter32
    MAX-ACCESS  read-only
    STATUS      current
    DESCRIPTION 
        "This is the number of requests for which no response has been received within the specified timeout. The timeout value is application-dependent. If an answer is received afterward, it is treated as an unmatched answer and the bwDiameterStatsFailureAnswersIn is incremented."
    ::= { bwExternalXSTransactionEntry 6 }

  bwExternalXSDiameterRequestsIn OBJECT-TYPE
    SYNTAX      Counter32
    MAX-ACCESS  read-only
    STATUS      current
    DESCRIPTION 
        "This is the number of received requests on the corresponding Diameter stack instance."
    ::= { bwExternalXSTransactionEntry 7 }

  bwExternalXSDiameterInformationalAnswersOut OBJECT-TYPE
    SYNTAX      Counter32
    MAX-ACCESS  read-only
    STATUS      current
    DESCRIPTION 
        "This is the number of informational answers (Result-Code value = 1xxx) sent by the corresponding Diameter stack instance."
    ::= { bwExternalXSTransactionEntry 8 }

  bwExternalXSDiameterSuccessAnswersOut OBJECT-TYPE
    SYNTAX      Counter32
    MAX-ACCESS  read-only
    STATUS      current
    DESCRIPTION 
        "This is the number of successful answers (Result-Code value = 2xxx) sent by the corresponding Diameter stack instance."
    ::= { bwExternalXSTransactionEntry 9 }

  bwExternalXSDiameterFailureAnswersOut OBJECT-TYPE
    SYNTAX      Counter32
    MAX-ACCESS  read-only
    STATUS      current
    DESCRIPTION 
        "This is the number of failure answers (Result-Code/Experimental-Result-Code value >= 3000) sent by the corresponding Diameter stack instance."
    ::= { bwExternalXSTransactionEntry 10 }

-- SH Relay Interface ......................

  bwShRelayInterfaceServerUnreachable OBJECT-TYPE
    SYNTAX      Counter32
    MAX-ACCESS  read-only
    STATUS      current
    DESCRIPTION 
        "This is the number of Sh requests not sent by the XS Sh Relay because none of the HSSes or Diameter Agents is currently connected."
    ::= { shRelayInterfaceStats 1 }

-- Mobility Module stats ......................

  bwMobilityMobileOriginationTriggers OBJECT-TYPE
    SYNTAX      Counter32
    MAX-ACCESS  read-only
    STATUS      current
    DESCRIPTION 
        "This is the number of mobile origination triggers received by the Application server."
    ::= { mobilityStats 1 }

  bwMobilityMobileTerminationTriggers OBJECT-TYPE
    SYNTAX      Counter32
    MAX-ACCESS  read-only
    STATUS      current
    DESCRIPTION 
        "This is the number of mobile termination triggers received by the Application server."
    ::= { mobilityStats 2 }

  bwMobilityIMRNOriginations OBJECT-TYPE
    SYNTAX      Counter32
    MAX-ACCESS  read-only
    STATUS      current
    DESCRIPTION 
        "This is the number of IMRN originating calls arriving at the Application server."
    ::= { mobilityStats 3 }

  bwMobilityIMRNTerminations OBJECT-TYPE
    SYNTAX      Counter32
    MAX-ACCESS  read-only
    STATUS      current
    DESCRIPTION 
        " This is the number of IMRN terminating calls received by the Application server."
    ::= { mobilityStats 4 }

  bwMobilityIMRNAllocationFailures OBJECT-TYPE
    SYNTAX      Counter32
    MAX-ACCESS  read-only
    STATUS      current
    DESCRIPTION 
        "The number of times IMRN allocation has failed."
    ::= { mobilityStats 5 }

  bwMobilityIMRNAllocationTimeOuts OBJECT-TYPE
    SYNTAX      Counter32
    MAX-ACCESS  read-only
    STATUS      current
    DESCRIPTION 
        "The number of times IMRN allocation have timed out."
    ::= { mobilityStats 6 }

  bwMobilityOriginationCallDenies OBJECT-TYPE
    SYNTAX      Counter32
    MAX-ACCESS  read-only
    STATUS      current
    DESCRIPTION 
        "The number of times mobile originations have been denied."
    ::= { mobilityStats 7 }

  bwMobilityTerminationCallDenies OBJECT-TYPE
    SYNTAX      Counter32
    MAX-ACCESS  read-only
    STATUS      current
    DESCRIPTION 
        "The number of times mobile terminations have been denied."
    ::= { mobilityStats 8 }

  bwMobilityIMRNMaxUsed OBJECT-TYPE
    SYNTAX      Gauge32
    MAX-ACCESS  read-only
    STATUS      current
    DESCRIPTION 
        "The maximum number number of IMRNs used by the system (High Watermark)."
    ::= { mobilityStats 9 }

  bwMobilityIMRNsInUse OBJECT-TYPE
    SYNTAX      Gauge32
    MAX-ACCESS  read-only
    STATUS      current
    DESCRIPTION 
        "This gauge is incremented when an IMRN is allocated and decremented when an IMRN is de-allocated."
    ::= { mobilityStats 10 }

  bwMobilityIMRNMinHoldTime OBJECT-TYPE
    SYNTAX      Gauge32
    MAX-ACCESS  read-only
    STATUS      current
    DESCRIPTION 
        "This gauge is updated when an IMRN hold time is smaller than the last minimum IMRN hold time."
    ::= { mobilityStats 11 }

  bwMobilityIMRNMaxHoldTime OBJECT-TYPE
    SYNTAX      Gauge32
    MAX-ACCESS  read-only
    STATUS      current
    DESCRIPTION 
        "This gauge is updated when an IMRN hold time is greater than the last minimum IMRN hold time."
    ::= { mobilityStats 12 }

  bwMobilityIMRNAvgHoldTime OBJECT-TYPE
    SYNTAX      Gauge32
    MAX-ACCESS  read-only
    STATUS      current
    DESCRIPTION 
        "This gauge is computed by adding the total IMRN hold times, up to the last 1,000, and dividing it by the total number of IMRN operations (up to the last 1,000)."
    ::= { mobilityStats 13 }

  bwMobilitySPTable OBJECT-TYPE
    SYNTAX      SEQUENCE  OF  BwMobilitySPEntry
    MAX-ACCESS  not-accessible
    STATUS      current
    DESCRIPTION "Each row contains the service counters for the mobility service for each service provider in the system"
    ::= { mobilityStats 14 }

  bwMobilityGroupTable OBJECT-TYPE
    SYNTAX      SEQUENCE  OF  BwMobilityGroupEntry
    MAX-ACCESS  not-accessible
    STATUS      current
    DESCRIPTION "Each row contains the service counters for the mobility service for each group in the system"
    ::= { mobilityStats 15 }

  bwMobilityCallsAnchored OBJECT-TYPE
    SYNTAX      Counter32
    MAX-ACCESS  read-write
    STATUS      current
    DESCRIPTION 
        "This counter tracks the number of times mobile calls are anchored. It is tracked at the system level."
-- @feature:203930
    ::= { mobilityStats 16 }

  bwMobilityCallsNotAnchored OBJECT-TYPE
    SYNTAX      Counter32
    MAX-ACCESS  read-write
    STATUS      current
    DESCRIPTION 
        "This counter tracks the number of times mobile calls are not anchored. It is tracked at the system level."
-- @feature:203930
    ::= { mobilityStats 17 }

-- Service : Mobility Module SP ...........................................

  bwMobilitySPEntry OBJECT-TYPE
    SYNTAX      BwMobilitySPEntry
    MAX-ACCESS  not-accessible
    STATUS      current
    DESCRIPTION
        "Each row contains the service counters for the Mobility service for each service provider in the system"
    INDEX { bwMobilitySPIndex }
    ::= { bwMobilitySPTable 1 }

  BwMobilitySPEntry ::= SEQUENCE {
    bwMobilitySPIndex                  Unsigned32,
    bwMobilitySPID                     DisplayString,
    bwMobilitySPOriginationCallDenies  Counter32,
    bwMobilitySPTerminationCallDenies  Counter32,
    bwMobilitySPIMRNAllocationFailures Counter32,
    bwMobilitySPIMRNAllocationTimeOuts Counter32,
    bwMobilitySPIMRNOriginations       Counter32,
    bwMobilitySPIMRNMaxUsed            Gauge32,
    bwMobilitySPIMRNsInUse             Gauge32,
    bwMobilitySPIMRNMinHoldTime        Gauge32,
    bwMobilitySPIMRNMaxHoldTime        Gauge32,
    bwMobilitySPIMRNAvgHoldTime        Gauge32,
    bwMobilitySPCallsAnchored          Counter32,
    bwMobilitySPCallsNotAnchored       Counter32
    }

 bwMobilitySPIndex OBJECT-TYPE
    SYNTAX       Unsigned32
    MAX-ACCESS   read-only
    STATUS       current
    DESCRIPTION  
        "This column represents the index of the Service Provider in the system."
    ::= { bwMobilitySPEntry 1 }

  bwMobilitySPID OBJECT-TYPE
    SYNTAX       DisplayString
    MAX-ACCESS   read-only
    STATUS       current
    DESCRIPTION  
        "This string represents a Service Provider ID."
    ::= { bwMobilitySPEntry 2 }

 bwMobilitySPOriginationCallDenies OBJECT-TYPE
    SYNTAX       Counter32
    MAX-ACCESS   read-write
    STATUS       current
    DESCRIPTION  
        "The number of times mobile originations have been denied for a given service provider. "
    ::= { bwMobilitySPEntry 3 }

 bwMobilitySPTerminationCallDenies OBJECT-TYPE
    SYNTAX       Counter32
    MAX-ACCESS   read-write
    STATUS       current
    DESCRIPTION  
        "The number of times mobile terminations have been denied for a given service provider. "
    ::= { bwMobilitySPEntry 4 }

  bwMobilitySPIMRNAllocationFailures OBJECT-TYPE
    SYNTAX      Counter32
    MAX-ACCESS  read-write
    STATUS      current
    DESCRIPTION 
        "The number of times the Intermediate Routing Number (IMRN) or IP Multimedia Routing Number (IMRN) allocation has failed for a given service provider."
-- @feature:181182
    ::= { bwMobilitySPEntry 5 }

  bwMobilitySPIMRNAllocationTimeOuts OBJECT-TYPE
    SYNTAX      Counter32
    MAX-ACCESS  read-write
    STATUS      current
    DESCRIPTION 
        "The number of times an Intermediate Routing Number (IMRN) or IP Multimedia Routing Number (IMRN) allocation has timed out for a given service provider."
-- @feature:181182
    ::= { bwMobilitySPEntry 6 }

  bwMobilitySPIMRNOriginations OBJECT-TYPE
    SYNTAX      Counter32
    MAX-ACCESS  read-write
    STATUS      current
    DESCRIPTION 
        "The number of Intermediate Routing Number (IMRN) or IP Multimedia Routing Number (IMRN) originating calls arriving at the Application Server for a given service provider."
-- @feature:181182
    ::= { bwMobilitySPEntry 7 }

  bwMobilitySPIMRNMaxUsed OBJECT-TYPE
    SYNTAX      Gauge32
    MAX-ACCESS  read-write
    STATUS      current
    DESCRIPTION 
        "The maximum number number of Intermediate Routing Numbers (IMRNs) or IP Multimedia Routing Numbers (IMRNs) used from the service provider/enterprise pool (High Watermark)."
-- @feature:181182
    ::= { bwMobilitySPEntry 8 }

  bwMobilitySPIMRNsInUse OBJECT-TYPE
    SYNTAX      Gauge32
    MAX-ACCESS  read-write
    STATUS      current
    DESCRIPTION 
        "The number of times an Intermediate Routing Number (IMRN) or IP Multimedia Routing Number (IMRN) belonging to the service provider/enterprise pool is allocated and decremented when an IMRN belonging to the service provider/enterprise pool is deallocated."
-- @feature:181182
    ::= { bwMobilitySPEntry 9 }

  bwMobilitySPIMRNMinHoldTime OBJECT-TYPE
    SYNTAX      Gauge32
    MAX-ACCESS  read-write
    STATUS      current
    DESCRIPTION 
        "The number of times an Intermediate Routing Number (IMRN) or IP Multimedia Routing Number (IMRN) hold-time is smaller than the last minimum IMRN hold-time for an IMRN belonging to a specific service provider/enterprise pool."
-- @feature:181182
    ::= { bwMobilitySPEntry 10 }

  bwMobilitySPIMRNMaxHoldTime OBJECT-TYPE
    SYNTAX      Gauge32
    MAX-ACCESS  read-write
    STATUS      current
    DESCRIPTION 
        "The number of times an Intermediate Routing Number (IMRN) or IP Multimedia Routing Number (IMRN) hold-time is greater than the last maximum IMRN hold-time for an IMRN belonging to a specific service provider/enterprise pool."
-- @feature:181182
    ::= { bwMobilitySPEntry 11 }

  bwMobilitySPIMRNAvgHoldTime OBJECT-TYPE
    SYNTAX      Gauge32
    MAX-ACCESS  read-write
    STATUS      current
    DESCRIPTION 
        "This gauge is computed by adding the total number of Intermediate Routing Number (IMRN) or IP Multimedia Routing Number (IMRN) hold-times (up to the last 1,000) and dividing it by the total number of IMRN operations (up to the last 1,000 for IMRNs belonging to a specific service provider/enterprise pool)."
-- @feature:181182
    ::= { bwMobilitySPEntry 12 }

  bwMobilitySPCallsAnchored OBJECT-TYPE
    SYNTAX      Counter32
    MAX-ACCESS  read-write
    STATUS      current
    DESCRIPTION 
        "This counter tracks the number of times mobile calls are anchored. It is tracked at the service provider/Enterprise level."
-- @feature:203930
    ::= { bwMobilitySPEntry 13 }

  bwMobilitySPCallsNotAnchored OBJECT-TYPE
    SYNTAX      Counter32
    MAX-ACCESS  read-write
    STATUS      current
    DESCRIPTION 
        "This counter tracks the number of times mobile calls are not anchored. It is tracked at the service provider/Enterprise level."
-- @feature:203930
    ::= { bwMobilitySPEntry 14 }

-- Service : Mobility Module Group Table.....................................

  bwMobilityGroupEntry OBJECT-TYPE
    SYNTAX      BwMobilityGroupEntry
    MAX-ACCESS  not-accessible
    STATUS      current
    DESCRIPTION
        "Each row contains the service counters for the Mobility service for each group in the system"
    INDEX { bwMobilityGroupIndex }
    ::= { bwMobilityGroupTable 1 }

  BwMobilityGroupEntry ::= SEQUENCE {
    bwMobilityGroupIndex                  Unsigned32,
    bwMobilityGroupID                     DisplayString,
    bwMobilityGroupOriginationCallDenies  Counter32,
    bwMobilityGroupTerminationCallDenies  Counter32,
    bwMobilityGroupIMRNAllocationFailures Counter32,
    bwMobilityGroupIMRNAllocationTimeOuts Counter32,
    bwMobilityGroupIMRNOriginations       Counter32,
    bwMobilityGroupIMRNMaxUsed            Gauge32,
    bwMobilityGroupIMRNsInUse             Gauge32,
    bwMobilityGroupIMRNMinHoldTime        Gauge32,
    bwMobilityGroupIMRNMaxHoldTime        Gauge32,
    bwMobilityGroupIMRNAvgHoldTime        Gauge32,
    bwMobilityGroupCallsAnchored          Counter32,
    bwMobilityGroupCallsNotAnchored       Counter32
 }

 bwMobilityGroupIndex OBJECT-TYPE
    SYNTAX       Unsigned32
    MAX-ACCESS   read-only
    STATUS       current
    DESCRIPTION  
        "This column represents the index of the group in the system."
    ::= { bwMobilityGroupEntry 1 }

  bwMobilityGroupID OBJECT-TYPE
    SYNTAX       DisplayString
    MAX-ACCESS   read-only
    STATUS       current
    DESCRIPTION  
        "This string represents a group ID."
    ::= { bwMobilityGroupEntry 2 }

  bwMobilityGroupOriginationCallDenies OBJECT-TYPE
    SYNTAX      Counter32
    MAX-ACCESS  read-only
    STATUS      current
    DESCRIPTION 
        "The number of times mobile originations have been denied for a given group."
    ::= { bwMobilityGroupEntry 3 }

  bwMobilityGroupTerminationCallDenies OBJECT-TYPE
    SYNTAX      Counter32
    MAX-ACCESS  read-only
    STATUS      current
    DESCRIPTION 
        "The number of times mobile terminations have been denied for a given group."
    ::= { bwMobilityGroupEntry 4 }

  bwMobilityGroupIMRNAllocationFailures OBJECT-TYPE
    SYNTAX      Counter32
    MAX-ACCESS  read-write
    STATUS      current
    DESCRIPTION 
        "The number of times the Intermediate Routing Number (IMRN) or IP Multimedia Routing Number (IMRN) allocation has failed for a given group."
-- @feature:181182
    ::= { bwMobilityGroupEntry 5 }

  bwMobilityGroupIMRNAllocationTimeOuts OBJECT-TYPE
    SYNTAX      Counter32
    MAX-ACCESS  read-write
    STATUS      current
    DESCRIPTION 
        "The number of times the IMRN allocation has timed out for a given group."
-- @feature:181182
    ::= { bwMobilityGroupEntry 6 }

  bwMobilityGroupIMRNOriginations OBJECT-TYPE
    SYNTAX      Counter32
    MAX-ACCESS  read-write
    STATUS      current
    DESCRIPTION 
        "The number of Intermediate Routing Number (IMRN) or IP Multimedia Routing Number (IMRN) originating calls arriving at the Application Server for a given group."
-- @feature:181182
    ::= { bwMobilityGroupEntry 7 }

  bwMobilityGroupIMRNMaxUsed OBJECT-TYPE
    SYNTAX      Gauge32
    MAX-ACCESS  read-only
    STATUS      current
    DESCRIPTION 
        "The maximum number of Intermediate Routing Numbers (IMRNs) or IP Multimedia Routing Numbers (IMRNs) used from the group pool (High Watermark)."
-- @feature:181182
    ::= { bwMobilityGroupEntry 8 }

  bwMobilityGroupIMRNsInUse OBJECT-TYPE
    SYNTAX      Gauge32
    MAX-ACCESS  read-only
    STATUS      current
    DESCRIPTION 
        "The number of times an Intermediate Routing Number (IMRN) or IP Multimedia Routing Number (IMRN) belonging to a group pool is allocated and decremented when an IMRN belonging to the group pool is deallocated."
-- @feature:181182
    ::= { bwMobilityGroupEntry 9 }

  bwMobilityGroupIMRNMinHoldTime OBJECT-TYPE
    SYNTAX      Gauge32
    MAX-ACCESS  read-only
    STATUS      current
    DESCRIPTION 
        "The number of times an Intermediate Routing Number (IMRN) or IP Multimedia Routing Number (IMRN) hold-time is smaller than the last minimum IMRN hold-time for an IMRN belonging to a specific group pool."
-- @feature:181182
    ::= { bwMobilityGroupEntry 10 }

  bwMobilityGroupIMRNMaxHoldTime OBJECT-TYPE
    SYNTAX      Gauge32
    MAX-ACCESS  read-only
    STATUS      current
    DESCRIPTION 
        "The number of times an Intermediate Routing Number (IMRN) or IP Multimedia Routing Number (IMRN) hold-time is greater than the last maximum IMRN hold time for an IMRN belonging to a specific group pool."
-- @feature:181182
    ::= { bwMobilityGroupEntry 11 }

  bwMobilityGroupIMRNAvgHoldTime OBJECT-TYPE
    SYNTAX      Gauge32
    MAX-ACCESS  read-only
    STATUS      current
    DESCRIPTION 
        "This gauge is computed by adding the total number of Intermediate Routing Number (IMRN) or IP Multimedia Routing Number (IMRN) hold-times (up to the last 1,000) and dividing it by the total number of IMRN operations (up to the last 1,000 for IMRNs belonging to a specific group pool)."
-- @feature:181182
    ::= { bwMobilityGroupEntry 12 }

  bwMobilityGroupCallsAnchored OBJECT-TYPE
    SYNTAX      Counter32
    MAX-ACCESS  read-write
    STATUS      current
    DESCRIPTION 
        "This counter tracks the number of times mobile calls are anchored. It is tracked  at the group level."
-- @feature:203930
    ::= { bwMobilityGroupEntry 13 }

  bwMobilityGroupCallsNotAnchored OBJECT-TYPE
    SYNTAX      Counter32
    MAX-ACCESS  read-write
    STATUS      current
    DESCRIPTION 
        "This counter tracks the number of times mobile calls are not anchored. It is tracked at the group level."
-- @feature:203930
    ::= { bwMobilityGroupEntry 14 }

-- Protocol :: CAP ...........................................

  bwCAPStatsRegisterRequests OBJECT-TYPE
    SYNTAX      Counter32
    MAX-ACCESS  read-write
    STATUS      current
    DESCRIPTION 
        "This counter reflects the number of CAP registerRequest messages that have been received by the system."
    ::= { capStats 1 }

  bwCAPStatsUnRegistersIn OBJECT-TYPE
    SYNTAX      Counter32
    MAX-ACCESS  read-write
    STATUS      current
    DESCRIPTION 
        "This counter reflects the number of CAP unRegister messages that have been received by the system."
    ::= { capStats 2 }

  bwCAPStatsUnRegistersOut OBJECT-TYPE
    SYNTAX      Counter32
    MAX-ACCESS  read-write
    STATUS      current
    DESCRIPTION 
        "This counter reflects the number of CAP unRegister messages that have been sent out by the system."
    ::= { capStats 3 }

  bwCAPStatsSessionUpdatesOut OBJECT-TYPE
    SYNTAX      Counter32
    MAX-ACCESS  read-write
    STATUS      current
    DESCRIPTION 
        "This counter reflects the number of CAP sessionUpdate messages that have been sent out by the system."
    ::= { capStats 4 }

  bwCAPStatsProfileUpdatesOut OBJECT-TYPE
    SYNTAX      Counter32
    MAX-ACCESS  read-write
    STATUS      current
    DESCRIPTION 
        "This counter reflects the number of CAP profileUpdate messages that have been sent out by the system."
    ::= { capStats 5 }

  bwCAPStatsCallUpdatesOut OBJECT-TYPE
    SYNTAX      Counter32
    MAX-ACCESS  read-write
    STATUS      current
    DESCRIPTION 
        "ThisThis counter reflects the number of CAP callUpdate messages that have been sent out by the system."
    ::= { capStats 6 }

  bwCAPStatsCallActionsIn OBJECT-TYPE
    SYNTAX      Counter32
    MAX-ACCESS  read-write
    STATUS      current
    DESCRIPTION 
        "This counter reflects the number of CAP callAction messages that have been received by the system."
    ::= { capStats 7 }

  bwCAPStatsAcknowledgementsIn OBJECT-TYPE
    SYNTAX      Counter32
    MAX-ACCESS  read-write
    STATUS      current
    DESCRIPTION 
        "This counter reflects the number of CAP acknowledgement messages that have been received by the system."
    ::= { capStats 8 }

  bwCAPStatsAclViolations OBJECT-TYPE
    SYNTAX      Counter32
    MAX-ACCESS  read-write
    STATUS      current
    DESCRIPTION 
        "This counter reflects the number of incoming CAP connections that have been rejected because the connecting machine is not in the CAP access control list.  This counter causes an alarm to be generated when its threshold value is reached."
    ::= { capStats 10 }

  bwCAPStatsUnsuccessfulRegisterResponses OBJECT-TYPE
    SYNTAX      Counter32
    MAX-ACCESS  read-write
    STATUS      current
    DESCRIPTION 
        "This counter reflects the number of unsuccessful CAP registerResponse messages that the system sends out.  This counter causes an alarm to be generated when its threshold value is reached."
    ::= { capStats 11 }

  bwCAPStatsRegisterResponsesTable OBJECT-TYPE
    SYNTAX      SEQUENCE OF BwCAPStatsRegisterResponsesEntry
    MAX-ACCESS  not-accessible
    STATUS      current
    DESCRIPTION 
        "This table contains counters for the different types of CAP registerResponse messages sent by the system in response to a received CAP registerRequest message.  The following are the various types of registerResponse messages and an index value identifying each type: 1 - successful registerResponse, 2 - unsuccessful registerResponse (unknown user id), 3 - unsuccessful registerResponse (incorrect user credentials), 4 - unsuccessful registerResponse (feature unauthorized)."
    ::= { capStats 12 }

  bwCAPStatsRegisterResponsesEntry OBJECT-TYPE
    SYNTAX      BwCAPStatsRegisterResponsesEntry
    MAX-ACCESS  not-accessible
    STATUS      current
    DESCRIPTION 
        "This row contains information on a particular CAP registerResponse type sent out by the system."
    INDEX       { bwCAPStatsRegisterResponsesType }
    ::= { bwCAPStatsRegisterResponsesTable 1 }

  BwCAPStatsRegisterResponsesEntry ::= SEQUENCE {
    bwCAPStatsRegisterResponsesType     Unsigned32,
    bwCAPStatsRegisterResponses         Counter32
  }

  bwCAPStatsRegisterResponsesType OBJECT-TYPE
    SYNTAX      Unsigned32
    MAX-ACCESS  read-only
    STATUS      current
    DESCRIPTION 
        "This integer represents a registerResponse type.  This is also the index into the table."
    ::= { bwCAPStatsRegisterResponsesEntry 1 }

  bwCAPStatsRegisterResponses OBJECT-TYPE
    SYNTAX      Counter32
    MAX-ACCESS  read-write
    STATUS      current
    DESCRIPTION 
        "This counter reflects the number of CAP registerResponse messages that have been sent out by the system."
    ::= { bwCAPStatsRegisterResponsesEntry 2 }

  bwCAPStatsCallControlInfosOut OBJECT-TYPE
    SYNTAX      Counter32
    MAX-ACCESS  read-write
    STATUS      current
    DESCRIPTION 
        "This counter is incremented whenever a CAP callControlInfo message is sent out by the system"
    ::= { capStats 13 }

  bwCAPStatsRegisterAuthentications OBJECT-TYPE
    SYNTAX      Counter32
    MAX-ACCESS  read-write
    STATUS      current
    DESCRIPTION 
        "This counter is incremented whenever the Execution Server receives a registerAuthentication CAP message"
    ::= { capStats 14 }

  bwCAPStatsResponseAuthentications OBJECT-TYPE
    SYNTAX      Counter32
    MAX-ACCESS  read-write
    STATUS      current
    DESCRIPTION 
        "This counter is incremented whenever the Execution Server receives a responseAuthentication CAP message"
    ::= { capStats 15 }

  bwCAPStatsInfoRequests OBJECT-TYPE
    SYNTAX      Counter32
    MAX-ACCESS  read-write
    STATUS      current
    DESCRIPTION 
        "This counter is incremented whenever the Execution Server receives a infoRequest CAP message"
    ::= { capStats 16 }

  bwCAPStatsInfoResponses OBJECT-TYPE
    SYNTAX      Counter32
    MAX-ACCESS  read-write
    STATUS      current
    DESCRIPTION 
        "This counter is incremented whenever the Execution Server receives a infoResponse CAP message"
    ::= { capStats 17 }

  bwCAPStatsExternalNotifies OBJECT-TYPE
    SYNTAX      Counter32
    MAX-ACCESS  read-write
    STATUS      current
    DESCRIPTION 
        "This counter is incremented whenever the Execution Server receives a externalNotify CAP message"
    ::= { capStats 18 }

  bwCAPMonitoringUsersRequests OBJECT-TYPE
    SYNTAX      Counter32
    MAX-ACCESS  read-write
    STATUS      current
    DESCRIPTION 
        "The number of monitoringUsersRequest CAP messages received."
    ::= { capStats 19 }

  bwCAPMonitoringUsersResponses OBJECT-TYPE
    SYNTAX      Counter32
    MAX-ACCESS  read-write
    STATUS      current
    DESCRIPTION 
        "The number of monitoringUsersResponse CAP messages sent."
    ::= { capStats 20 }

  bwCAPStatsQueueUpdatesOut OBJECT-TYPE
    SYNTAX      Counter32
    MAX-ACCESS  read-write
    STATUS      current
    DESCRIPTION 
        "This counter reflects the number of CAP queueUpdate messages that have been sent out by the system."
    ::= { capStats 21 }

  bwCAPStatsQueueActionsIn OBJECT-TYPE
    SYNTAX      Counter32
    MAX-ACCESS  read-write
    STATUS      current
    DESCRIPTION 
        "This counter reflects the number of CAP queueAction messages that have been received by the system."
    ::= { capStats 22 }

  bwCAPStatsDatagramsIn OBJECT-TYPE
    SYNTAX      Counter32
    MAX-ACCESS  read-write
    STATUS      current
    DESCRIPTION 
        "This counter reflects the number of CAP datagram  commands  that have been received by the system."
    ::= { capStats 23 }

  bwCAPStatsDatagramsOut OBJECT-TYPE
    SYNTAX      Counter32
    MAX-ACCESS  read-write
    STATUS      current
    DESCRIPTION 
        "This counter reflects the number of CAP datagram  commands  that have been sent by the system."
    ::= { capStats 24 }

  bwCAPStatsTotalMsgs OBJECT-TYPE
    SYNTAX      Counter32
    MAX-ACCESS  read-write
    STATUS      current
    DESCRIPTION 
        "This counter cumulates the total number of CAP messages that have been handled by the system."
    ::= { capStats 25 }

  bwCAPNumInboundDiscardedMessages OBJECT-TYPE
    SYNTAX      Counter32
    MAX-ACCESS  read-write
    STATUS      current
    DESCRIPTION 
        "This is the number of inbound messages that were discarded from the inbound queue."
    ::= { capStats 26 }

  bwCAPNumOutboundDiscardedMessages OBJECT-TYPE
    SYNTAX      Counter32
    MAX-ACCESS  read-write
    STATUS      current
    DESCRIPTION 
        "This is the number of outbound messages that were discarded from the outbound queue."
    ::= { capStats 27 }

  bwCAPNumConnections OBJECT-TYPE
    SYNTAX      Counter32
    MAX-ACCESS  read-write
    STATUS      current
    DESCRIPTION 
        "This is the number of connections that were created on the execution server for the CAP protocol."
    ::= { capStats 28 }

  bwCAPNumDisconnections OBJECT-TYPE
    SYNTAX      Counter32
    MAX-ACCESS  read-write
    STATUS      current
    DESCRIPTION 
        "This is the number of disconnections that were performed on the execution server for the CAP protocol."
    ::= { capStats 29 }

  bwCAPNumCCC2Connections OBJECT-TYPE
    SYNTAX      Counter32
    MAX-ACCESS  read-write
    STATUS      current
    DESCRIPTION 
        "This is the number of connections that were created on the execution server for the CCC2 protocol."
    ::= { capStats 30 }

  bwCAPNumCCC2Disconnections OBJECT-TYPE
    SYNTAX      Counter32
    MAX-ACCESS  read-write
    STATUS      current
    DESCRIPTION 
        "This is the number of disconnections that were performed on the execution server for the CCC2 protocol."
    ::= { capStats 31 }

  bwCAPNumCapSCallCenterConnections OBJECT-TYPE
    SYNTAX      Counter32
    MAX-ACCESS  read-write
    STATUS      current
    DESCRIPTION 
        "This is the number of connections that were created on the execution server for the CapSCallCenter protocol."
    ::= { capStats 32 }

  bwCAPNumCapSCallCenterDisconnections OBJECT-TYPE
    SYNTAX      Counter32
    MAX-ACCESS  read-write
    STATUS      current
    DESCRIPTION 
        "This is the number of disconnections that were performed on the execution server for the CapSCallCenter protocol."
    ::= { capStats 33 }

-- Protocol :: SMDI ...........................................

  bwSmdiNbOfActiveConnection OBJECT-TYPE
    SYNTAX      Gauge32
    MAX-ACCESS  read-only
    STATUS      current
    DESCRIPTION 
        "Counts the total number of currently active Terminal Server SMDI connections."
    ::= { smdiStats 1 }

  bwSmdiNbOfOpenedConnection OBJECT-TYPE
    SYNTAX      Counter32
    MAX-ACCESS  read-write
    STATUS      current
    DESCRIPTION 
        "This counter gives the total number of SMDI connections that were opened since the last reboot of the system or reset of the PMs."
    ::= { smdiStats 2 }

  bwSmdiIncomingMWIActivationRequests OBJECT-TYPE
    SYNTAX      Counter32
    MAX-ACCESS  read-write
    STATUS      current
    DESCRIPTION 
        "This counter reflects the number of SMDI MWI activation requests that were received and processed by the server."
    ::= { smdiStats 3 }

  bwSmdiIncomingMWIDesactivationRequests OBJECT-TYPE
    SYNTAX      Counter32
    MAX-ACCESS  read-write
    STATUS      current
    DESCRIPTION 
        "This counter reflects the number of SMDI MWI desactivation requests that were received and processed by the server."
    ::= { smdiStats 4 }

  bwSmdiInvalidRequestsReceived OBJECT-TYPE
    SYNTAX      Counter32
    MAX-ACCESS  read-write
    STATUS      current
    DESCRIPTION 
        "This counter reflects the number of invalid SMDI requests."
    ::= { smdiStats 5 }

  bwSmdiBlockResponsesSent OBJECT-TYPE
    SYNTAX      Counter32
    MAX-ACCESS  read-write
    STATUS      current
    DESCRIPTION 
        "This counter reflects the number of SMDI MWI negative acknowledgement with a cause set to BLK."
    ::= { smdiStats 6 }

  bwSmdiInvalidResponsesSent OBJECT-TYPE
    SYNTAX      Counter32
    MAX-ACCESS  read-write
    STATUS      current
    DESCRIPTION 
        "This counter reflects the number of SMDI MWI negative acknowledgement with a cause set to INV."
    ::= { smdiStats 7 }

  bwSmdiOutgoingMWIActivationRequests OBJECT-TYPE
    SYNTAX      Counter32
    MAX-ACCESS  read-write
    STATUS      current
    DESCRIPTION 
        "This counter reflects the number of Number of outgoing SMDI MWI OP message."
    ::= { smdiStats 8 }

  bwSmdiOutgoingMWIDeactivationRequests OBJECT-TYPE
    SYNTAX      Counter32
    MAX-ACCESS  read-write
    STATUS      current
    DESCRIPTION 
        "This counter reflects the number of Number of outgoing SMDI MWI RMV message."
    ::= { smdiStats 9 }

  bwSmdiBlockResponsesReceived OBJECT-TYPE
    SYNTAX      Counter32
    MAX-ACCESS  read-write
    STATUS      current
    DESCRIPTION 
        "This counter reflects the number of SMDI MWI negative acknowledgement with a cause set to BLK received from a station host, i.e. a Class 5 End Office."
    ::= { smdiStats 10 }

  bwSmdiInvalidResponsesReceived OBJECT-TYPE
    SYNTAX      Counter32
    MAX-ACCESS  read-write
    STATUS      current
    DESCRIPTION 
        "This counter reflects the number of SMDI MWI negative acknowledgement with a cause set to INV."
    ::= { smdiStats 11 }

  bwSMDIMessageDeskMessageSent OBJECT-TYPE
    SYNTAX      Counter32
    MAX-ACCESS  read-write
    STATUS      current
    DESCRIPTION 
        "This counter reflects the number of outgoing SMDI MD messages sent by BroadWorks."
    ::= { smdiStats 12 }


-- Media management ...........................................

  bwMediaCommandsTransmitted OBJECT-TYPE
    SYNTAX      Counter32
    MAX-ACCESS  read-write
    STATUS      current
    DESCRIPTION 
        "Contains the number of times a media command was transmitted, for the entire Application Server."
    ::= { mediaStats 1 }

  bwMediaNotificationsReceived OBJECT-TYPE
    SYNTAX      Counter32
    MAX-ACCESS  read-write
    STATUS      current
    DESCRIPTION 
        "Contains the number of times a media notification was received, for the entire Application Server."
    ::= { mediaStats 2 }

  bwMediaResourceAllocAttempts OBJECT-TYPE
    SYNTAX      Counter32
    MAX-ACCESS  read-write
    STATUS      current
    DESCRIPTION 
        "Contains the number of media resource allocation attempts, for the entire Application Server."
    ::= { mediaStats 3 }

  bwMediaResourceAllocFailures OBJECT-TYPE
    SYNTAX      Counter32
    MAX-ACCESS  read-write
    STATUS      current
    DESCRIPTION 
        "Contains the number of times a media command was transmitted, for the entire Application Server."
    ::= { mediaStats 4 }

-- Media Cr Interface ...........................................

  bwMediaCrIncomingMessageCount OBJECT-TYPE
    SYNTAX      Counter32
    MAX-ACCESS  read-only
    STATUS      current
    DESCRIPTION 
        "This is the number of Cr messages received over all Cr connections"
    ::= { crStats 1 }

  bwMediaCrOutgoingMessageCount OBJECT-TYPE
    SYNTAX      Counter32
    MAX-ACCESS  read-only
    STATUS      current
    DESCRIPTION 
        "This is the number of Cr messages sent over all Cr connections."
    ::= { crStats 2 }

  bwMediaCrConnectionCount OBJECT-TYPE
    SYNTAX      Counter32
    MAX-ACCESS  read-only
    STATUS      current
    DESCRIPTION 
        "This is the number of active Cr connections."
    ::= { crStats 3 }

  bwCrConnectionStatsTable OBJECT-TYPE
    SYNTAX      SEQUENCE OF BwCrConnectionStatsEntry
    MAX-ACCESS  not-accessible
    STATUS      current
    DESCRIPTION
        "This table contains counters for the Medi Cr connection."
    ::=  { crStats 4 }

  bwMediaCrModifyConferenceFailureCount OBJECT-TYPE
    SYNTAX      Counter32
    MAX-ACCESS  read-only
    STATUS      current
    DESCRIPTION 
        "This is the number of Cr modify conference failures."
-- @feature:179056
    ::= { crStats 5 }

  bwMediaCrReconnectionCount  OBJECT-TYPE
    SYNTAX      Counter32
    MAX-ACCESS  read-only
    STATUS      current
    DESCRIPTION 
        "This is the number of times the MediaCr connections are reconnected to a secondary Media Server."
-- @feature:184307
    ::= { crStats 6 }

  bwMediaCrRecoveredConferencesCount OBJECT-TYPE
    SYNTAX      Counter32
    MAX-ACCESS  read-only
    STATUS      current
    DESCRIPTION 
        "This is the number of times a conference (N-Way, Instant Group, Group Page, Shared Call Appearance Bridging, DTMF Transmission, Push To Talk, Call Recording, etc.) is reconnected to a secondary Media Server. Note: Call Recording is included in this count."
-- @feature:184307
    ::= { crStats 7 }

  bwCrConnectionStatsEntry OBJECT-TYPE
    SYNTAX      BwCrConnectionStatsEntry
    MAX-ACCESS  not-accessible
    STATUS      current
    DESCRIPTION
        "This row contains information on a particular Media Cr"
    INDEX   {  bwMediaCrConnectionIndex  }
                ::=  { bwCrConnectionStatsTable 1 }

  BwCrConnectionStatsEntry  ::=  SEQUENCE {
    bwMediaCrConnectionIndex                    Unsigned32,
    bwMediaCrConnectionAddr                     DisplayString,
    bwMediaCrIncomingMessageCountPerConnection  Gauge32,
    bwMediaCrOutgoingMessageCountPerConnection  Gauge32,
    bwMediaCrConnectionState                    INTEGER,
    bwMediaCrReconnectionCountPerConnection     Counter32
    }

  bwMediaCrConnectionIndex  OBJECT-TYPE
    SYNTAX      Unsigned32
    MAX-ACCESS  read-only
    STATUS      current
    DESCRIPTION
        "This is the index used to access all Media Cr gauge tables."
    ::=  { bwCrConnectionStatsEntry 1 }

  bwMediaCrConnectionAddr  OBJECT-TYPE
    SYNTAX      DisplayString
    MAX-ACCESS  read-only
    STATUS      current
    DESCRIPTION
        "This represents the Media Cr Connection address."
    ::=  { bwCrConnectionStatsEntry 2 }

  bwMediaCrIncomingMessageCountPerConnection OBJECT-TYPE
    SYNTAX      Gauge32
    MAX-ACCESS  read-only
    STATUS      current
    DESCRIPTION 
        "This is the number of Cr messages sent over a specific Cr connection."
    ::= { bwCrConnectionStatsEntry 3 }

  bwMediaCrOutgoingMessageCountPerConnection OBJECT-TYPE
    SYNTAX      Gauge32
    MAX-ACCESS  read-only
    STATUS      current
    DESCRIPTION 
        "This is the number of Cr messages sent over a specific Cr connection."
    ::= { bwCrConnectionStatsEntry 4 }

  bwMediaCrConnectionState OBJECT-TYPE
    SYNTAX      INTEGER { opening ( 0 ) , opened ( 1 ) , closed ( 2 ) , inactive ( 3 ) }
    MAX-ACCESS  read-only
    STATUS      current
    DESCRIPTION 
        "This is the state of the Cr connection."
    ::= { bwCrConnectionStatsEntry 5 }

  bwMediaCrReconnectionCountPerConnection OBJECT-TYPE
    SYNTAX      Counter32
    MAX-ACCESS  read-write
    STATUS      current
    DESCRIPTION 
        "This is the number of times a specific MediaCr connection is reconnected to a secondary Media Server."
-- @feature:184307
    ::= { bwCrConnectionStatsEntry 6 }

-- WholeSale Protocol management ...........................................

  bwWSPStatsServiceRequestsIn OBJECT-TYPE
    SYNTAX      Counter32
    MAX-ACCESS  read-write
    STATUS      current
    DESCRIPTION 
        "This counter is incremented whenever a WSP ServiceRequest message is received."
    ::= { wspStats 1 }

  bwWSPStatsServiceActionsOut OBJECT-TYPE
    SYNTAX      Counter32
    MAX-ACCESS  read-write
    STATUS      current
    DESCRIPTION 
        "This counter is incremented whenever a WSP ServiceAction message is transmitted."
    ::= { wspStats 2 }

  bwWSPStatsServiceUpdatesIn OBJECT-TYPE
    SYNTAX      Counter32
    MAX-ACCESS  read-write
    STATUS      current
    DESCRIPTION 
        "This counter is incremented whenever a WSP ServiceUpdate message is received."
    ::= { wspStats 3 }

  bwWSPStatsServiceAcknowledgementsOut OBJECT-TYPE
    SYNTAX      Counter32
    MAX-ACCESS  read-write
    STATUS      current
    DESCRIPTION 
        "This counter is incremented whenever a WSP ServiceAcknowledgement message is transmitted."
    ::= { wspStats 4 }

-- Realtime Accounting management ...........................................

  bwRealtimeAccountingRequestsTransmitted OBJECT-TYPE
    SYNTAX      Counter32
    MAX-ACCESS  read-write
    STATUS      current
    DESCRIPTION 
        "Number of new Accounting Requests sent to a Radius Server. Incremented each time a new Accounting Request transmission is first attempted toward a Radius Server."
    ::= { realtimeAccountingStats 1 }

  bwRealtimeAccountingRequestsRetransmitted OBJECT-TYPE
    SYNTAX      Counter32
    MAX-ACCESS  read-write
    STATUS      current
    DESCRIPTION 
        "Number of Accounting Requests sent to Radius Server(s) due to retransmissions to the same server. Incremented each time an Accounting Request transmission is retransmitted toward an Accounting Radius Server (be it to the same server as the one where the original request was sent, or to the alternate server)."
    ::= { realtimeAccountingStats 2 }

  bwRealtimeAccountingRequestsDropped OBJECT-TYPE
    SYNTAX      Counter32
    MAX-ACCESS  read-write
    STATUS      current
    DESCRIPTION 
        "Number of Accounting Requests that were discarded due to the lack of a responsive Accounting Radius Server. Incremented each time an Accounting Request is dropped, after all transmissions attempts have failed."
    ::= { realtimeAccountingStats 3 }

-- External Call Logs management ...........................................

  bwExternalCallLogsTransmitted OBJECT-TYPE
    SYNTAX      Counter32
    MAX-ACCESS  read-write
    STATUS      current
    DESCRIPTION 
        "Incremented each time a new external call log transmission is first attempted toward a Call detail server."
    ::= { externalCallLogsStats 1 }

  bwExternalCallLogsRetransmitted OBJECT-TYPE
    SYNTAX      Counter32
    MAX-ACCESS  read-write
    STATUS      current
    DESCRIPTION 
        "Incremented each time a new external call log transmission is retransmitted towards a Call Detail Radius Server (be it to the same server as the one where the original call log was sent, or to the alternate server)."
    ::= { externalCallLogsStats 2 }

  bwExternalCallLogsDropped OBJECT-TYPE
    SYNTAX      Counter32
    MAX-ACCESS  read-write
    STATUS      current
    DESCRIPTION 
        "Incremented each time a call log is dropped, after all transmissions attempts have failed."
    ::= { externalCallLogsStats 3 }

  bwExternalCallLogsQueued OBJECT-TYPE
    SYNTAX      Counter32
    MAX-ACCESS  read-write
    STATUS      current
    DESCRIPTION 
        "Incremented each time a call log is written to the AS file-based queue, after all transmissions attempts have failed."
    ::= { externalCallLogsStats 4 }

  bwExternalCallLogsTransmittedFromQueue OBJECT-TYPE
    SYNTAX      Counter32
    MAX-ACCESS  read-write
    STATUS      current
    DESCRIPTION 
        "Incremented on the first attempt to send to the call detail server a call log read from the file based queue."
    ::= { externalCallLogsStats 5 }

  bwExternalCallLogsRetransmittedFromQueue OBJECT-TYPE
    SYNTAX      Counter32
    MAX-ACCESS  read-write
    STATUS      current
    DESCRIPTION 
        "Incremented on all attempts but the first one to send to the Call Detail Server a call log read from the file based queue."
    ::= { externalCallLogsStats 6 }

-- XS - BroadWorks Common Communication Protocol ........................

  bwCommonCommXSStatsTable OBJECT-TYPE
    SYNTAX      SEQUENCE OF BwCommonCommXSStatsEntry
    MAX-ACCESS  not-accessible
    STATUS      current
    DESCRIPTION 
        "This table contains counters for BCCT for the XS process."
    ::= { commonCommStats 1 }

  bwCommonCommXSStatsEntry OBJECT-TYPE
    SYNTAX      BwCommonCommXSStatsEntry
    MAX-ACCESS  not-accessible
    STATUS      current
    DESCRIPTION 
        "Definition of the entries for bwCommonCommXSStatsTable."
    INDEX       { bwCommonCommXSStatsIndex }
    ::= { bwCommonCommXSStatsTable 1 }

  BwCommonCommXSStatsEntry ::= SEQUENCE {
    bwCommonCommXSStatsIndex                    Unsigned32,
    bwCommonCommXSHost                          DisplayString,
    bwCommonCommXSInterface                     DisplayString,
    bwCommonCommXSProtocol                      DisplayString,
    bwCommonCommXSAcceptedOutboundConnections   Counter32,
    bwCommonCommXSAcceptedInboundConnections    Counter32,
    bwCommonCommXSRejectedOutboundConnections   Counter32,
    bwCommonCommXSRejectedInboundConnections    Counter32,
    bwCommonCommXSOutputMessagesProcessed       Counter32,
    bwCommonCommXSInputMessagesProcessed        Counter32,
    bwCommonCommXSOutputCommunicationErrors     Counter32,
    bwCommonCommXSInputCommunicationErrors      Counter32
  }

  bwCommonCommXSStatsIndex OBJECT-TYPE
    SYNTAX      Unsigned32
    MAX-ACCESS  read-only
    STATUS      current
    DESCRIPTION 
        "This integer represents an index in table bwCommonCommXSStatsTable. The index represents a connection for a specific Host-Interfacece-Protocol combination."
    ::= { bwCommonCommXSStatsEntry 1 }

  bwCommonCommXSHost OBJECT-TYPE
    SYNTAX      DisplayString
    MAX-ACCESS  read-only
    STATUS      current
    DESCRIPTION 
        "The address of a host connected to the BroadWorks Common Communication Protocol."
    ::= { bwCommonCommXSStatsEntry 2 }

  bwCommonCommXSInterface OBJECT-TYPE
    SYNTAX      DisplayString
    MAX-ACCESS  read-only
    STATUS      current
    DESCRIPTION 
        "The IP address of a local interface that a protocol is bound to."
    ::= { bwCommonCommXSStatsEntry 3 }

  bwCommonCommXSProtocol OBJECT-TYPE
    SYNTAX      DisplayString
    MAX-ACCESS  read-only
    STATUS      current
    DESCRIPTION 
        "The name of a BroadWorks Common Communication Protocol client protocol, e.g. OCI or SyncApi."
    ::= { bwCommonCommXSStatsEntry 4 }

  bwCommonCommXSAcceptedOutboundConnections OBJECT-TYPE
    SYNTAX      Counter32
    MAX-ACCESS  read-write
    STATUS      current
    DESCRIPTION 
        "This counter is incremented whenever a client in this process connects to the framework to a remote host, using the interface and protocol."
    ::= { bwCommonCommXSStatsEntry 5 }

  bwCommonCommXSAcceptedInboundConnections OBJECT-TYPE
    SYNTAX      Counter32
    MAX-ACCESS  read-write
    STATUS      current
    DESCRIPTION 
        "This counter is incremented whenever a client in this process connects to the framework from a remote host, using the interface and protocol."
    ::= { bwCommonCommXSStatsEntry 6 }

  bwCommonCommXSRejectedOutboundConnections OBJECT-TYPE
    SYNTAX      Counter32
    MAX-ACCESS  read-write
    STATUS      current
    DESCRIPTION 
        "This counter is incremented whenever a client connection request going from this process to a remote host and going through this interface has been rejected for a particular protocol."
    ::= { bwCommonCommXSStatsEntry 7 }

  bwCommonCommXSRejectedInboundConnections OBJECT-TYPE
    SYNTAX      Counter32
    MAX-ACCESS  read-write
    STATUS      current
    DESCRIPTION 
        "This counter is incremented whenever a client connection request coming to this host and going through this interface has been rejected by the framework for a particular protocol."
    ::= { bwCommonCommXSStatsEntry 8 }

  bwCommonCommXSOutputMessagesProcessed OBJECT-TYPE
    SYNTAX      Counter32
    MAX-ACCESS  read-write
    STATUS      current
    DESCRIPTION 
        "This counter is incremented whenever a message has been sent and processed for this host, interface and protocol."
    ::= { bwCommonCommXSStatsEntry 9 }

  bwCommonCommXSInputMessagesProcessed OBJECT-TYPE
    SYNTAX      Counter32
    MAX-ACCESS  read-write
    STATUS      current
    DESCRIPTION 
        "This counter is incremented whenever a message has been received and processed for this host, interface and protocol."
    ::= { bwCommonCommXSStatsEntry 10 }

  bwCommonCommXSOutputCommunicationErrors OBJECT-TYPE
    SYNTAX      Counter32
    MAX-ACCESS  read-write
    STATUS      current
    DESCRIPTION 
        "This counter is incremented whenever a message could not be read because the TCP stack returned an error."
    ::= { bwCommonCommXSStatsEntry 11 }

  bwCommonCommXSInputCommunicationErrors OBJECT-TYPE
    SYNTAX      Counter32
    MAX-ACCESS  read-write
    STATUS      current
    DESCRIPTION 
        "This counter is incremented whenever a message has been sent and processed for this host, interface and protocol."
    ::= { bwCommonCommXSStatsEntry 12 }

-- XS - TCP Framework ........................

  bwXSTcpServersStatsTable OBJECT-TYPE
    SYNTAX      SEQUENCE OF BwXSTcpServersStatsEntry
    MAX-ACCESS  not-accessible
    STATUS      current
    DESCRIPTION 
        "This table contains counters for TCP underlying framework for the XS process."
    ::= { tcpStats 1 }

  bwXSTcpServersStatsEntry OBJECT-TYPE
    SYNTAX      BwXSTcpServersStatsEntry
    MAX-ACCESS  not-accessible
    STATUS      current
    DESCRIPTION 
        "Definition of the entries for bwXSTcpServersStatsTable."
    INDEX       { bwXSTcpServersStatsIndex }
    ::= { bwXSTcpServersStatsTable 1 }

  BwXSTcpServersStatsEntry ::= SEQUENCE {
    bwXSTcpServersStatsIndex                Unsigned32,
    bwXSTcpServersName                      DisplayString,
    bwXSTcpServersNbConnectionsAccepted     Counter32,
    bwXSTcpServersNbConnectionsRefused      Counter32,
    bwXSTcpServersNbConnectionsInitiated    Counter32,
    bwXSTcpServersNbConnectionsClosed       Counter32,
    bwXSTcpServersNbBytesSent               Gauge32,
    bwXSTcpServersNbBytesReceived           Gauge32,
    bwXSTcpServersOutgoingQueueSize         Gauge32,
    bwXSTcpServersIncomingQueueSize         Gauge32,
    bwXSTcpServersNbBytesSentSecure         Gauge32,
    bwXSTcpServersNbBytesReceivedSecure     Gauge32
  }

  bwXSTcpServersStatsIndex OBJECT-TYPE
    SYNTAX      Unsigned32
    MAX-ACCESS  read-only
    STATUS      current
    DESCRIPTION 
        "This integer represents an index in table bwXSTcpServersStatsTable. This is the index to a specific TCP server name."
    ::= { bwXSTcpServersStatsEntry 1 }

  bwXSTcpServersName OBJECT-TYPE
    SYNTAX      DisplayString
    MAX-ACCESS  read-only
    STATUS      current
    DESCRIPTION 
        "The name of TCP server - Names are internally defined at at the application level."
    ::= { bwXSTcpServersStatsEntry 2 }

  bwXSTcpServersNbConnectionsAccepted OBJECT-TYPE
    SYNTAX      Counter32
    MAX-ACCESS  read-write
    STATUS      current
    DESCRIPTION 
        "This counter represents the number of connections accepted by the TCP server."
    ::= { bwXSTcpServersStatsEntry 3 }

  bwXSTcpServersNbConnectionsRefused OBJECT-TYPE
    SYNTAX      Counter32
    MAX-ACCESS  read-write
    STATUS      current
    DESCRIPTION 
        "This counter represents the number of connections refused by the TCP server."
    ::= { bwXSTcpServersStatsEntry 4 }

  bwXSTcpServersNbConnectionsInitiated OBJECT-TYPE
    SYNTAX      Counter32
    MAX-ACCESS  read-write
    STATUS      current
    DESCRIPTION 
        "This counter represents the number of connections initiated by the TCP server."
    ::= { bwXSTcpServersStatsEntry 5 }

  bwXSTcpServersNbConnectionsClosed OBJECT-TYPE
    SYNTAX      Counter32
    MAX-ACCESS  read-write
    STATUS      current
    DESCRIPTION 
        "This counter represents the number of connections closed by the TCP server or remote hosts."
    ::= { bwXSTcpServersStatsEntry 6 }

  bwXSTcpServersNbBytesSent OBJECT-TYPE
    SYNTAX      Gauge32
    MAX-ACCESS  read-write
    STATUS      current
    DESCRIPTION 
        "This counter represents the number of bytes sent by the TCP server."
    ::= { bwXSTcpServersStatsEntry 7 }

  bwXSTcpServersNbBytesReceived OBJECT-TYPE
    SYNTAX      Gauge32
    MAX-ACCESS  read-write
    STATUS      current
    DESCRIPTION 
        "This counter represents the number of bytes received by the TCP server."
    ::= { bwXSTcpServersStatsEntry 8 }

  bwXSTcpServersOutgoingQueueSize OBJECT-TYPE
    SYNTAX      Gauge32
    MAX-ACCESS  read-only
    STATUS      current
    DESCRIPTION 
        "This counter represents the number of bytes in the outgoing queue."
    ::= { bwXSTcpServersStatsEntry 9 }

  bwXSTcpServersIncomingQueueSize OBJECT-TYPE
    SYNTAX      Gauge32
    MAX-ACCESS  read-only
    STATUS      current
    DESCRIPTION 
        "This counter represents the number of bytes in the incoming queue."
    ::= { bwXSTcpServersStatsEntry 10 }

  bwXSTcpServersNbBytesSentSecure OBJECT-TYPE
    SYNTAX      Gauge32
    MAX-ACCESS  read-write
    STATUS      current
    DESCRIPTION 
        "This counter represents the number of bytes sent by the TCP server over secure connections."
    ::= { bwXSTcpServersStatsEntry 11 }

  bwXSTcpServersNbBytesReceivedSecure OBJECT-TYPE
    SYNTAX      Gauge32
    MAX-ACCESS  read-write
    STATUS      current
    DESCRIPTION 
        "This counter represents the number of bytes received by the TCP server over secure connections."
    ::= { bwXSTcpServersStatsEntry 12 }

-- XS - Concurrent Framework ........................

  bwXSMonitoringExecutorTable OBJECT-TYPE
    SYNTAX      SEQUENCE OF BwXSMonitoringExecutorEntry
    MAX-ACCESS  not-accessible
    STATUS      current
    DESCRIPTION 
        "This table contains counters for the concurrent framework."
    ::= { concurrentStats 1 }

  bwXSMonitoringExecutorEntry OBJECT-TYPE
    SYNTAX      BwXSMonitoringExecutorEntry
    MAX-ACCESS  not-accessible
    STATUS      current
    DESCRIPTION 
        "Definition of the entries for bwXSMonitoringExecutorTable."
    INDEX       { bwXSMonitoringExecutorIndex }
    ::= { bwXSMonitoringExecutorTable 1 }

  BwXSMonitoringExecutorEntry ::= SEQUENCE {
    bwXSMonitoringExecutorIndex             Unsigned32,
    bwXSMonitoringExecutorName              DisplayString,
    bwXSMonitoringExecutorCurrentPoolSize   Gauge32,
    bwXSMonitoringExecutorMaxPoolSize       Gauge32,
    bwXSMonitoringExecutorAvgActiveThreads  Gauge32,
    bwXSMonitoringExecutorTaskQueueSize     Gauge32,
    bwXSMonitoringExecutorNbTasksRun        Counter32,
    bwXSMonitoringExecutorNbWarnings        Counter32,
    bwXSMonitoringExecutorNbErrors          Counter32,
    bwXSMonitoringExecutorLongestTaskMs     Gauge32,
    bwXSMonitoringExecutorLongestTaskName   DisplayString
  }

  bwXSMonitoringExecutorIndex OBJECT-TYPE
    SYNTAX      Unsigned32
    MAX-ACCESS  read-only
    STATUS      current
    DESCRIPTION 
        "This integer represents an index in table bwXSMonitoringExecutorTable. This is the index to a specific Monitoring Executor name."
    ::= { bwXSMonitoringExecutorEntry 1 }

  bwXSMonitoringExecutorName OBJECT-TYPE
    SYNTAX      DisplayString
    MAX-ACCESS  read-only
    STATUS      current
    DESCRIPTION 
        "The name of the Monitoring Executor - Names are internally defined at the application level."
    ::= { bwXSMonitoringExecutorEntry 2 }

  bwXSMonitoringExecutorCurrentPoolSize OBJECT-TYPE
    SYNTAX      Gauge32
    MAX-ACCESS  read-only
    STATUS      current
    DESCRIPTION 
        "The current thread pool size"
    ::= { bwXSMonitoringExecutorEntry 3 }

  bwXSMonitoringExecutorMaxPoolSize OBJECT-TYPE
    SYNTAX      Gauge32
    MAX-ACCESS  read-only
    STATUS      current
    DESCRIPTION 
        "The maximum thread pool size"
    ::= { bwXSMonitoringExecutorEntry 4 }

  bwXSMonitoringExecutorAvgActiveThreads OBJECT-TYPE
    SYNTAX      Gauge32
    MAX-ACCESS  read-only
    STATUS      current
    DESCRIPTION 
        "The average number of active threads, rounded up"
    ::= { bwXSMonitoringExecutorEntry 5 }

  bwXSMonitoringExecutorTaskQueueSize OBJECT-TYPE
    SYNTAX      Gauge32
    MAX-ACCESS  read-only
    STATUS      current
    DESCRIPTION 
        "Number of tasks in the queue (includes scheduled and recurring tasks)"
    ::= { bwXSMonitoringExecutorEntry 6 }

  bwXSMonitoringExecutorNbTasksRun OBJECT-TYPE
    SYNTAX      Counter32
    MAX-ACCESS  read-write
    STATUS      current
    DESCRIPTION 
        "Number of tasks run"
    ::= { bwXSMonitoringExecutorEntry 7 }

  bwXSMonitoringExecutorNbWarnings OBJECT-TYPE
    SYNTAX      Counter32
    MAX-ACCESS  read-write
    STATUS      current
    DESCRIPTION 
        "Number of warnings that occured"
    ::= { bwXSMonitoringExecutorEntry 8 }

  bwXSMonitoringExecutorNbErrors OBJECT-TYPE
    SYNTAX      Counter32
    MAX-ACCESS  read-write
    STATUS      current
    DESCRIPTION 
        "Number of errors that occured"
    ::= { bwXSMonitoringExecutorEntry 9 }

  bwXSMonitoringExecutorLongestTaskMs OBJECT-TYPE
    SYNTAX      Gauge32
    MAX-ACCESS  read-only
    STATUS      current
    DESCRIPTION 
        "Longest completed task execution time in milliseconds"
    ::= { bwXSMonitoringExecutorEntry 10 }

  bwXSMonitoringExecutorLongestTaskName OBJECT-TYPE
    SYNTAX      DisplayString
    MAX-ACCESS  read-only
    STATUS      current
    DESCRIPTION 
        "Longest completed task name"
    ::= { bwXSMonitoringExecutorEntry 11 }

-- XS - SOAP ........................

  bwSOAPMaxSessions OBJECT-TYPE
    SYNTAX      Gauge32
    MAX-ACCESS  read-only
    STATUS      current
    DESCRIPTION 
        "Maximum number of incoming SOAP sessions simultaneously active since the system was started."
    ::= { soapStats 1 }

  bwSOAPAvgSessions OBJECT-TYPE
    SYNTAX      Gauge32
    MAX-ACCESS  read-only
    STATUS      current
    DESCRIPTION 
        "Average number of incoming SOAP sessions simultaneously active, based on a rolling average over the last 100 sessions."
    ::= { soapStats 2 }

  bwSOAPMaxThreads OBJECT-TYPE
    SYNTAX      Gauge32
    MAX-ACCESS  read-only
    STATUS      current
    DESCRIPTION 
        "This gauge measures the maximum percentage of SOAP processing threads simultaneously active since the system was started."
    ::= { soapStats 3 }

  bwSOAPAvgThreads OBJECT-TYPE
    SYNTAX      Gauge32
    MAX-ACCESS  read-only
    STATUS      current
    DESCRIPTION 
        "Average percentage of SOAP threads simultaneously active, based on a rolling average over the last 100 sessions."
    ::= { soapStats 4 }

  bwSOAPMaxServiceTime OBJECT-TYPE
    SYNTAX      Gauge32
    MAX-ACCESS  read-only
    STATUS      current
    DESCRIPTION 
        "Maximum time in milliseconds required to process an incoming SOAP request, since the system was started."
    ::= { soapStats 5 }

  bwSOAPAvgServiceTime OBJECT-TYPE
    SYNTAX      Gauge32
    MAX-ACCESS  read-only
    STATUS      current
    DESCRIPTION 
        "Average time in milliseconds required to process an incoming SOAP request, based on a rolling average over the last 100 requests."
    ::= { soapStats 6 }

  bwSOAPNumDroppedRequests OBJECT-TYPE
    SYNTAX      Counter32
    MAX-ACCESS  read-write
    STATUS      current
    DESCRIPTION 
        "Number of SOAP server requests dropped because the number of SOAP threads was too low."
    ::= { soapStats 7 }

-- XS - SMPP.................................................
  bwSmppSubmitSMRequestsSent OBJECT-TYPE
    SYNTAX      Counter32
    MAX-ACCESS  read-write
    STATUS      current
    DESCRIPTION 
        "Number of outgoing SMPP submit_sm requests sent."
    ::= { smppStats 1 }

  bwSmppInvalidSubmitSMResponsesReceived OBJECT-TYPE
    SYNTAX      Counter32
    MAX-ACCESS  read-write
    STATUS      current
    DESCRIPTION 
        "Count of invalid received submit_sm_resp"
    ::= { smppStats 2 }

  bwSmppSubmitSMResponseTimeout OBJECT-TYPE
    SYNTAX      Counter32
    MAX-ACCESS  read-write
    STATUS      current
    DESCRIPTION 
        "Number of submit_sm requests timeouts detected."
    ::= { smppStats 3 }

-- dnsModule modules

  bwDnsQueryTimeMax OBJECT-TYPE
    SYNTAX      Gauge32
    MAX-ACCESS  read-write
    STATUS      current
    DESCRIPTION 
        "This gauge reports the maximum query time in milliseconds."
    ::= { dnsStats 1 }

  bwDnsQueryTimeMaxTimestampMSB OBJECT-TYPE
    SYNTAX      Gauge32
    MAX-ACCESS  read-write
    STATUS      current
    DESCRIPTION 
        "The gauge reports the most significant part of the timestamp (4 most significant bytes) of when bwDnsQueryTimeMax was obtained."
    ::= { dnsStats 2 }

  bwDnsQueryTimeMaxTimestampLSB OBJECT-TYPE
    SYNTAX      Gauge32
    MAX-ACCESS  read-write
    STATUS      current
    DESCRIPTION 
        "The gauge reports the least significant part of the timestamp (4 least significant bytes) of when bwDnsQueryTimeMax was obtained."
    ::= { dnsStats 3 }

  bwDnsQueryTimeAvg OBJECT-TYPE
    SYNTAX      Gauge32
    MAX-ACCESS  read-write
    STATUS      current
    DESCRIPTION 
        "This gauge reports the average query time in milliseconds."
    ::= { dnsStats 4 }

  bwDnsStatsQueriesTable OBJECT-TYPE
    SYNTAX      SEQUENCE OF BwDnsStatsQueriesEntry
    MAX-ACCESS  not-accessible
    STATUS      current
    DESCRIPTION 
        "This table contains DNS statistics."
    ::= { dnsStats 5 }

  bwDnsStatsQueriesEntry OBJECT-TYPE
    SYNTAX      BwDnsStatsQueriesEntry
    MAX-ACCESS  not-accessible
    STATUS      current
    DESCRIPTION 
        "This row contains information on a particular DNS query type."
    INDEX       { bwDnsStatsQueryIndex }
    ::= { bwDnsStatsQueriesTable 1 }

  BwDnsStatsQueriesEntry ::= SEQUENCE {
    bwDnsStatsQueryIndex          Unsigned32,
    bwDnsStatsQueryType           DisplayString,
    bwDnsStatsQueries             Counter32,
    bwDnsStatsQueryTimeouts       Counter32,
    bwDnsStatsCallpQueryTimeouts  Counter32,
    bwDnsStatsQueryErrorResponses Counter32
  }

  bwDnsStatsQueryIndex OBJECT-TYPE
    SYNTAX      Unsigned32
    MAX-ACCESS  read-only
    STATUS      current
    DESCRIPTION 
        "This column is the index for the table."
    ::= { bwDnsStatsQueriesEntry 1 }

  bwDnsStatsQueryType OBJECT-TYPE
    SYNTAX      DisplayString
    MAX-ACCESS  read-only
    STATUS      current
    DESCRIPTION 
        "This column represents the DNS query type."
    ::= { bwDnsStatsQueriesEntry 2 }

  bwDnsStatsQueries OBJECT-TYPE
    SYNTAX      Counter32
    MAX-ACCESS  read-write
    STATUS      current
    DESCRIPTION 
        "This counter reflects the number of DNS queries for a given type."
    ::= { bwDnsStatsQueriesEntry 3 }

  bwDnsStatsQueryTimeouts OBJECT-TYPE
    SYNTAX      Counter32
    MAX-ACCESS  read-write
    STATUS      current
    DESCRIPTION 
        "This counter reflects the number of DNS queries timeouts for a given type."
    ::= { bwDnsStatsQueriesEntry 4 }

  bwDnsStatsCallpQueryTimeouts OBJECT-TYPE
    SYNTAX      Counter32
    MAX-ACCESS  read-write
    STATUS      current
    DESCRIPTION 
        "This counter reflects the number of DNS queries timeouts for a given type initiated from a call processing thread."
    ::= { bwDnsStatsQueriesEntry 5 }

  bwDnsStatsQueryErrorResponses OBJECT-TYPE
    SYNTAX      Counter32
    MAX-ACCESS  read-write
    STATUS      current
    DESCRIPTION 
        "This counter tracks the number of times BroadWorks receives DNS error response."
-- @feature:193116
    ::= { bwDnsStatsQueriesEntry 6 }

  bwDnsQueryTimeStatsReset OBJECT-TYPE
    SYNTAX      Counter32
    MAX-ACCESS  read-write
    STATUS      current
    DESCRIPTION 
        "When set to a value other than 0, the values of the gauges bwDnsQueryTimeMax, bwDnsQueryTimeAvg, bwDnsQueryTimeMaxTimestampMSB, and bwDnsQueryTimeMaxTimestampLSB are reset to 0."
    ::= { dnsStats 6 }

  dnsNumberPortabilityStats OBJECT IDENTIFIER
    ::= { dnsStats 7 }

  bwDnsNumberPortabilityMaxThreads OBJECT-TYPE
    SYNTAX      Gauge32
    MAX-ACCESS  read-only
    STATUS      current
    DESCRIPTION 
        "This gauge measures the maximum number of simultaneously active number portability DNS processing threads since the system was started.  A DNS number portability thread is used by a DNS session for a number portability query."
-- @feature:193116
    ::= { dnsNumberPortabilityStats 1 }

  bwDnsNumberPortabilityAvgThreads OBJECT-TYPE
    SYNTAX      Gauge32
    MAX-ACCESS  read-only
    STATUS      current
    DESCRIPTION 
        "This gauge measures the average number of simultaneously active number portability DNS threads, based on a rolling average over the last 100 sessions.  Each data point is computed right after the creating of a DNS session for a number portability query."
-- @feature:193116
    ::= { dnsNumberPortabilityStats 2 }

  bwDnsNumberPortabilityQueryMaxTime OBJECT-TYPE
    SYNTAX      Gauge32
    MAX-ACCESS  read-only
    STATUS      current
    DESCRIPTION 
        "This gauge reports the maximum number portability database query time in milliseconds."
-- @feature:193116
    ::= { dnsNumberPortabilityStats 3 }

  bwDnsNumberPortabilityQueryAvgTime OBJECT-TYPE
    SYNTAX      Gauge32
    MAX-ACCESS  read-only
    STATUS      current
    DESCRIPTION 
        "This gauge reports the average number portability database query time in milliseconds."
-- @feature:193116
    ::= { dnsNumberPortabilityStats 4 }

  bwDnsNumberPortabilityNumDroppedRequests OBJECT-TYPE
    SYNTAX      Counter32
    MAX-ACCESS  read-write
    STATUS      current
    DESCRIPTION 
        "This counter tracks the number of number portability DNS requests dropped because the number of DNS number portability threads was too low."
-- @feature:193116
    ::= { dnsNumberPortabilityStats 5 }

-- Offline Charging Module
  bwOfflineChargingACROut OBJECT-TYPE
    SYNTAX      Counter32
    MAX-ACCESS  read-write
    STATUS      obsolete
    DESCRIPTION 
        "This is the number of ACR unique requests sent by BroadWorks. If the request is transmitted multiple times, only the first transmission is counted."
    ::= { offlineChargingStats 1 }

  bwOfflineChargingACASuccessIn OBJECT-TYPE
    SYNTAX      Counter32
    MAX-ACCESS  read-write
    STATUS      obsolete
    DESCRIPTION 
        "This is the number of ACA messages received indicating success."
    ::= { offlineChargingStats 2 }

  bwOfflineChargingACAFailureIn OBJECT-TYPE
    SYNTAX      Counter32
    MAX-ACCESS  read-write
    STATUS      obsolete
    DESCRIPTION 
        "This is the number of ACA messages received indicating failure."
    ::= { offlineChargingStats 3 }

  bwOfflineChargingACRTimeout OBJECT-TYPE
    SYNTAX      Counter32
    MAX-ACCESS  read-write
    STATUS      obsolete
    DESCRIPTION 
        "This is the number ACR messages for which an ACA message has not been received before timeout."
    ::= { offlineChargingStats 4 }

  bwOfflineChargingUnknownServer OBJECT-TYPE
    SYNTAX      Counter32
    MAX-ACCESS  read-write
    STATUS      obsolete
    DESCRIPTION 
        "This is the number of ACR messages not sent because one or more specified offline charging servers are not configured within BroadWorks."
    ::= { offlineChargingStats 5 }

  bwOfflineChargingInvalidServer OBJECT-TYPE
    SYNTAX      Counter32
    MAX-ACCESS  read-write
    STATUS      obsolete
    DESCRIPTION 
        "This is the number of ACR messages not sent because the redundancy configuration of one or more specified offline charging server is incompatible with the requested destination."
    ::= { offlineChargingStats 6 }

  bwOfflineChargingServerUnreachable OBJECT-TYPE
    SYNTAX      Counter32
    MAX-ACCESS  read-write
    STATUS      current
    DESCRIPTION 
        "This is the number of ACR messages not sent because none of the destination offline charging servers is currently connected."
    ::= { offlineChargingStats 7 }

  bwOfflineChargingDFNDown OBJECT-TYPE
    SYNTAX      Counter32
    MAX-ACCESS  read-write
    STATUS      obsolete
    DESCRIPTION 
        "This is the number of ACR messages not sent because of communication failure with the DFN process."
    ::= { offlineChargingStats 8 }

  bwOfflineChargingAPNError OBJECT-TYPE
    SYNTAX      Counter32
    MAX-ACCESS  read-write
    STATUS      obsolete
    DESCRIPTION 
        "This is the number of ACR messages not sent because of an error in the APN."
    ::= { offlineChargingStats 9 }

  bwOfflineChargingQueued OBJECT-TYPE
    SYNTAX      Counter32
    MAX-ACCESS  read-write
    STATUS      current
    DESCRIPTION 
        "This is the number of offline charging requests that were written to the Application Server file-based queued due to the lack of a responsive offline charging server."
    ::= { offlineChargingStats 10 }

  bwOfflineChargingTransmittedFromQueue OBJECT-TYPE
    SYNTAX      Counter32
    MAX-ACCESS  read-write
    STATUS      current
    DESCRIPTION 
        "This is the number of offline charging requests read from the Application Server file-based queue."
    ::= { offlineChargingStats 11 }

  bwOfflineChargingRetransmittedFromQueue OBJECT-TYPE
    SYNTAX      Counter32
    MAX-ACCESS  read-write
    STATUS      current
    DESCRIPTION 
        "This is the number of retransmissions of offline charging request read from the Application Server file-based queue to an external offline charging server."
    ::= { offlineChargingStats 12 }

-- OCI-C Module ............................................

  bwOCICNumOutgoingOverloadDiscard OBJECT-TYPE
    SYNTAX      Counter32
    MAX-ACCESS  read-write
    STATUS      current
    DESCRIPTION 
        "This is the number of OCI-C messages that have been discarded due to an overload situation."
    ::= { ocicStats 1 }

  bwOcicStatsTable OBJECT-TYPE
    SYNTAX      SEQUENCE OF BwOcicStatsEntry
    MAX-ACCESS  not-accessible
    STATUS      current
    DESCRIPTION 
        "This table contains OCI-C statistics."
    ::= { ocicStats 2 }

  bwOcicStatsEntry OBJECT-TYPE
    SYNTAX      BwOcicStatsEntry
    MAX-ACCESS  not-accessible
    STATUS      current
    DESCRIPTION 
        "This row contains information on a particular OCI-C statistics table entry."
    INDEX       { bwOCICStatsEntryIndex }
    ::= { bwOcicStatsTable 1 }

  BwOcicStatsEntry ::= SEQUENCE {
    bwOCICStatsEntryIndex               Unsigned32,
    bwOCICApplicationId                 DisplayString,
    bwOCICNumNoConnectionDiscard        Counter32,
    bwOCICNumRouteExhaustionDiscard     Counter32,
    bwOCICNumResponseTimeout            Counter32
  }

  bwOCICStatsEntryIndex OBJECT-TYPE
    SYNTAX      Unsigned32
    MAX-ACCESS  read-only
    STATUS      current
    DESCRIPTION 
        "The index of an bwOcicStatsEntry in the bwOcicStatsTable.  The index represents a specific OCI-C Application ID."
    ::= { bwOcicStatsEntry 1 }

  bwOCICApplicationId OBJECT-TYPE
    SYNTAX      DisplayString
    MAX-ACCESS  read-only
    STATUS      current
    DESCRIPTION 
        "The OCI-C Application ID for an bwOcicStatsEntry in the bwOcicStatsTable."
    ::= { bwOcicStatsEntry 2 }

  bwOCICNumNoConnectionDiscard OBJECT-TYPE
    SYNTAX      Counter32
    MAX-ACCESS  read-write
    STATUS      current
    DESCRIPTION 
        "Number of outgoing OCI-C requests discarded because no connection was available."
    ::= { bwOcicStatsEntry 3 }

  bwOCICNumRouteExhaustionDiscard OBJECT-TYPE
    SYNTAX      Counter32
    MAX-ACCESS  read-write
    STATUS      current
    DESCRIPTION 
        "Number of outgoing OCI-C requests discarded due to route exhaustion."
    ::= { bwOcicStatsEntry 4 }

  bwOCICNumResponseTimeout OBJECT-TYPE
    SYNTAX      Counter32
    MAX-ACCESS  read-write
    STATUS      current
    DESCRIPTION 
        "Number of outgoing OCI-C requests discarded due to response timeout."
    ::= { bwOcicStatsEntry 5 }

-- Online Charging Module ............................................
  bwOnlineChargingCCROut OBJECT-TYPE
    SYNTAX      Counter32
    MAX-ACCESS  read-write
    STATUS      obsolete
    DESCRIPTION 
        "This is the number of CCR unique requests sent by BroadWorks.  If the request is transmitted multiple times, only the first transmission is counted."
    ::= { onlineChargingStats 1 }

  bwOnlineChargingCCASuccessIn OBJECT-TYPE
    SYNTAX      Counter32
    MAX-ACCESS  read-write
    STATUS      obsolete
    DESCRIPTION 
        "This is the number of CCA messages received indicating success."
    ::= { onlineChargingStats 2 }

  bwOnlineChargingCCAFailureIn OBJECT-TYPE
    SYNTAX      Counter32
    MAX-ACCESS  read-write
    STATUS      obsolete
    DESCRIPTION 
        "This is the number of CCA messages received indicating failure.  This does not include failure to grant credits, since this is a normal condition that does not indicate a problem with the system."
    ::= { onlineChargingStats 3 }

  bwOnlineChargingCCRTimeout OBJECT-TYPE
    SYNTAX      Counter32
    MAX-ACCESS  read-write
    STATUS      obsolete
    DESCRIPTION 
        "This is the number of CCR messages for which a CCA message has not been received before timeout."
    ::= { onlineChargingStats 4 }

  bwOnlineChargingUnknownServer OBJECT-TYPE
    SYNTAX      Counter32
    MAX-ACCESS  read-write
    STATUS      obsolete
    DESCRIPTION 
        "This is the number of CCR messages not sent because one or more specified online charging servers are not configured within BroadWorks."
    ::= { onlineChargingStats 5 }

  bwOnlineChargingInvalidServer OBJECT-TYPE
    SYNTAX      Counter32
    MAX-ACCESS  read-write
    STATUS      obsolete
    DESCRIPTION 
        "This is the number of CCR messages not sent because the redundancy configuration of one or more specified online charging servers is incompatible with the requested destination."
    ::= { onlineChargingStats 6 }

  bwOnlineChargingServerUnreachable OBJECT-TYPE
    SYNTAX      Counter32
    MAX-ACCESS  read-write
    STATUS      current
    DESCRIPTION 
        "This is the number of CCR messages not sent because none of the destination online charging servers is currently connected."
    ::= { onlineChargingStats 7 }

  bwOnlineChargingDFNDown OBJECT-TYPE
    SYNTAX      Counter32
    MAX-ACCESS  read-write
    STATUS      obsolete
    DESCRIPTION 
        "This is the number of CCR messages not sent because of communication failure with the DFN process."
    ::= { onlineChargingStats 8 }

  bwOnlineChargingAPNError OBJECT-TYPE
    SYNTAX      Counter32
    MAX-ACCESS  read-write
    STATUS      obsolete
    DESCRIPTION 
        "This is the number of CCR messages not sent because of an error in the APN."
    ::= { onlineChargingStats 9 }

-- BroadWorks Execution Server MIB Conformance Definition  ...........................................

  bwExecutionMibGroups OBJECT IDENTIFIER 
    ::= { bwExecutionMibConformance 1 }

  bwExecutionMibCompliancy OBJECT IDENTIFIER
    ::= { bwExecutionMibConformance 2 }

  bwExecutionMgcpGroup OBJECT-GROUP
    OBJECTS     { bwMGCPStatsMGCPCommandOuts, bwMGCPStatsMGCPCommandIns, 
                  bwMGCPStatsMGCPResponseOuts, 
                  bwMGCPStatsMGCPResponseIns, 
                  bwMGCPStatsAuditConnectionOuts, 
                  bwMGCPStatsAuditEndpointOuts, 
                  bwMGCPStatsCreateConnectionOuts, 
                  bwMGCPStatsDeleteAgentConnectionOuts, 
                  bwMGCPStatsDeleteConnectionOuts, 
                  bwMGCPStatsDeleteGatewayConnectionIns, 
                  bwMGCPStatsEndpointConfigurationOuts, 
                  bwMGCPStatsExtraCommandOuts, 
                  bwMGCPStatsModifyConnectionOuts, 
                  bwMGCPStatsNotificationRequestOuts, 
                  bwMGCPStatsNotifyIns, bwMGCPStatsRestartInProgressIns, 
                  bwMGCPStatsMGCPCommandResponseOuts, 
                  bwMGCPStatsMGCPCommandResponseIns, 
                  bwMGCPStatsAuditConnectionResponseIns, 
                  bwMGCPStatsAuditEndpointResponseIns, 
                  bwMGCPStatsCreateConnectionResponseIns, 
                  bwMGCPStatsDeleteAgentConnectionResponseIns, 
                  bwMGCPStatsDeleteConnectionResponseIns, 
                  bwMGCPStatsDeleteGatewayConnectionResponseOuts, 
                  bwMGCPStatsEndpointConfigurationResponseIns, 
                  bwMGCPStatsExtraCommandResponseIns, 
                  bwMGCPStatsModifyConnectionResponseIns, 
                  bwMGCPStatsNotificationRequestResponseIns, 
                  bwMGCPStatsNotifyResponseOuts, 
                  bwMGCPStatsRestartInProgressResponseOuts, 
                  bwMGCPStatsDialToneDelay, bwMGCPStatsMinDialToneDelay, 
                  bwMGCPStatsMaxDialToneDelay, 
                  bwMGCPStatsSetupSignalDelay, 
                  bwMGCPStatsMinSetupSignalDelay, 
                  bwMGCPStatsMaxSetupSignalDelay, 
                  bwMGCPStatsAnswerSignalDelay, 
                  bwMGCPStatsMinAnswerSignalDelay, 
                  bwMGCPStatsMaxAnswerSignalDelay, 
                  bwMGCPStatsMessageRetryPercentage }
    STATUS      current
    DESCRIPTION 
        "This group defines the statistics for the MGCP protocol."
    ::= { bwExecutionMibGroups 1 }

  bwExecutionImsGroup OBJECT-GROUP
    OBJECTS     { bwIMSSuccessfulConnectionAttempts, 
                  bwIMSUnsuccessfulConnectionAttempts, 
                  bwIMSSuccessfulDownLoadAttempts, 
                  bwIMSUnsuccessfulDownLoadAttempts, bwIMSMaxSessions, 
                  bwIMSAvgSessions, bwIMSMaxThreads, bwIMSAvgThreads, 
                  bwIMSMaxServiceTime, bwIMSAvgServiceTime, 
                  bwIMSNumKeepAlive, bwIMSNumDroppedRequests }
    STATUS      current
    DESCRIPTION 
        "This group defines the statistics for the IMS protocol."
    ::= { bwExecutionMibGroups 2 }

  bwExecutionCapGroup OBJECT-GROUP
    OBJECTS     { bwCAPStatsRegisterRequests, bwCAPStatsUnRegistersIn, 
                  bwCAPStatsUnRegistersOut, bwCAPStatsSessionUpdatesOut, 
                  bwCAPStatsProfileUpdatesOut, bwCAPStatsCallUpdatesOut, 
                  bwCAPStatsCallActionsIn, bwCAPStatsAcknowledgementsIn, 
                  bwCAPStatsAclViolations, 
                  bwCAPStatsUnsuccessfulRegisterResponses, 
                  bwCAPStatsCallControlInfosOut, 
                  bwCAPStatsRegisterAuthentications, 
                  bwCAPStatsResponseAuthentications, 
                  bwCAPStatsInfoRequests, bwCAPStatsInfoResponses, 
                  bwCAPStatsExternalNotifies, 
                  bwCAPMonitoringUsersRequests, 
                  bwCAPMonitoringUsersResponses, 
                  bwCAPStatsQueueUpdatesOut, bwCAPStatsQueueActionsIn, 
                  bwCAPStatsDatagramsIn, bwCAPStatsDatagramsOut, 
                  bwCAPStatsTotalMsgs, bwCAPStatsRegisterResponsesType, 
                  bwCAPStatsRegisterResponses, 
                  bwCAPNumInboundDiscardedMessages, 
                  bwCAPNumOutboundDiscardedMessages, bwCAPNumConnections, 
                  bwCAPNumDisconnections, bwCAPNumCCC2Connections, 
                  bwCAPNumCCC2Disconnections, 
                  bwCAPNumCapSCallCenterConnections, 
                  bwCAPNumCapSCallCenterDisconnections }
    STATUS      current
    DESCRIPTION 
        "This group defines the statistics for the CAP protocol."
    ::= { bwExecutionMibGroups 3 }

  bwExecutionSmdiGroup OBJECT-GROUP
    OBJECTS     { bwSmdiNbOfActiveConnection, bwSmdiNbOfOpenedConnection, 
                  bwSmdiIncomingMWIActivationRequests, 
                  bwSmdiIncomingMWIDesactivationRequests, 
                  bwSmdiInvalidRequestsReceived, 
                  bwSmdiBlockResponsesSent, bwSmdiInvalidResponsesSent, 
                  bwSmdiOutgoingMWIActivationRequests, 
                  bwSmdiOutgoingMWIDeactivationRequests, 
                  bwSmdiBlockResponsesReceived, 
                  bwSmdiInvalidResponsesReceived, 
                  bwSMDIMessageDeskMessageSent }
    STATUS      current
    DESCRIPTION 
        "This group defines the statistics for the SMDI protocol."
    ::= { bwExecutionMibGroups 4 }

  bwExecutionMediaResourceGroup OBJECT-GROUP
    OBJECTS     { bwMediaCommandsTransmitted, 
                  bwMediaNotificationsReceived, 
                  bwMediaResourceAllocAttempts, 
                  bwMediaResourceAllocFailures }
    STATUS      current
    DESCRIPTION 
        "This group defines the statistics for the Media Resource protocol."
    ::= { bwExecutionMibGroups 5 }

  bwExecutionWholeSalesGroup OBJECT-GROUP
    OBJECTS     { bwWSPStatsServiceRequestsIn, 
                  bwWSPStatsServiceActionsOut, 
                  bwWSPStatsServiceUpdatesIn, 
                  bwWSPStatsServiceAcknowledgementsOut }
    STATUS      current
    DESCRIPTION 
        "This group defines the statistics for the Whole Sales protocol."
    ::= { bwExecutionMibGroups 6 }

  bwExecutionRealTimeAccntGroup OBJECT-GROUP
    OBJECTS     { bwRealtimeAccountingRequestsTransmitted, 
                  bwRealtimeAccountingRequestsRetransmitted, 
                  bwRealtimeAccountingRequestsDropped }
    STATUS      current
    DESCRIPTION 
        "This group defines the statistics for the Real Time Accounting protocol."
    ::= { bwExecutionMibGroups 7 }

  bwExecutionExtCallLogsGroup OBJECT-GROUP
    OBJECTS     { bwExternalCallLogsTransmitted, 
                  bwExternalCallLogsRetransmitted, 
                  bwExternalCallLogsDropped, bwExternalCallLogsQueued, 
                  bwExternalCallLogsTransmittedFromQueue, 
                  bwExternalCallLogsRetransmittedFromQueue }
    STATUS      current
    DESCRIPTION 
        "This group defines the statistics for the External Call Logs protocol."
    ::= { bwExecutionMibGroups 8 }

  bwExecutionXsBcctGroup OBJECT-GROUP
    OBJECTS     { bwCommonCommXSStatsIndex, bwCommonCommXSHost, 
                  bwCommonCommXSInterface, bwCommonCommXSProtocol, 
                  bwCommonCommXSAcceptedOutboundConnections, 
                  bwCommonCommXSAcceptedInboundConnections, 
                  bwCommonCommXSRejectedOutboundConnections, 
                  bwCommonCommXSRejectedInboundConnections, 
                  bwCommonCommXSOutputMessagesProcessed, 
                  bwCommonCommXSInputMessagesProcessed, 
                  bwCommonCommXSOutputCommunicationErrors, 
                  bwCommonCommXSInputCommunicationErrors }
    STATUS      current
    DESCRIPTION 
        "This group defines the statistics for the BCCT protocol for the Application Server Execution Server process."
    ::= { bwExecutionMibGroups 9 }

  bwExecutionCallpGroup OBJECT-GROUP
    OBJECTS     { bwCallpNetworkOriginationAttempts, 
                  bwCallpNetworkTerminationAttempts, 
                  bwCallpNetworkTerminationsAnswered, 
                  bwCallpUserOriginationAttempts, 
                  bwCallpUserTerminationAttempts, 
                  bwCallpUserTerminationsAnswered, 
                  bwCallpEmergencyCallAttempts, 
                  bwCallpEmergencyCallAlarms, bwCallpActiveCalls, 
                  bwCallpCallsPerSecond, 
                  bwCallpMaximumNumberofSimCallsExceeded, 
                  bwCallpMaximumCallTimeforAnsweredCallsExceeded, 
                  bwCallpMaximumCallTimeforUnansweredCallsExceeded, 
                  bwCallpActiveCallsAsPercentOfLicense, 
                  bwCallpMaximumNumberofSimVideoCallsExceeded, 
                  bwCallpMediaTypeNotSupported, 
                  bwCallpRemoteOfficeEmergencyCallsBlocked, 
                  bwStateReplicationMessageSent, bwStateReplicationMessageReceived,
                  bwStateReplicationOwnershipTaken, bwStateReplicationOwnershipGranted,
                  bwStateReplicationRemoteLockTaken, bwStateReplicationRemoteLockGranted,
                  bwCallpSystemServiceSimultaneousCallsExceeded, 
                  bwCallpSystemServiceSimultaneousVideoCallsExceeded,
                  bwCallpSystemServiceMaximumCallTimeforAnsweredCallsExceeded,
                  bwCallpSystemServiceRedirectCallsExceeded,
                  bwRedundancyMessageSent, bwRedundancyMessageReceived,
                  bwRedundancyLinkFailureCount, bwRedundancyLinkFailureCountTimeMSB, 
                  bwRedundancyLinkFailureCountTimeLSB,
                  bwCallpSPIndex, bwCallpSPID, 
                  bwCallpSPUserOriginationAttempts, 
                  bwCallpSPUserTerminationAttempts, 
                  bwCallpSPUserTerminationsAnswered, 
                  bwCallpSPEmergencyCallAttempts, 
                  bwCallpSPMaximumNumberofSimCallsExceeded, 
                  bwCallpSPMaximumCallTimeforAnsweredCallsExceeded, 
                  bwCallpSPMaximumCallTimeforUnansweredCallsExceeded, 
                  bwCallpSPMaximumNumberofSimVideoCallsExceeded, 
                  bwCallpSPMediaTypeNotSupported, bwCallpGroupIndex, 
                  bwCallpGroupID, bwCallpGroupUserOriginationAttempts, 
                  bwCallpGroupUserTerminationAttempts, 
                  bwCallpGroupUserTerminationsAnswered, 
                  bwCallpGroupEmergencyCallAttempts, 
                  bwCallpGroupMaximumNumberofSimCallsExceeded, 
                  bwCallpGroupMaximumCallTimeforAnsweredCallsExceeded, 
                  bwCallpGroupMaximumCallTimeforUnansweredCallsExceeded, 
                  bwCallpGroupMaximumNumberofSimVideoCallsExceeded, 
                  bwCallpGroupMediaTypeNotSupported }
    STATUS      current
    DESCRIPTION 
        "This group defines the statistics for call processing."
    ::= { bwExecutionMibGroups 10 }

  bwExecutionSmtpGroup OBJECT-GROUP
    OBJECTS     { bwSMTPTotalPrimaryEmailSendAttempts, 
                  bwSMTPTotalSecondaryEmailSendAttempts, 
                  bwSMTPPrimaryUnSuccessfulEmailSendAttempts, 
                  bwSMTPSecondaryUnSuccessfulEmailSendAttempts }
    STATUS      current
    DESCRIPTION 
        "This group defines the statistics for the SMTP protocol."
    ::= { bwExecutionMibGroups 11 }

  bwExecutionSipGroup OBJECT-GROUP
    OBJECTS     { bwSipSummaryTotalTransactions, bwSipStatsInviteIns, 
                  bwSipStatsInviteOuts, bwSipStatsAckIns, 
                  bwSipStatsAckOuts, bwSipStatsByeIns, bwSipStatsByeOuts, 
                  bwSipStatsCancelIns, bwSipStatsCancelOuts, 
                  bwSipStatsOptionsIns, bwSipStatsOptionsOuts, 
                  bwSipStatsRegisterIns, bwSipStatsRegisterOuts, 
                  bwSipStatsInfoIns, bwSipStatsInfoOuts, 
                  bwSipStatsNotifyIns, bwSipStatsNotifyOuts, 
                  bwSipStatsPrackIns, bwSipStatsPrackOuts, 
                  bwSipStatsOtherIns, bwSipStatsOtherOuts, 
                  bwSipStatsInviteResponseIns, 
                  bwSipStatsInviteResponseOuts, bwSipStatsByeResponseIns, 
                  bwSipStatsByeResponseOuts, bwSipStatsCancelResponseIns, 
                  bwSipStatsCancelResponseOuts, 
                  bwSipStatsOptionsResponseIns, 
                  bwSipStatsOptionsResponseOuts, 
                  bwSipStatsRegisterResponseIns, 
                  bwSipStatsRegisterResponseOuts, 
                  bwSipStatsPrackResponseIns, 
                  bwSipStatsPrackResponseOuts, bwSipStatsInfoResponseIns, 
                  bwSipStatsInfoResponseOuts, 
                  bwSipStatsNotifyResponseIns, 
                  bwSipStatsNotifyResponseOuts, 
                  bwSipStatsOtherResponseIns, 
                  bwSipStatsOtherResponseOuts, bwSipStatsRetryInvites, 
                  bwSipStatsRetryByes, bwSipStatsRetryCancels, 
                  bwSipStatsRetryResponses, bwSipStatsSubscribeIns, 
                  bwSipStatsSubscribeOuts, bwSipStatsMessageIns, 
                  bwSipStatsMessageOuts, bwSipStatsSubscribeResponseIns, 
                  bwSipStatsSubscribeResponseOuts, 
                  bwSipStatsMessageResponseIns, 
                  bwSipStatsMessageResponseOuts, bwSipStatsUpdateIns, 
                  bwSipStatsUpdateOuts, bwSipStatsUpdateResponseIns, 
                  bwSipStatsUpdateResponseOuts, 
                  bwSipStatsSetupSignalDelay, 
                  bwSipStatsMinSetupSignalDelay, 
                  bwSipStatsMaxSetupSignalDelay, 
                  bwSipStatsAnswerSignalDelay, 
                  bwSipStatsMinAnswerSignalDelay, 
                  bwSipStatsMaxAnswerSignalDelay, 
                  bwSipStatsRegistrationsPerMinute, 
                  bwSipStatsMsgRetryPercentageToOther, 
                  bwSipStatsMsgRetryToNeID, bwSipStatsMsgRetryToNeAddr, 
                  bwSipStatsMsgRetryToNePercentage, 
                  bwSipStatsActiveTcpConnections, bwSipStatsTcpIns, 
                  bwSipStatsTcpOuts, bwSipStatsTcpFailures, 
                  bwSipStatsUdpIns, bwSipStatsUdpOuts, 
                  bwSIPReclaimedStaleTcpConnections,
                  bwSipPeerConnectionFailureCount, bwSipPeerConnectionMessageReceived,
                  bwSipPeerConnectionMessageSent, bwSipPeerConnectionFailureCountTimeMSB,
                  bwSipPeerConnectionFailureCountTimeLSB }
    STATUS      current
    DESCRIPTION 
        "This group defines the statistics for the SIP protocol."
    ::= { bwExecutionMibGroups 12 }

  bwExecutionAccntCodeServiceGroup OBJECT-GROUP
    OBJECTS     { bwAuthCodeNumAttempts, bwAuthCodeNumValidations, 
                  bwAccountCodeNumAttempts, 
                  bwAccountCodeNumPerCallAttempts, bwAccountCodesSPIndex, 
                  bwAccountCodesSPID, bwAuthCodeSPNumAttempts, 
                  bwAuthCodeSPNumValidations, bwAccountCodeSPNumAttempts, 
                  bwAccountCodeSPNumPerCallAttempts, 
                  bwAccountCodesGroupIndex, bwAccountCodesGroupID, 
                  bwAuthCodeGroupNumAttempts, 
                  bwAuthCodeGroupNumValidations, 
                  bwAccountCodeGroupNumAttempts, 
                  bwAccountCodeGroupNumPerCallAttempts }
    STATUS      current
    DESCRIPTION 
        "This group defines the statistics for the Account Code Service."
    ::= { bwExecutionMibGroups 13 }

  bwExecutionAnonymousCallRejectionServiceGroup OBJECT-GROUP
    OBJECTS     { bwAnonymousCallsNumRejected, 
                  bwAnonymousCallRejectionSPIndex, 
                  bwAnonymousCallRejectionSPID, 
                  bwAnonymousCallsSPNumRejected, 
                  bwAnonymousCallRejectionGroupIndex, 
                  bwAnonymousCallRejectionGroupID, 
                  bwAnonymousCallsGroupNumRejected }
    STATUS      current
    DESCRIPTION 
        "This group defines the statistics for the Anonymous Call Rejection Service."
    ::= { bwExecutionMibGroups 14 }

  bwExecutionAuthenticationServiceGroup OBJECT-GROUP
    OBJECTS     { bwAuthenticationNumChallenges, 
                  bwAuthenticationNumValidResponses, 
                  bwAuthenticationSPIndex, bwAuthenticationSPID, 
                  bwAuthenticationSPNumChallenges, 
                  bwAuthenticationSPNumValidResponses, 
                  bwAuthenticationGroupIndex, bwAuthenticationGroupID, 
                  bwAuthenticationGroupNumChallenges, 
                  bwAuthenticationGroupNumValidResponses }
    STATUS      current
    DESCRIPTION 
        "This group defines the statistics for the Authentication Service."
    ::= { bwExecutionMibGroups 15 }

  bwExecutionAutoAttendantServiceGroup OBJECT-GROUP
    OBJECTS     { bwAutoAttendantNumAnswers, bwAutoAttendantNumTransfers, 
                  bwAutoAttendantSPIndex, bwAutoAttendantSPID, 
                  bwAutoAttendantSPNumAnswers, 
                  bwAutoAttendantSPNumTransfers, 
                  bwAutoAttendantGroupIndex, bwAutoAttendantGroupID, 
                  bwAutoAttendantGroupNumAnswers, 
                  bwAutoAttendantGroupNumTransfers }
    STATUS      current
    DESCRIPTION 
        "This group defines the statistics for the Auto Attendant Service."
    ::= { bwExecutionMibGroups 16 }

  bwExecutionCallCapacityServiceGroup OBJECT-GROUP
    OBJECTS     { bwCallCapacityNumCallsAttempted, 
                  bwCallCapacityNumCallsBlocked, bwCallCapacitySPIndex, 
                  bwCallCapacitySPID, bwCallCapacitySPNumCallsAttempted, 
                  bwCallCapacitySPNumCallsBlocked, 
                  bwCallCapacityGroupIndex, bwCallCapacityGroupID, 
                  bwCallCapacityGroupNumCallsAttempted, 
                  bwCallCapacityGroupNumCallsBlocked }
    STATUS      current
    DESCRIPTION 
        "This group defines the statistics for the Call Capacity Service."
    ::= { bwExecutionMibGroups 17 }

  bwExecutionCFAlwaysServiceGroup OBJECT-GROUP
    OBJECTS     { bwCFANumForwarded, bwCFANumPhoneActivations, 
                  bwCFANumPhoneDeactivations, bwCFADestinationChanged, 
                  bwCFANumPhoneInterrogation, 
                  bwCallForwardingAlwaysSPIndex, 
                  bwCallForwardingAlwaysSPID, bwCFASPNumForwarded, 
                  bwCFASPNumPhoneActivations, 
                  bwCFASPNumPhoneDeactivations, 
                  bwCFASPDestinationChanged, 
                  bwCFASPNumPhoneInterrogation, 
                  bwCallForwardingAlwaysGroupIndex, 
                  bwCallForwardingAlwaysGroupID, bwCFAGroupNumForwarded, 
                  bwCFAGroupNumPhoneActivations, 
                  bwCFAGroupNumPhoneDeactivations, 
                  bwCFAGroupDestinationChanged, 
                  bwCFAGroupNumPhoneInterrogation }
    STATUS      current
    DESCRIPTION 
        "This group defines the statistics for the Call Forward Always Service."
    ::= { bwExecutionMibGroups 18 }

  bwExecutionCFBusyServiceGroup OBJECT-GROUP
    OBJECTS     { bwCFBNumForwarded, bwCFBNumPhoneActivations, 
                  bwCFBNumPhoneDeactivations, bwCFBDestinationChanged, 
                  bwCFBNumPhoneInterrogation, 
                  bwCallForwardingBusySPIndex, bwCallForwardingBusySPID, 
                  bwCFBSPNumForwarded, bwCFBSPNumPhoneActivations, 
                  bwCFBSPNumPhoneDeactivations, 
                  bwCFBSPDestinationChanged, 
                  bwCFBSPNumPhoneInterrogation, 
                  bwCallForwardingBusyGroupIndex, 
                  bwCallForwardingBusyGroupID, bwCFBGroupNumForwarded, 
                  bwCFBGroupNumPhoneActivations, 
                  bwCFBGroupNumPhoneDeactivations, 
                  bwCFBGroupDestinationChanged, 
                  bwCFBGroupNumPhoneInterrogation }
    STATUS      current
    DESCRIPTION 
        "This group defines the statistics for the Call Forward Busy Service."
    ::= { bwExecutionMibGroups 19 }

  bwExecutionCFNoAnswerServiceGroup OBJECT-GROUP
    OBJECTS     { bwCFNANumForwarded, bwCFNADestinationChanged, 
                  bwCFNANumPhoneActivations, bwCFNANumPhoneDeactivations, 
                  bwCFNANumPhoneInterrogation, 
                  bwCallForwardingNoAnswerSPIndex, 
                  bwCallForwardingNoAnswerSPID, bwCFNASPNumForwarded, 
                  bwCFNASPDestinationChanged, 
                  bwCFNASPNumPhoneActivations, 
                  bwCFNASPNumPhoneDeactivations, 
                  bwCFNASPNumPhoneInterrogation, 
                  bwCallForwardingNoAnswerGroupIndex, 
                  bwCallForwardingNoAnswerGroupID, 
                  bwCFNAGroupNumForwarded, bwCFNAGroupDestinationChanged, 
                  bwCFNAGroupNumPhoneActivations, 
                  bwCFNAGroupNumPhoneDeactivations, 
                  bwCFNAGroupNumPhoneInterrogation }
    STATUS      current
    DESCRIPTION 
        "This group defines the statistics for the Call Forward No-Answer Service."
    ::= { bwExecutionMibGroups 20 }

  bwExecutionCallNotifyServiceGroup OBJECT-GROUP
    OBJECTS     { bwCallNotifyNumNotifications, bwCallNotifySPIndex, 
                  bwCallNotifySPID, bwCallNotifySPNumNotifications, 
                  bwCallNotifyGroupIndex, bwCallNotifyGroupID, 
                  bwCallNotifyGroupNumNotifications }
    STATUS      current
    DESCRIPTION 
        "This group defines the statistics for the Call Notify Service."
    ::= { bwExecutionMibGroups 21 }

  bwExecutionCallParkServiceGroup OBJECT-GROUP
    OBJECTS     { bwCallParkNumAttempts, bwCallParkNumFailures, 
                  bwCallParkNumRetrieveAttempts, 
                  bwCallParkNumRetrieveFailures, bwCallParkSPIndex, 
                  bwCallParkSPID, bwCallParkSPNumAttempts, 
                  bwCallParkSPNumFailures, 
                  bwCallParkSPNumRetrieveAttempts, 
                  bwCallParkSPNumRetrieveFailures, bwCallParkGroupIndex, 
                  bwCallParkGroupID, bwCallParkGroupNumAttempts, 
                  bwCallParkGroupNumFailures, 
                  bwCallParkGroupNumRetrieveAttempts, 
                  bwCallParkGroupNumRetrieveFailures }
    STATUS      current
    DESCRIPTION 
        "This group defines the statistics for the Call Park Service."
    ::= { bwExecutionMibGroups 22 }

  bwExecutionCallPickupServiceGroup OBJECT-GROUP
    OBJECTS     { bwCallPickupNumAttempts, bwCallPickupNumFailures, 
                  bwCallPickupSPIndex, bwCallPickupSPID, 
                  bwCallPickupSPNumAttempts, bwCallPickupSPNumFailures, 
                  bwCallPickupGroupIndex, bwCallPickupGroupID, 
                  bwCallPickupGroupNumAttempts, 
                  bwCallPickupGroupNumFailures }
    STATUS      current
    DESCRIPTION 
        "This group defines the statistics for the Call Pickup Service."
    ::= { bwExecutionMibGroups 23 }

  bwExecutionCallReturnServiceGroup OBJECT-GROUP
    OBJECTS     { bwCallReturnNumReturns, bwCallReturnSPIndex, 
                  bwCallReturnSPID, bwCallReturnSPNumReturns, 
                  bwCallReturnGroupIndex, bwCallReturnGroupID, 
                  bwCallReturnGroupNumReturns }
    STATUS      current
    DESCRIPTION 
        "This group defines the statistics for the Call Return Service."
    ::= { bwExecutionMibGroups 24 }

  bwExecutionCompilotCallMgrServiceGroup OBJECT-GROUP
    OBJECTS     { bwCommPilotCallMgrNumDial, bwCommPilotCallMgrNumAnswer, 
                  bwCommPilotCallMgrNumRelease, 
                  bwCommPilotCallMgrNumHold, 
                  bwCommPilotCallMgrNumTransfer, 
                  bwCommPilotCallMgrNumConference, 
                  bwCommPilotCallMgrNumTransferVM, 
                  bwCommPilotCallMgrNumConferenceAnswer, 
                  bwCommPilotCallMgrNumConferenceHold, 
                  bwCommPilotCallMgrNumConferenceRelease, 
                  bwCommPilotCallMgrNumTransferCC, 
                  bwCommPilotCallMgrNumConferenceAdd, 
                  bwCommPilotCallManagerSPIndex, 
                  bwCommPilotCallManagerSPID, 
                  bwCommPilotCallMgrSPNumDial, 
                  bwCommPilotCallMgrSPNumAnswer, 
                  bwCommPilotCallMgrSPNumRelease, 
                  bwCommPilotCallMgrSPNumHold, 
                  bwCommPilotCallMgrSPNumTransfer, 
                  bwCommPilotCallMgrSPNumConference, 
                  bwCommPilotCallMgrSPNumTransferVM, 
                  bwCommPilotCallMgrSPNumConferenceAnswer, 
                  bwCommPilotCallMgrSPNumConferenceHold, 
                  bwCommPilotCallMgrSPNumConferenceRelease, 
                  bwCommPilotCallMgrSPNumTransferCC, 
                  bwCommPilotCallMgrSPNumConferenceAdd, 
                  bwCommPilotCallManagerGroupIndex, 
                  bwCommPilotCallManagerGroupID, 
                  bwCommPilotCallMgrGroupNumDial, 
                  bwCommPilotCallMgrGroupNumAnswer, 
                  bwCommPilotCallMgrGroupNumRelease, 
                  bwCommPilotCallMgrGroupNumHold, 
                  bwCommPilotCallMgrGroupNumTransfer, 
                  bwCommPilotCallMgrGroupNumConference, 
                  bwCommPilotCallMgrGroupNumTransferVM, 
                  bwCommPilotCallMgrGroupNumConferenceAnswer, 
                  bwCommPilotCallMgrGroupNumConferenceHold, 
                  bwCommPilotCallMgrGroupNumConferenceRelease, 
                  bwCommPilotCallMgrGroupNumTransferCC, 
                  bwCommPilotCallMgrGroupNumConferenceAdd, 
                  bwCommPilotCallMgrNumCallPark, 
                  bwCommPilotCallMgrNumGroupCallPark, 
                  bwCommPilotCallMgrNumCallParkRetrieve, 
                  bwCommPilotCallMgrSPNumCallPark, 
                  bwCommPilotCallMgrSPNumGroupCallPark, 
                  bwCommPilotCallMgrSPNumCallParkRetrieve, 
                  bwCommPilotCallMgrGroupNumCallPark, 
                  bwCommPilotCallMgrGroupNumGroupCallPark, 
                  bwCommPilotCallMgrGroupNumCallParkRetrieve }
    STATUS      current
    DESCRIPTION 
        "This group defines the statistics for the CommPilot Call Manager Service."
    ::= { bwExecutionMibGroups 25 }

  bwExecutionDoNotDisturbServiceGroup OBJECT-GROUP
    OBJECTS     { bwDoNotDisturbNumInvoked, bwDndPhoneActivations, 
                  bwDndPhoneDeactivations, bwDoNotDisturbSPIndex, 
                  bwDoNotDisturbSPID, bwDoNotDisturbSPNumInvoked, 
                  bwDNDSPNumPhoneActivations, 
                  bwDNDSPNumPhoneDeactivations, bwDoNotDisturbGroupIndex, 
                  bwDoNotDisturbGroupID, bwDoNotDisturbGroupNumInvoked, 
                  bwDNDGroupNumPhoneActivations, 
                  bwDNDGroupNumPhoneDeactivations }
    STATUS      current
    DESCRIPTION 
        "This group defines the statistics for the Do Not Disturb Service."
    ::= { bwExecutionMibGroups 26 }

  bwExecutionFlashCallXferServiceGroup OBJECT-GROUP
    OBJECTS     { bwFlashCallTransferNumTransfers, 
                  bwFlashCallTransferSPIndex, bwFlashCallTransferSPID, 
                  bwFlashCallTransferSPNumTransfers, 
                  bwFlashCallTransferGroupIndex, 
                  bwFlashCallTransferGroupID, 
                  bwFlashCallTransferGroupNumTransfers }
    STATUS      current
    DESCRIPTION 
        "This group defines the statistics for Flash Call Xfer Service."
    ::= { bwExecutionMibGroups 27 }

  bwExecutionFlashCallWaitingServiceGroup OBJECT-GROUP
    OBJECTS     { bwFlashCallWaitingNumAnswers, 
                  bwFlashCallWaitingSPIndex, bwFlashCallWaitingSPID, 
                  bwFlashCallWaitingSPNumAnswers, 
                  bwFlashCallWaitingGroupIndex, 
                  bwFlashCallWaitingGroupID, 
                  bwFlashCallWaitingGroupNumAnswers }
    STATUS      current
    DESCRIPTION 
        "This group defines the statistics for Flash Call Waiting Service."
    ::= { bwExecutionMibGroups 28 }

  bwExecutionFlashConsultationServiceGroup OBJECT-GROUP
    OBJECTS     { bwFlashConsultationNumCalls, 
                  bwFlashConsultationSPIndex, bwFlashConsultationSPID, 
                  bwFlashConsultationSPNumCalls, 
                  bwFlashConsultationGroupIndex, 
                  bwFlashConsultationGroupID, 
                  bwFlashConsultationGroupNumCalls }
    STATUS      current
    DESCRIPTION 
        "This group defines the statistics for Flash Consultation Service."
    ::= { bwExecutionMibGroups 29 }

  bwExecutionFlash3wcServiceGroup OBJECT-GROUP
    OBJECTS     { bwFlashThreeWayCallNum3WC, bwFlashThreeWayCallSPIndex, 
                  bwFlashThreeWayCallSPID, bwFlashThreeWayCallSPNum3WC, 
                  bwFlashThreeWayCallGroupIndex, 
                  bwFlashThreeWayCallGroupID, 
                  bwFlashThreeWayCallGroupNum3WC }
    STATUS      current
    DESCRIPTION 
        "This group defines the statistics for Flash Three Way Calling Service."
    ::= { bwExecutionMibGroups 30 }

  bwExecutionHuntGroupServiceGroup OBJECT-GROUP
    OBJECTS     { bwHuntGroupNumAttempts, bwHuntGroupNumBusy, 
                  bwHuntGroupsSPIndex, bwHuntGroupsSPID, 
                  bwHuntGroupSPNumAttempts, bwHuntGroupSPNumBusy,
                  bwHuntGroupsGroupIndex, bwHuntGroupsGroupID, 
                  bwHuntGroupsGroupNumAttempts, bwHuntGroupsGroupNumBusy }
    STATUS      current
    DESCRIPTION 
        "This group defines the statistics for the Hunt Group Service."
    ::= { bwExecutionMibGroups 31 }

  bwExecutionIcpServiceGroup OBJECT-GROUP
    OBJECTS     { bwICPNumInterGroupBlocks, bwICPNumCollectCallBlocks, 
                  bwICPNumIntraGroupBlocks, bwICPNumOutsideCallerBlocks, 
                  bwIncomingCallingPlanSPIndex, 
                  bwIncomingCallingPlanSPID, bwICPSPNumInterGroupBlocks, 
                  bwICPSPNumCollectCallBlocks, 
                  bwICPSPNumIntraGroupBlocks, 
                  bwICPSPNumOutsideCallerBlocks, 
                  bwIncomingCallingPlanGroupIndex, 
                  bwIncomingCallingPlanGroupID, 
                  bwICPGroupNumInterGroupBlocks, 
                  bwICPGroupNumCollectCallBlocks, 
                  bwICPGroupNumIntraGroupBlocks, 
                  bwICPGroupNumOutsideCallerBlocks }
    STATUS      current
    DESCRIPTION 
        "This group defines the statistics for the Incoming Calling Plan Service."
    ::= { bwExecutionMibGroups 32 }

  bwExecutionIpPhoneServiceGroup OBJECT-GROUP
    OBJECTS     { bwIPPhoneNumForwards, bwIPPhoneSPIndex, bwIPPhoneSPID, 
                  bwIPPhoneSPNumForwards, bwIPPhoneGroupIndex, 
                  bwIPPhoneGroupID, bwIPPhoneGroupNumForwards }
    STATUS      current
    DESCRIPTION 
        "This group defines the statistics for the IP Phone Service."
    ::= { bwExecutionMibGroups 33 }

  bwExecutionLastNumberRedialServiceGroup OBJECT-GROUP
    OBJECTS     { bwLNRNumRedials, bwLastNumberRedialSPIndex, 
                  bwLastNumberRedialSPID, bwLNRSPNumRedials, 
                  bwLastNumberRedialGroupIndex, 
                  bwLastNumberRedialGroupID, bwLNRGroupNumRedials }
    STATUS      current
    DESCRIPTION 
        "This group defines the statistics for the Last Number Redial Service."
    ::= { bwExecutionMibGroups 34 }

  bwExecutionOcpServiceGroup OBJECT-GROUP
    OBJECTS     { bwOCPNumGroupCallsBlocked, bwOCPNumLocalCallsBlocked, 
                  bwOCPNumTollFreeCallsBlocked, bwOCPNumTollCallsBlocked, 
                  bwOCPNumIntlCallsBlocked, 
                  bwOCPNumOperatorAssistedCallsBlocked, 
                  bwOCPNumChargeableDirAssistCallsBlocked, 
                  bwOCPNumSpecialServices1CallsBlocked, 
                  bwOCPNumSpecialServices2CallsBlocked, 
                  bwOCPNumPremiumServices1CallsBlocked, 
                  bwOCPNumPremiumServices2CallsBlocked, 
                  bwOCPNumCasualCallsBlocked, 
                  bwOCPNumURLDialingCallsBlocked, 
                  bwOCPNumUnknownCallsBlocked, 
                  bwOCPNumSuccessfulAuthorizations, 
                  bwOCPNumUnsuccessfulAuthorizations, bwOCPNumTransfers, 
                  bwOCPSACNumSuccessfulLock, bwOCPSACNumSuccessfulUnlock, 
                  bwOCPSACNumUnsuccessfulLock, 
                  bwOCPSACNumUnsuccessfulUnlock, 
                  bwOCPSACNumUnsuccessfulCodeUsage, 
                  bwOCPNumOutsideGroupTransferBlocks, 
                  bwOutgoingCallingPlanSPIndex, 
                  bwOutgoingCallingPlanSPID, bwOCPSPNumGroupCallsBlocked, 
                  bwOCPSPNumLocalCallsBlocked, 
                  bwOCPSPNumTollFreeCallsBlocked, 
                  bwOCPSPNumTollCallsBlocked, bwOCPSPNumIntlCallsBlocked, 
                  bwOCPSPNumOperatorAssistedCallsBlocked, 
                  bwOCPSPNumChargeableDirAssistCallsBlocked, 
                  bwOCPSPNumSpecialServices1CallsBlocked, 
                  bwOCPSPNumSpecialServices2CallsBlocked, 
                  bwOCPSPNumPremiumServices1CallsBlocked, 
                  bwOCPSPNumPremiumServices2CallsBlocked, 
                  bwOCPSPNumCasualCallsBlocked, 
                  bwOCPSPNumURLDialingCallsBlocked, 
                  bwOCPSPNumUnknownCallsBlocked, 
                  bwOCPSPNumSuccessfulAuthorizations, 
                  bwOCPSPNumUnsuccessfulAuthorizations, 
                  bwOCPSPNumTransfers, bwOCPSACSPNumSuccessfulLock, 
                  bwOCPSACSPNumSuccessfulUnlock, 
                  bwOCPSACSPNumUnsuccessfulLock, 
                  bwOCPSACSPNumUnsuccessfulUnlock, 
                  bwOCPSACSPNumUnsuccessfulCodeUsage, 
                  bwOCPSPNumOutsideGroupTransferBlocks, 
                  bwOutgoingCallingPlanGroupIndex, 
                  bwOutgoingCallingPlanGroupID, 
                  bwOCPGroupNumGroupCallsBlocked, 
                  bwOCPGroupNumLocalCallsBlocked, 
                  bwOCPGroupNumTollFreeCallsBlocked, 
                  bwOCPGroupNumTollCallsBlocked, 
                  bwOCPGroupNumIntlCallsBlocked, 
                  bwOCPGroupNumOperatorAssistedCallsBlocked, 
                  bwOCPGroupNumChargeableDirAssistCallsBlocked, 
                  bwOCPGroupNumSpecialServices1CallsBlocked, 
                  bwOCPGroupNumSpecialServices2CallsBlocked, 
                  bwOCPGroupNumPremiumServices1CallsBlocked, 
                  bwOCPGroupNumPremiumServices2CallsBlocked, 
                  bwOCPGroupNumCasualCallsBlocked, 
                  bwOCPGroupNumURLDialingCallsBlocked, 
                  bwOCPGroupNumUnknownCallsBlocked, 
                  bwOCPGroupNumSuccessfulAuthorizations, 
                  bwOCPGroupNumUnsuccessfulAuthorizations, 
                  bwOCPGroupNumTransfers, bwOCPSACGroupNumSuccessfulLock, 
                  bwOCPSACGroupNumSuccessfulUnlock, 
                  bwOCPSACGroupNumUnsuccessfulLock, 
                  bwOCPSACGroupNumUnsuccessfulUnlock, 
                  bwOCPSACGroupNumUnsuccessfulCodeUsage, 
                  bwOCPGroupNumOutsideGroupTransferBlocks }
    STATUS      current
    DESCRIPTION 
        "This group defines the statistics for the Outgoing Calling Plan Service."
    ::= { bwExecutionMibGroups 35 }

  bwExecutionPriorityAlertServiceGroup OBJECT-GROUP
    OBJECTS     { bwPriorityAlertNumDistinctive, bwPriorityAlertSPIndex, 
                  bwPriorityAlertSPID, bwPriorityAlertSPNumDistinctive, 
                  bwPriorityAlertGroupIndex, bwPriorityAlertGroupID, 
                  bwPriorityAlertGroupNumDistinctive }
    STATUS      current
    DESCRIPTION 
        "This group defines the statistics for the Priority Alert Service."
    ::= { bwExecutionMibGroups 36 }

  bwExecutionSelectiveCallAcceptanceServiceGroup OBJECT-GROUP
    OBJECTS     { bwSCANumAcceptances, bwSelectiveCallAcceptanceSPIndex, 
                  bwSelectiveCallAcceptanceSPID, bwSCASPNumAcceptances, 
                  bwSelectiveCallAcceptanceGroupIndex, 
                  bwSelectiveCallAcceptanceGroupID, 
                  bwSCAGroupNumAcceptances }
    STATUS      current
    DESCRIPTION 
        "This group defines the statistics for the Selective Call Acceptance Service."
    ::= { bwExecutionMibGroups 37 }

  bwExecutionSelectiveCallForwardServiceGroup OBJECT-GROUP
    OBJECTS     { bwSCFNumForwards, bwSCFNumPhoneActivations, 
                  bwSCFNumPhoneDeactivations, 
                  bwSelectiveCallForwardSPIndex, 
                  bwSelectiveCallForwardSPID, bwSCFSPNumForwards, 
                  bwSCFSPNumPhoneActivations, 
                  bwSCFSPNumPhoneDeactivations, 
                  bwSelectiveCallForwardGroupIndex, 
                  bwSelectiveCallForwardGroupID, bwSCFGroupNumForwards, 
                  bwSCFGroupNumPhoneActivations, 
                  bwSCFGroupNumPhoneDeactivations }
    STATUS      current
    DESCRIPTION 
        "This group defines the statistics for the Selective Call Forward Service."
    ::= { bwExecutionMibGroups 38 }

  bwExecutionSelectiveCallRejectionServiceGroup OBJECT-GROUP
    OBJECTS     { bwSCRNumRejects, bwSelectiveCallRejectionSPIndex, 
                  bwSelectiveCallRejectionSPID, bwSCRSPNumRejects, 
                  bwSelectiveCallRejectionGroupIndex, 
                  bwSelectiveCallRejectionGroupID, bwSCRGroupNumRejects }
    STATUS      current
    DESCRIPTION 
        "This group defines the statistics for the Selective Call Rejection Service."
    ::= { bwExecutionMibGroups 39 }

  bwExecutionSimRingServiceGroup OBJECT-GROUP
    OBJECTS     { bwSimRingPersonalNumAttempts, bwSimRingPersonalNumBusy, 
                  bwSimRingPersonalSPIndex, bwSimRingPersonalSPID, 
                  bwSimRingPersonalSPNumAttempts, 
                  bwSimRingPersonalSPNumBusy, 
                  bwSimRingPersonalGroupIndex, bwSimRingPersonalGroupID, 
                  bwSimRingPersonalGroupNumAttempts, 
                  bwSimRingPersonalGroupNumBusy }
    STATUS      current
    DESCRIPTION 
        "This group defines the statistics for the Simultaneous Ringing Service."
    ::= { bwExecutionMibGroups 40 }

  bwExecutionVoiceMessagingServiceGroup OBJECT-GROUP
    OBJECTS     { bwVMNumBusyGreetingsPlayed, 
                  bwVMNumNoAnswerGreetingsPlayed, bwVMNumMessagesLeft, 
                  bwVMRNumBusyGreetingsRecorded, 
                  bwVMRNumNoAnswerGreetingsRecorded, 
                  bwVMRNumPersonalizedNamesRecorded, 
                  bwVMRNumLoginAttempts, bwVMRNumLoginFailures, 
                  bwVMRNumComposeSendAttempts, 
                  bwVMRNumComposeSendGroupAttempts, 
                  bwVMRNumForwardSendAttempts, 
                  bwVMRNumForwardSendGroupAttempts, 
                  bwVMRNumReplySendAttempts, bwVMRNumSendFailed, 
                  bwVMRNumSendGroupFailed, bwVMRDeleteAllMsgsAttempts, 
                  bwVMRCallBackAttempts, 
                  bwVPNumAABusHoursGreetingRecorded, 
                  bwVPNumAAAfterHoursGreetingRecorded, 
                  bwVPNumCFADestinationChanged, bwVPNumPasscodeChanged, 
                  bwVMRNumComposeSendListAttempts, 
                  bwVMRNumForwardSendListAttempts, 
                  bwVMRNumSendListFailed, bwVPGreetingRecorded, 
                  bwVMGreetingRecorded, bwVPCCall, 
                  bwMultiMediaMsgDeposit, bwVMMultiMediaGreetingRecorded, 
                  bwAutoAttendantMultiMediaPromptRecorded, 
                  bwVoiceMessagingSPIndex, bwVoiceMessagingSPID, 
                  bwVMSPNumBusyGreetingsPlayed, 
                  bwVMSPNumNoAnswerGreetingsPlayed, 
                  bwVMSPNumMessagesLeft, bwVMRSPNumBusyGreetingsRecorded, 
                  bwVMRSPNumNoAnswerGreetingsRecorded, 
                  bwVMRSPNumPersonalizedNamesRecorded, 
                  bwVMRSPNumLoginAttempts, bwVMRSPNumLoginFailures, 
                  bwVMRSPNumComposeSendAttempts, 
                  bwVMRSPNumComposeSendGroupAttempts, 
                  bwVMRSPNumForwardSendAttempts, 
                  bwVMRSPNumForwardSendGroupAttempts, 
                  bwVMRSPNumReplySendAttempts, bwVMRSPNumSendFailed, 
                  bwVMRSPNumSendGroupFailed, 
                  bwVMRSPDeleteAllMsgsAttempts, bwVMRSPCallBackAttempts, 
                  bwVPSPNumAABusHoursGreetingRecorded, 
                  bwVPSPNumAAAfterHoursGreetingRecorded, 
                  bwVPSPNumCFADestinationChanged, 
                  bwVPSPNumPasscodeChanged, 
                  bwVMRSPNumComposeSendListAttempts, 
                  bwVMRSPNumForwardSendListAttempts, 
                  bwVMRSPNumSendListFailed, bwVPSPGreetingRecorded, 
                  bwVMSPGreetingRecorded, bwVPCSPCall, 
                  bwSPMultiMediaMsgDeposit, 
                  bwVMSPMultiMediaGreetingRecorded, 
                  bwAutoAttendantSPMultiMediaPromptRecorded, 
                  bwVoiceMessagingGroupIndex, bwVoiceMessagingGroupID, 
                  bwVMGroupNumBusyGreetingsPlayed, 
                  bwVMGroupNumNoAnswerGreetingsPlayed, 
                  bwVMGroupNumMessagesLeft, 
                  bwVMRGroupNumBusyGreetingsRecorded, 
                  bwVMRGroupNumNoAnswerGreetingsRecorded, 
                  bwVMRGroupNumPersonalizedNamesRecorded, 
                  bwVMRGroupNumLoginAttempts, bwVMRGroupNumLoginFailures, 
                  bwVMRGroupNumComposeSendAttempts, 
                  bwVMRGroupNumComposeSendGroupAttempts, 
                  bwVMRGroupNumForwardSendAttempts, 
                  bwVMRGroupNumForwardSendGroupAttempts, 
                  bwVMRGroupNumReplySendAttempts, 
                  bwVMRGroupNumSendFailed, bwVMRGroupNumSendGroupFailed, 
                  bwVMRGroupDeleteAllMsgsAttempts, 
                  bwVMRGroupCallBackAttempts, 
                  bwVPGroupNumAABusHoursGreetingRecorded, 
                  bwVPGroupNumAAAfterHoursGreetingRecorded, 
                  bwVPGroupNumCFADestinationChanged, 
                  bwVPGroupNumPasscodeChanged, 
                  bwVMRGroupNumComposeSendListAttempts, 
                  bwVMRGroupNumForwardSendListAttempts, 
                  bwVMRGroupNumSendListFailed, bwVPGroupGreetingRecorded, 
                  bwVMGroupGreetingRecorded, bwVPCGroupCall, 
                  bwGroupMultiMediaMsgDeposit, 
                  bwVMGroupMultiMediaGreetingRecorded, 
                  bwAutoAttendantGroupMultiMediaPromptRecorded, 
                  bwMessagingQuery, bwMessagingQueryNoUser, 
                  bwMessagingQueryNoMailbox, bwMessagingSPQuery, 
                  bwMessagingSPQueryNoUser, bwMessagingSPQueryNoMailbox, 
                  bwMessagingGroupQuery, bwMessagingGroupQueryNoUser, 
                  bwMessagingGroupQueryNoMailbox, bwVPNumAAHolidayGreetingRecorded, 
                  bwSVPNumLoginAttempts, bwSVPNumLoginFailures,
                  bwVPSPNumAAHolidayGreetingRecorded, bwVPGroupNumAAHolidayGreetingRecorded,
                  bwVMmp3recordFail, bwVMmp3playbackFail }
    STATUS      current
    DESCRIPTION 
        "This group defines the statistics for the Voice Messaging Service."
    ::= { bwExecutionMibGroups 41 }

  bwExecutionSeriesCompletionServiceGroup OBJECT-GROUP
    OBJECTS     { bwSeriesCompletionNumAttempts, 
                  bwSeriesCompletionNumBusy, bwSeriesCompletionSPIndex, 
                  bwSeriesCompletionSPID, 
                  bwSeriesCompletionSPNumAttempts, 
                  bwSeriesCompletionSPNumBusy, 
                  bwSeriesCompletionGroupIndex, 
                  bwSeriesCompletionGroupID, 
                  bwSeriesCompletionGroupNumAttempts, 
                  bwSeriesCompletionGroupNumBusy }
    STATUS      current
    DESCRIPTION 
        "This group defines the statistics for the Series Completion Service."
    ::= { bwExecutionMibGroups 42 }

  bwExecutionInterceptServiceGroup OBJECT-GROUP
    OBJECTS     { bwInterceptUserOriginationInvocations, 
                  bwInterceptGroupOriginationInvocations, 
                  bwInterceptUserTerminationInvocations, 
                  bwInterceptGroupTerminationInvocations, 
                  bwInterceptTransfers, bwInterceptSPIndex, 
                  bwInterceptSPID, 
                  bwInterceptSPUserOriginationInvocations, 
                  bwInterceptSPGroupOriginationInvocations, 
                  bwInterceptSPUserTerminationInvocations, 
                  bwInterceptSPGroupTerminationInvocations, 
                  bwInterceptSPTransfers, bwInterceptGroupIndex, 
                  bwInterceptGroupID, 
                  bwInterceptGroupUserOriginationInvocations, 
                  bwInterceptGroupGroupOriginationInvocations, 
                  bwInterceptGroupUserTerminationInvocations, 
                  bwInterceptGroupGroupTerminationInvocations, 
                  bwInterceptGroupTransfers }
    STATUS      current
    DESCRIPTION 
        "This group defines the statistics for the Intercept Service."
    ::= { bwExecutionMibGroups 43 }

  bwExecutionInstantConferencingServiceGroup OBJECT-GROUP
    OBJECTS     { bwICGroupPortLimitExceeded, bwICNumAttempts, 
                  bwICOutdialNumAttempts, bwInstantConferencingSPIndex, 
                  bwInstantConferencingSPID, 
                  bwICSPGroupPortLimitExceeded, bwICSPNumAttempts, 
                  bwICSPOutdialNumAttempts, 
                  bwInstantConferencingGroupIndex, 
                  bwInstantConferencingGroupID, 
                  bwICGroupGroupPortLimitExceeded, bwICGroupNumAttempts, 
                  bwICGroupOutdialNumAttempts, 
                  bwInstantConferencingBridgeIndex, 
                  bwInstantConferencingBridgeName, 
                  bwInstantConferencingBridgeGroupName, 
                  bwInstantConferencingCurrentUsage, 
                  bwInstantConferencingTodaysPeakUsage, 
                  bwInstantConferencingYesterdaysPeakUsage }
    STATUS      current
    DESCRIPTION 
        "This group defines the statistics for the Instant Conferencing Service."
    ::= { bwExecutionMibGroups 44 }

  bwExecutionCallingLineIdBlockingServiceGroup OBJECT-GROUP
    OBJECTS     { bwCallingLineIDDeliveryBlockPerCallBlocks, 
                  bwCallingLineIDDeliveryPerCall, 
                  bwCallingLineIDDeliveryBlockSPIndex, 
                  bwCallingLineIDDeliveryBlockSPID, 
                  bwCallingLineIDDeliveryBlockSPPerCallBlocks, 
                  bwCallingLineIDDeliveryPerCallSP, 
                  bwCallingLineIDDeliveryBlockGroupIndex, 
                  bwCallingLineIDDeliveryBlockGroupID, 
                  bwCallingLineIDDeliveryBlockGroupPerCallBlocks, 
                  bwCallingLineIDDeliveryPerCallGroup }
    STATUS      current
    DESCRIPTION 
        "This group defines the statistics for the Calling Line ID Blocking Service."
    ::= { bwExecutionMibGroups 45 }

  bwExecutionSessionAuditServiceGroup OBJECT-GROUP
    OBJECTS     { bwSessionAuditNumCallsAudited, 
                  bwSessionAuditNumEndpointsAudited, 
                  bwSessionAuditNumCallsFailedAudit, 
                  bwSessionAuditNumEndpointsFailedAudit, 
                  bwSessionAuditSPIndex, bwSessionAuditSPID, 
                  bwSessionAuditSPNumCallsAudited, 
                  bwSessionAuditSPNumEndpointsAudited, 
                  bwSessionAuditSPNumCallsFailedAudit, 
                  bwSessionAuditSPNumEndpointsFailedAudit, 
                  bwSessionAuditGroupIndex, bwSessionAuditGroupID, 
                  bwSessionAuditGroupNumCallsAudited, 
                  bwSessionAuditGroupNumEndpointsAudited, 
                  bwSessionAuditGroupNumCallsFailedAudit, 
                  bwSessionAuditGroupNumEndpointsFailedAudit }
    STATUS      current
    DESCRIPTION 
        "This group defines the statistics for the Session Audit Service."
    ::= { bwExecutionMibGroups 46 }

  bwExecutionWindowsMessagingServiceGroup OBJECT-GROUP
    OBJECTS     { bwWindowsMessagingIMSessionSuccessCounter }
    STATUS      current
    DESCRIPTION 
        "This group defines the statistics for the Windows Messaging Service."
    ::= { bwExecutionMibGroups 47 }

  bwExecutionCalWaitingServiceGroup OBJECT-GROUP
    OBJECTS     { bwCWNumPhoneCancellations, bwCallWaitingSPIndex, 
                  bwCallWaitingSPID, bwCWSPNumPhoneCancellations, 
                  bwCallWaitingGroupIndex, bwCallWaitingGroupID, 
                  bwCWGroupNumPhoneCancellations }
    STATUS      current
    DESCRIPTION 
        "This group defines the statistics for the Call Waiting Service."
    ::= { bwExecutionMibGroups 48 }

  bwExecutionAlternateNumberServiceGroup OBJECT-GROUP
    OBJECTS     { bwAlternateNumbersUsage, bwAlternateNumbersSPIndex, 
                  bwAlternateNumbersSPID, bwAlternateNumbersSPUsage, 
                  bwAlternateNumbersGroupIndex, 
                  bwAlternateNumbersGroupID, 
                  bwAlternateNumbersGroupUsage }
    STATUS      current
    DESCRIPTION 
        "This group defines the statistics for the Alternate Number Service."
    ::= { bwExecutionMibGroups 49 }

  bwExecutionCustomerOriginatedTraceServiceGroup OBJECT-GROUP
    OBJECTS     { bwCotActivation, bwCotFailureNoId, bwMidCallCotActivation, 
                  bwMidCallCotFailureNoId, bwCotSPIndex, 
                  bwCotSPID, bwCotSPActivation, bwCotSPFailureNoId, 
                  bwMidCallCotSPActivation, bwMidCallCotSPFailureNoId,
                  bwCotGroupIndex, bwCotGroupID, bwCotGroupActivation, 
                  bwCotGroupFailureNoId, bwMidCallCotGroupActivation, 
                  bwMidCallCotGroupFailureNoId }
    STATUS      current
    DESCRIPTION 
        "This group defines the statistics for the Customer Originated Trace Service."
    ::= { bwExecutionMibGroups 50 }

  bwExecutionSpeedDialing8ServiceGroup OBJECT-GROUP
    OBJECTS     { bwSD8NumTimesDialed, bwSD8NumTimesProgrammed, 
                  bwSD8SPIndex, bwSD8SPID, bwSD8SPNumTimesDialed, 
                  bwSD8SPNumTimesProgrammed, bwSD8GroupIndex, 
                  bwSD8GroupID, bwSD8GroupNumTimesDialed, 
                  bwSD8GroupNumTimesProgrammed }
    STATUS      current
    DESCRIPTION 
        "This group defines the statistics for the Speed Dialing 8 Service."
    ::= { bwExecutionMibGroups 51 }

  bwExecutionMusicOnHoldServiceGroup OBJECT-GROUP
    OBJECTS     { bwMusicOnHoldNumUses, 
                  bwMusicOnHoldExternalSourceNumFailures, 
                  bwMusicOnHoldSPIndex, bwMusicOnHoldSPID, 
                  bwMusicOnHoldSPNumUses, 
                  bwMusicOnHoldSPExternalSourceNumFailures, 
                  bwMusicOnHoldGroupIndex, bwMusicOnHoldGroupID, 
                  bwMusicOnHoldGroupNumUses, 
                  bwMusicOnHoldGroupExternalSourceNumFailures }
    STATUS      current
    DESCRIPTION 
        "This group defines the statistics for the Music On Hold Service."
    ::= { bwExecutionMibGroups 52 }

  bwExecutionCallingNameQueriesServiceGroup OBJECT-GROUP
    OBJECTS     { bwCNAMQueriesSent, bwCNAMQueriesFailed, 
                  bwCNAMQueriesTimeout, bwCNAMSPIndex, bwCNAMSPID, 
                  bwCNAMSPQueriesSent, bwCNAMSPQueriesFailed, 
                  bwCNAMSPQueriesTimeout, bwCNAMGroupIndex, 
                  bwCNAMGroupID, bwCNAMGroupQueriesSent, 
                  bwCNAMGroupQueriesFailed, bwCNAMGroupQueriesTimeout }
    STATUS      current
    DESCRIPTION 
        "This group defines the statistics for the Calling Name Queries Service."
    ::= { bwExecutionMibGroups 53 }

  bwExecutionThirdPartyMWIControlServiceGroup OBJECT-GROUP
    OBJECTS     { bwThirdPartyMWIControlNotifyIns, 
                  bwThirdPartyMWIControlNotifyFailures }
    STATUS      current
    DESCRIPTION 
        "This group defines the statistics for the Third Party Message Waiting Indicator Control Service."
    ::= { bwExecutionMibGroups 54 }

  bwExecutionCallCenterServiceGroup OBJECT-GROUP
    OBJECTS     { bwCallCenterSPIndex, 
                  bwCallCenterSPID, 
                  bwCallCenterGroupIndex, bwCallCenterGroupID, 
                  bwCallCenterNumCalls, 
                  bwCallCenterNumSizeOverflow, 
                  bwCallCenterNumTimeOverflow, 
                  bwCallCenterNumBouncedCalls, 
                  bwCallCenterNumEntranceMessage, 
                  bwCallCenterNumComfortMessage, 
                  bwCallCenterNumComfortBypassMessage, 
                  bwCallCenterNumStrandedMessage, 
                  bwCallCenterNumNightServiceMessage, 
                  bwCallCenterNumManualNightServiceMessage, 
                  bwCallCenterNumHolidayServiceMessage, 
                  bwCallCenterNumForcedForwardingMessage, 
                  bwCallCenterNumHoldReminder,
                  bwCallCenterNumBouncedHeldCall,
                  bwCallCenterNumAgentWhisperMessage,
                  bwCallCenterNumOutgoingCall,
                  bwCallCenterNumEscalatedCalls,
                  bwCallCenterNumEscalatedCallsFailure,
                  bwCallCenterNumEmergencyCalls,
                  bwCallCenterNumEmergencyCallsFailure,
                  bwCallCenterNumQueuePositionMessage,
                  bwCallCenterNumQueueWaitTimeMessage,
                  bwCallCenterSPNumCalls, bwCallCenterSPNumSizeOverflow, 
                  bwCallCenterSPNumTimeOverflow, 
                  bwCallCenterSPNumBouncedCalls, 
                  bwCallCenterSPNumEntranceMessage, 
                  bwCallCenterSPNumComfortMessage, 
                  bwCallCenterSPNumComfortBypassMessage, 
                  bwCallCenterSPNumStrandedMessage, 
                  bwCallCenterSPNumNightServiceMessage, 
                  bwCallCenterSPNumManualNightServiceMessage, 
                  bwCallCenterSPNumHolidayServiceMessage, 
                  bwCallCenterSPNumForcedForwardingMessage, 
                  bwCallCenterSPNumHoldReminder,
                  bwCallCenterSPNumBouncedHeldCall,
                  bwCallCenterSPNumAgentWhisperMessage,
                  bwCallCenterSPNumOutgoingCall,
                  bwCallCenterSPNumEscalatedCalls,
                  bwCallCenterSPNumEscalatedCallsFailure,
                  bwCallCenterSPNumEmergencyCalls,
                  bwCallCenterSPNumEmergencyCallsFailure,
                  bwCallCenterSPNumQueuePositionMessage,
                  bwCallCenterSPNumQueueWaitTimeMessage,
                  bwCallCenterGroupNumCalls, 
                  bwCallCenterGroupNumSizeOverflow, 
                  bwCallCenterGroupNumTimeOverflow, 
                  bwCallCenterGroupNumBouncedCalls, 
                  bwCallCenterGroupNumEntranceMessage, 
                  bwCallCenterGroupNumComfortMessage, 
                  bwCallCenterGroupNumComfortBypassMessage, 
                  bwCallCenterGroupNumStrandedMessage, 
                  bwCallCenterGroupNumNightServiceMessage, 
                  bwCallCenterGroupNumManualNightServiceMessage, 
                  bwCallCenterGroupNumHolidayServiceMessage, 
                  bwCallCenterGroupNumForcedForwardingMessage, 
                  bwCallCenterNumOverflowMessage, 
                  bwCallCenterSPNumOverflowMessage, 
                  bwCallCenterGroupNumOverflowMessage,
                  bwCallCenterGroupNumHoldReminder,
                  bwCallCenterGroupNumBouncedHeldCall,
                  bwCallCenterGroupNumAgentWhisperMessage,
                  bwCallCenterGroupNumOutgoingCall,
                  bwCallCenterGroupNumEscalatedCalls,
                  bwCallCenterGroupNumEscalatedCallsFailure,
                  bwCallCenterGroupNumEmergencyCalls,
                  bwCallCenterGroupNumEmergencyCallsFailure,
                  bwCallCenterGroupNumQueuePositionMessage,
                  bwCallCenterGroupNumQueueWaitTimeMessage }
    STATUS      current
    DESCRIPTION 
        "This group defines the statistics for the Call Center Service."
    ::= { bwExecutionMibGroups 55 }

  bwExecutionCallForwardGroupNoAnswerServiceGroup OBJECT-GROUP
    OBJECTS     { bwCFGNAForward, bwCFGNAOverflowForward, 
                  bwCFGNAOverflowNoForward, bwCFGNAExternalForward, 
                  bwCFGNAExternalNoForward, bwCFGNASPIndex, bwCFGNASPID, 
                  bwCFGNASPForward, bwCFGNASPOverflowForward, 
                  bwCFGNASPOverflowNoForward, bwCFGNASPExternalForward, 
                  bwCFGNASPExternalNoForward, bwCFGNAGroupIndex, 
                  bwCFGNAGroupID, bwCFGNAGroupForward, 
                  bwCFGNAGroupOverflowForward, 
                  bwCFGNAGroupOverflowNoForward, 
                  bwCFGNAGroupExternalForward, 
                  bwCFGNAGroupExternalNoForward }
    STATUS      current
    DESCRIPTION 
        "This group defines the statistics for the Call Forward Group No Answer Service."
    ::= { bwExecutionMibGroups 56 }

  bwExecutionSpeedDialing100ServiceGroup OBJECT-GROUP
    OBJECTS     { bwSD100Program, bwSD100Call, bwSD100SPIndex, 
                  bwSD100SPID, bwSD100SPProgram, bwSD100SPCall, 
                  bwSD100GroupIndex, bwSD100GroupID, bwSD100GroupProgram, 
                  bwSD100GroupCall }
    STATUS      current
    DESCRIPTION 
        "This group defines the statistics for the Speed Dialing 100 Service."
    ::= { bwExecutionMibGroups 57 }

  bwExecutionThirdPartyVoiceMailServiceGroup OBJECT-GROUP
    OBJECTS     { bwThirdPartyVoiceMailNbOfCFWBusy, 
                  bwThirdPartyVoiceMailNbOfCFWNoAnswer, 
                  bwThirdPartyVMailSPIndex, bwThirdPartyVMailSPID, 
                  bwThirdPartyVoiceMailSPNbOfCFWBusy, 
                  bwThirdPartyVoiceMailSPNbOfCFWNoAnswer, 
                  bwThirdPartyVMailGroupIndex, bwThirdPartyVMailGroupID, 
                  bwThirdPartyVoiceMailGroupNbOfCFWBusy, 
                  bwThirdPartyVoiceMailGroupNbOfCFWNoAnswer }
    STATUS      current
    DESCRIPTION 
        "This group defines the statistics for the Third Party Voice Mail Service."
    ::= { bwExecutionMibGroups 58 }

  bwExecutionDirectedCallPickupServiceGroup OBJECT-GROUP
    OBJECTS     { bwDirectedCallPickupNumAttempts, 
                  bwDirectedCallPickupNumFailures, 
                  bwDirectedCallPickupSPIndex, bwDirectedCallPickupSPID, 
                  bwDirectedCallPickupSPNumAttempts, 
                  bwDirectedCallPickupSPNumFailures, 
                  bwDirectedCallPickupGroupIndex, 
                  bwDirectedCallPickupGroupID, 
                  bwDirectedCallPickupGroupNumAttempts, 
                  bwDirectedCallPickupGroupNumFailures }
    STATUS      current
    DESCRIPTION 
        "This group defines the statistics for the Directed Call Pickup Service."
    ::= { bwExecutionMibGroups 59 }

  bwExecutionFlashCallHoldServiceGroup OBJECT-GROUP
    OBJECTS     { bwFlashCallHoldNumActivations, bwFlashCallHoldSPIndex, 
                  bwFlashCallHoldSPID, bwFlashCallHoldSPNumActivations, 
                  bwFlashCallHoldGroupIndex, bwFlashCallHoldGroupID, 
                  bwFlashCallHoldGroupNumActivations }
    STATUS      current
    DESCRIPTION 
        "This group defines the statistics for the Flash Call Hold Service."
    ::= { bwExecutionMibGroups 60 }

  bwExecutionEmergencyZoneServiceGroup OBJECT-GROUP
    OBJECTS     { bwEZRegistrationsRejected, bwEZEmergencyCallsRejected, 
                  bwEZNormalCallsRejected, bwEZSPIndex, bwEZSPID, 
                  bwEZSPRegistrationsRejected, 
                  bwEZSPEmergencyCallsRejected, 
                  bwEZSPNormalCallsRejected, bwEZGroupIndex, bwEZGroupID, 
                  bwEZGroupRegistrationsRejected, 
                  bwEZGroupEmergencyCallsRejected, 
                  bwEZGroupNormalCallsRejected }
    STATUS      current
    DESCRIPTION 
        "This group defines the statistics for the Emergency Zone Service."
    ::= { bwExecutionMibGroups 61 }

  bwExecutionDirectedCallPickupWithBargeInServiceGroup OBJECT-GROUP
    OBJECTS     { bwDPUBIAttempt, bwDPUBIFailure, bwDPUBIBargeIn, 
                  bwDPUBIBargeInFailure, bwDPUBIExempt, 
                  bwDPUBINumSilentlyMonitoredCalls, bwDPUBINumSilentlyMonitoredCallsFailure,
                  bwDPUBISPIndex, bwDPUBISPID, bwDPUBISPAttempt, bwDPUBISPFailure, 
                  bwDPUBISPBargeIn, bwDPUBISPBargeInFailure, 
                  bwDPUBISPExempt, bwDPUBISPNumSilentlyMonitoredCalls, 
                  bwDPUBISPNumSilentlyMonitoredCallsFailure, bwDPUBIGroupIndex, 
                  bwDPUBIGroupID, bwDPUBIGroupAttempt, bwDPUBIGroupFailure, 
                  bwDPUBIGroupBargeIn, bwDPUBIGroupBargeInFailure, 
                  bwDPUBIGroupExempt, bwDPUBIGroupNumSilentlyMonitoredCalls, 
                  bwDPUBIGroupNumSilentlyMonitoredCallsFailure }
    STATUS      current
    DESCRIPTION 
        "This group defines the statistics for the Directed Call Pickup With Barge In Service."
    ::= { bwExecutionMibGroups 62 }

  bwExecutionAutomaticCallBackServiceGroup OBJECT-GROUP
    OBJECTS     { bwACBStarted, bwACBExpired, 
                  bwACBSPIndex, bwACBSPID, bwACBSPStarted, 
                  bwACBSPExpired, bwACBGroupIndex, 
                  bwACBGroupID, bwACBGroupStarted, 
                  bwACBGroupExpired, bwACBSPMaxOrigSession, 
                  bwACBSPMaxTermSession, bwACBGroupMaxOrigSession, 
                  bwACBGroupMaxTermSession, bwACBMaxOrigSession, 
                  bwACBMaxTermSession, bwLegacyACBSPOrigSession,
                  bwLegacyACBSPOrigSuccessSession, bwLegacyACBSPOrigFailedSession,
                  bwLegacyACBSPTermSession, bwLegacyACBSPTermSuccessSession,
                  bwLegacyACBSPTermFailedSession, bwLegacyACBGroupOrigSession,
                  bwLegacyACBGroupOrigSuccessSession, bwLegacyACBGroupOrigFailedSession,
                  bwLegacyACBGroupTermSession, bwLegacyACBGroupTermSuccessSession,
                  bwLegacyACBGroupTermFailedSession, bwLegacyACBGroupOrigSession,
                  bwLegacyACBGroupOrigSuccessSession, bwLegacyACBGroupOrigFailedSession,
                  bwLegacyACBGroupTermSession, bwLegacyACBGroupTermSuccessSession,
                  bwLegacyACBGroupTermFailedSession, bwLegacyACBOrigSession,
                  bwLegacyACBOrigSuccessSession, bwLegacyACBOrigFailedSession,
                  bwLegacyACBTermSession, bwLegacyACBTermSuccessSession,
                  bwLegacyACBTermFailedSession }
    STATUS      current
    DESCRIPTION 
        "This group defines the statistics for the Automatic Call Back Service."
    ::= { bwExecutionMibGroups 63 }

  bwExecutionRingTimeoutServiceGroup OBJECT-GROUP
    OBJECTS     { bwRingTimeoutNumExpires, bwRingTimeoutSPIndex, 
                  bwRingTimeoutSPID, bwRingTimeoutSPNumExpires, 
                  bwRingTimeoutGroupIndex, bwRingTimeoutGroupID, 
                  bwRingTimeoutGroupNumExpires }
    STATUS      current
    DESCRIPTION 
        "This group defines the statistics for the Ring Timeout Service."
    ::= { bwExecutionMibGroups 64 }

  bwExecutionSequentialRingServiceGroup OBJECT-GROUP
    OBJECTS     { bwSequentialRingNumAttempts, 
                  bwSequentialRingNumNoAnswer, 
                  bwSequentialRingActivations, bwSequentialRingAnswered, 
                  bwSequentialRingAbandoned, bwSequentialRingSPIndex, 
                  bwSequentialRingSPID, bwSequentialRingSPNumAttempts, 
                  bwSequentialRingSPNumNoAnswer, 
                  bwSequentialRingSPActivations, 
                  bwSequentialRingSPAnswered, 
                  bwSequentialRingSPAbandoned, 
                  bwSequentialRingGroupIndex, bwSequentialRingGroupID, 
                  bwSequentialRingGroupNumAttempts, 
                  bwSequentialRingGroupNumNoAnswer, 
                  bwSequentialRingGroupActivations, 
                  bwSequentialRingGroupAnswered, 
                  bwSequentialRingGroupAbandoned }
    STATUS      current
    DESCRIPTION 
        "This group defines the statistics for the Sequential Ring Service."
    ::= { bwExecutionMibGroups 65 }

  bwExecutionVideoAddOnServiceGroup OBJECT-GROUP
    OBJECTS     { bwVAOOutgoingAttempts, bwVAOOutgoingSuccess, 
                  bwVAOIncomingAttempts, bwVAOIncomingSuccess, 
                  bwVAOSPIndex, bwVAOSPID, bwVAOSPOutgoingAttempts, 
                  bwVAOSPOutgoingSuccess, bwVAOSPIncomingAttempts, 
                  bwVAOSPIncomingSuccess, bwVAOGroupIndex, bwVAOGroupID, 
                  bwVAOGroupOutgoingAttempts, bwVAOGroupOutgoingSuccess, 
                  bwVAOGroupIncomingAttempts, bwVAOGroupIncomingSuccess }
    STATUS      current
    DESCRIPTION 
        "This group defines the statistics for the Video Add-On Service."
    ::= { bwExecutionMibGroups 66 }

  bwExecutionMaliciousCallTraceServiceGroup OBJECT-GROUP
    OBJECTS     { bwMaliciousCallTraceApplied,
                  bwMaliciousCallTraceAnnouncement, 
                  bwMaliciousCallTraceSPIndex, bwMaliciousCallTraceSPID, 
                  bwMaliciousCallTraceSPApplied, 
                  bwMaliciousCallTraceSPAnnouncement,
                  bwMaliciousCallTraceGroupIndex, 
                  bwMaliciousCallTraceGroupID, 
                  bwMaliciousCallTraceGroupApplied,
                  bwMaliciousCallTraceGroupAnnouncement }
    STATUS      current
    DESCRIPTION 
        "This group defines the statistics for the Malicious Call Trace Service."
    ::= { bwExecutionMibGroups 67 }

  bwExecutionPushToTalkServiceGroup OBJECT-GROUP
    OBJECTS     { bwPTTInvoke, bwPTTReject, bwPTTSPIndex, bwPTTSPID, 
                  bwPTTSPInvoke, bwPTTSPReject, bwPTTGroupIndex, 
                  bwPTTGroupID, bwPTTGroupInvoke, bwPTTGroupReject }
    STATUS      current
    DESCRIPTION 
        "This group defines the statistics for the Push To Talk Service."
    ::= { bwExecutionMibGroups 68 }

  bwExecutionHotelingServiceGroup OBJECT-GROUP
    OBJECTS     { bwHotelingAssociate, bwHotelingDisassociate, 
                  bwHotelingTimeout, bwHotelingSPIndex, bwHotelingSPID, 
                  bwHotelingSPAssociate, bwHotelingSPDisassociate, 
                  bwHotelingSPTimeout, bwHotelingGroupIndex, 
                  bwHotelingGroupID, bwHotelingGroupAssociate, 
                  bwHotelingGroupDisassociate, bwHotelingGroupTimeout }
    STATUS      current
    DESCRIPTION 
        "This group defines the statistics for the Hoteling Service."
    ::= { bwExecutionMibGroups 69 }

  bwExecutionPreferredCarrierServiceGroup OBJECT-GROUP
    OBJECTS     { bwSubscriptionUserPIC, bwSubscriptionGroupPIC, 
                  bwSubscriptionServiceProviderPIC, 
                  bwSubscriptionDialedUserPIC, 
                  bwSubscriptionDialedGroupPIC, 
                  bwSubscriptionDialedServiceProviderPIC, 
                  bwNonSubscriptionDialedUserPIC, 
                  bwNonSubscriptionDialedGroupPIC, 
                  bwNonSubscriptionDialedServiceProviderPIC, 
                  bwNoIndicationUserPIC, bwNoIndicationGroupPIC, 
                  bwNoIndicationServiceProviderPIC, 
                  bwPreferredCarrierSPIndex, bwPreferredCarrierSPID, 
                  bwSPSubscriptionUserPIC, bwSPSubscriptionGroupPIC, 
                  bwSPSubscriptionServiceProviderPIC, 
                  bwSPSubscriptionDialedUserPIC, 
                  bwSPSubscriptionDialedGroupPIC, 
                  bwSPSubscriptionDialedServiceProviderPIC, 
                  bwSPNonSubscriptionDialedUserPIC, 
                  bwSPNonSubscriptionDialedGroupPIC, 
                  bwSPNonSubscriptionDialedServiceProviderPIC, 
                  bwSPNoIndicationUserPIC, bwSPNoIndicationGroupPIC, 
                  bwSPNoIndicationServiceProviderPIC, 
                  bwPreferredCarrierGroupIndex, 
                  bwPreferredCarrierGroupID, bwGroupSubscriptionUserPIC, 
                  bwGroupSubscriptionGroupPIC, 
                  bwGroupSubscriptionServiceProviderPIC, 
                  bwGroupSubscriptionDialedUserPIC, 
                  bwGroupSubscriptionDialedGroupPIC, 
                  bwGroupSubscriptionDialedServiceProviderPIC, 
                  bwGroupNonSubscriptionDialedUserPIC, 
                  bwGroupNonSubscriptionDialedGroupPIC, 
                  bwGroupNonSubscriptionDialedServiceProviderPIC, 
                  bwGroupNoIndicationUserPIC, 
                  bwGroupNoIndicationGroupPIC, 
                  bwGroupNoIndicationServiceProviderPIC }
    STATUS      current
    DESCRIPTION 
        "This group defines the statistics for the Preferred Carrier Service."
    ::= { bwExecutionMibGroups 70 }

  bwExecutionFamilySimRingServiceGroup OBJECT-GROUP
    OBJECTS     { bwFamilySimRingNumAttempts, bwFamilySimRingNumBusy, 
                  bwFamilySimRingSPIndex, bwFamilySimRingSPID, 
                  bwFamilySimRingSPNumAttempts, bwFamilySimRingSPNumBusy, 
                  bwFamilySimRingGroupIndex, bwFamilySimRingGroupID, 
                  bwFamilySimRingGroupNumAttempts, 
                  bwFamilySimRingGroupNumBusy }
    STATUS      current
    DESCRIPTION 
        "This group defines the statistics for the Family SimRing Service."
    ::= { bwExecutionMibGroups 71 }

  bwExecutionDiversionInhibitorServiceGroup OBJECT-GROUP
    OBJECTS     { bwDiversionInhibited, bwDiversionInhibitorSPIndex, 
                  bwDiversionInhibitorSPID, bwSPDiversionInhibited, 
                  bwDiversionInhibitorGroupIndex, 
                  bwDiversionInhibitorGroupID, bwGroupDiversionInhibited }
    STATUS      current
    DESCRIPTION 
        "This group defines the statistics for the Diversion Inhibitor Service."
    ::= { bwExecutionMibGroups 72 }

  bwExecutionInstantGroupCallServiceGroup OBJECT-GROUP
    OBJECTS     { bwIGCPushToTalkInvoke, bwIGCNormalInvoke, bwIGCSPIndex, 
                  bwIGCSPID, bwIGCSPPushToTalkInvoke, 
                  bwIGCSPNormalInvoke, bwIGCGroupIndex, bwIGCGroupID, 
                  bwIGCGroupPushToTalkInvoke, bwIGCGroupNormalInvoke }
    STATUS      current
    DESCRIPTION 
        "This group defines the statistics for the Instant Group Call Service."
    ::= { bwExecutionMibGroups 73 }

  bwExecutionAutomaticHoldAndRetrieveServiceGroup OBJECT-GROUP
    OBJECTS     { bwAHRHold, bwAHRRetrieve, bwAHRSPIndex, bwAHRSPID, 
                  bwAHRSPHold, bwAHRSPRetrieve, bwAHRGroupIndex, 
                  bwAHRGroupID, bwAHRGroupHold, bwAHRGroupRetrieve }
    STATUS      current
    DESCRIPTION 
        "This group defines the statistics for the Automatic Hold And Retrieve Service."
    ::= { bwExecutionMibGroups 74 }

  bwExecutionBusinessTrunkGroupServiceGroup OBJECT-GROUP
    OBJECTS     { bwTrunkOriginationAttempt, bwTrunkOriginationBlocked, 
                  bwTrunkTerminationAttempt, bwTrunkTerminationBlocked,
                  bwTrunkOodPbxRedirectionAttempt, bwTrunkOodPbxRedirectionBlocked,
                  bwTrunkSPIndex, bwTrunkSPID, 
                  bwTrunkSPOriginationAttempt, 
                  bwTrunkSPOriginationBlocked, 
                  bwTrunkSPTerminationAttempt, 
                  bwTrunkSPTerminationBlocked, 
                  bwTrunkSPOodPbxRedirectionAttempt, bwTrunkSPOodPbxRedirectionBlocked,
                  bwTrunkGroupIndex, 
                  bwTrunkGroupID, bwTrunkGroupOriginationAttempt, 
                  bwTrunkGroupOriginationBlocked, 
                  bwTrunkGroupTerminationAttempt, 
                  bwTrunkGroupTerminationBlocked, 
                  bwTrunkGroupOodPbxRedirectionAttempt, bwTrunkGroupOodPbxRedirectionBlocked,
                  bwTrunkGroupPerTGIndex, 
                  bwTrunkGroupPerTGName, 
                  bwTrunkGroupPerTGCapacityExceeded, 
                  bwTrunkGroupPerTGUnreachableDestination, 
                  bwTrunkGroupPerTGMaxActiveCalls, 
                  bwTrunkGroupPerTGMaxOutgoingActiveCalls, 
                  bwTrunkGroupPerTGMaxIncomingActiveCalls, 
                  bwTrunkGroupPerTGCapacityExceededInitialValue, 
                  bwTrunkGroupPerTGCapacityExceededOffsetValue, 
                  bwTrunkGroupPerTGGroupID, bwTrunkGroupPerTGBursting, 
                  bwTrunkGroupPerTGBurstingMaxActiveCalls, 
                  bwTrunkGroupPerTGBurstingMaxOutgoingActiveCalls, 
                  bwTrunkGroupPerTGBurstingMaxIncomingActiveCalls, bwTrunkGroupPerTGTotalActiveCalls,
                  bwTrunkGroupPerTGOutgoingActiveCalls, bwTrunkGroupPerTGIncomingActiveCalls,
                  bwTrunkGroupPerTGTotalCallHighWaterMark, bwTrunkGroupPerTGOutgoingCallHighWaterMark,
                  bwTrunkGroupPerTGIncomingCallHighWaterMark, bwTrunkGroupPerTGCallHighWaterMarkReset,
                  bwTrunkGroupPerTGTotalCallHighWaterMark, bwTrunkGroupPerTGHoldingOutgoingCallHighWaterMark,
                  bwTrunkGroupPerTGHoldingIncomingCallHighWaterMark, bwTrunkGroupPerTGOriginationAttempt,
                  bwTrunkGroupPerTGOriginationBlocked, bwTrunkGroupPerTGTerminationAttempt,
                  bwTrunkGroupPerTGTerminationBlocked, bwTrunkGroupPerTGTerminationFailure,
                  bwTrunkGroupPerTGOodPbxRedirectionAttempt, bwTrunkGroupPerTGOodPbxRedirectionBlocked,
                  bwTrunkGroupCallHighWaterMarkReset
                 }
    STATUS      current
    DESCRIPTION 
        "This group defines the statistics for the Business Trunk Group Service."
    ::= { bwExecutionMibGroups 75 }

  bwExecutionCustomRingbackServiceGroup OBJECT-GROUP
    OBJECTS     { bwCustomRingbackUserAudioAttempts, 
                  bwCustomRingbackUserVideoAttempts, 
                  bwCustomRingbackUserAudioFailures, 
                  bwCustomRingbackUserVideoFailures, 
                  bwCustomRingbackGroupAudioAttempts, 
                  bwCustomRingbackGroupVideoAttempts, 
                  bwCustomRingbackGroupAudioFailures, 
                  bwCustomRingbackGroupVideoFailures, 
                  bwCustomRingbackSPIndex, bwCustomRingbackSPID, 
                  bwCustomRingbackUserAudioSPAttempts, 
                  bwCustomRingbackUserVideoSPAttempts, 
                  bwCustomRingbackUserAudioSPFailures, 
                  bwCustomRingbackUserVideoSPFailures, 
                  bwCustomRingbackGroupAudioSPAttempts, 
                  bwCustomRingbackGroupVideoSPAttempts, 
                  bwCustomRingbackGroupAudioSPFailures, 
                  bwCustomRingbackGroupVideoSPFailures, 
                  bwCustomRingbackGroupIndex, bwCustomRingbackGroupID, 
                  bwCustomRingbackUserAudioGroupAttempts, 
                  bwCustomRingbackUserVideoGroupAttempts, 
                  bwCustomRingbackUserAudioGroupFailures, 
                  bwCustomRingbackUserVideoGroupFailures, 
                  bwCustomRingbackGroupAudioGroupAttempts, 
                  bwCustomRingbackGroupVideoGroupAttempts, 
                  bwCustomRingbackGroupAudioGroupFailures, 
                  bwCustomRingbackGroupVideoGroupFailures, 
                  bwCustomRingbackUserVideoCWSPAttempts, 
                  bwCustomRingbackUserAudioCWSPAttempts, 
                  bwCustomRingbackUserAudioCWSPFailures, 
                  bwCustomRingbackUserVideoCWSPFailures, 
                  bwCustomRingbackUserAudioCWGroupAttempts, 
                  bwCustomRingbackUserVideoCWGroupAttempts, 
                  bwCustomRingbackUserAudioCWGroupFailures, 
                  bwCustomRingbackUserVideoCWGroupFailures, 
                  bwCustomRingbackUserAudioCWAttempts, 
                  bwCustomRingbackUserVideoCWAttempts, 
                  bwCustomRingbackUserAudioCWFailures, 
                  bwCustomRingbackUserVideoCWFailures }
    STATUS      current
    DESCRIPTION 
        "This group defines the statistics for the Custom Ringback Service."
    ::= { bwExecutionMibGroups 76 }

  bwExecutionMssGroup OBJECT-GROUP
    OBJECTS     { bwNSqueryRequestsTransmitted, bwNSqueryCommFailures }
    STATUS      current
    DESCRIPTION 
        "This group defines the statistics for the Media Server Selection."
    ::= { bwExecutionMibGroups 77 }

  bwExecutionNrsGroup OBJECT-GROUP
    OBJECTS     { bwNbInvalidMessagesReceived, bwNbRequestsReceived, 
                  bwNbResponsesReceived, bwNbErrorsReceived, 
                  bwNbRequestsSent, bwNbResponsesSent, bwNbErrorsSent, 
                  bwNbRequestsResent, bwNbResponsesResent, 
                  bwNbRequestsUnanswered, bwNRSStatsTableProtocolName, 
                  bwNRSStatsTableNbRequestsReceived, 
                  bwNRSStatsTableNbResponsesReceived, 
                  bwNRSStatsTableNbErrorsReceived, 
                  bwNRSStatsTableNbRequestsSent, 
                  bwNRSStatsTableNbResponsesSent, 
                  bwNRSStatsTableNbErrorsSent, 
                  bwNRSStatsTableNbRequestsResent, 
                  bwNRSStatsTableNbResponsesResent, 
                  bwNRSStatsTableNbRequestsUnanswered }
    STATUS      current
    DESCRIPTION 
        "This group defines the statistics for the NRS based protocols."
    ::= { bwExecutionMibGroups 78 }

  bwExecutionXsPersistencyGroup OBJECT-GROUP
    OBJECTS     { perNbOpenedTransactions, perNbCommittedTransactions, 
                  perNbFailedTransactions, perNbCriticalErrors, 
                  ttNbConnectionsCreated, ttConnectionPoolSize,  
                  xsRemoteXlaNbTimesConnected, 
                  xsRemoteXlaNbTimesDisconnected, 
                  xsRemoteXlaUpdatesProcessed, xsRemoteXlaUpdatesPending }
    STATUS      current
    DESCRIPTION 
        "This group defines the statistics for the Application Server Execution Server process persistency."
    ::= { bwExecutionMibGroups 79 }

  bwExecutionProtocolMonitorGroup OBJECT-GROUP
    OBJECTS     { bwPMTNumMonitorsCreated, bwPMTNumMonitorsOpen, 
                  bwPMTNumLoggerCreated, bwPMTNumLoggerOpen }
    STATUS      current
    DESCRIPTION 
        "This group defines the statistics for the Protocol Monitor."
    ::= { bwExecutionMibGroups 80 }

  bwExecutionSystemStatsGroup OBJECT-GROUP
    OBJECTS     { bwSystemName, bwNumberOfUsers, bwNumberOfGroups, 
                  bwNumberOfServProv, bwNumberOfDNDefined, 
                  bwNumberOfDNAssigned, bwNumberOfDeviceType, 
                  bwNumberOfServiceType, bwNumberOfNonVirtualUsers, 
                  bwNumberOfLicensedUsers, bwDeviceTypeSystemIndex, 
                  bwDeviceTypeSystemID, bwNumberOfDeviceTypeSystem, 
                  bwServiceTypeSystemIndex, bwServiceTypeSystemID, 
                  bwNumberOfServiceTypeAssignedSystem, bwSystemSPIndex, 
                  bwSystemSPID, bwSystemSPName, bwNumberOfSPUsers, 
                  bwNumberOfSPGroups, bwNumberOfSPDNDefined, 
                  bwNumberOfSPDNAssigned, bwNumberOfSPDeviceType, 
                  bwSystemGroupIndex, bwSystemGroupSPID, bwSystemGroupID, 
                  bwSystemGroupName, bwNumberOfGroupUsers, 
                  bwNumberOfGroupDNDefined, bwNumberOfGroupDNAssigned, 
                  bwNumberOfGroupDeviceType }
    STATUS      current
    DESCRIPTION 
        "This group defines the system level statistics for the Application Server."
    ::= { bwExecutionMibGroups 81 }

  bwExecutionQueueStatsGroup OBJECT-GROUP
    OBJECTS     { bwSystemInternalQueueResets, 
                  bwSystemInternalQueueIndex, bwSystemInternalQueueName, 
                  bwSystemInternalQueueSize, 
                  bwSystemInternalQueueTimeAvg, 
                  bwSystemInternalQueueTimeMin, 
                  bwSystemInternalQueueTimeMax, 
                  bwSystemInternalQueueTimeMaxTimestampMSB, 
                  bwSystemInternalQueueLengthCurrent, 
                  bwSystemInternalQueueLengthAvg, 
                  bwSystemInternalQueueLengthMax, 
                  bwSystemInternalQueueLengthMaxTimestampMSB, 
                  bwSystemInternalQueueLengthMaxTimestampLSB, 
                  bwSystemInternalQueueTimeMaxTimestampLSB }
    STATUS      current
    DESCRIPTION 
        "This group defines the statistics for the Application Server processing internal queues."
    ::= { bwExecutionMibGroups 82 }

  bwExecutionOverloadControlStatsGroup OBJECT-GROUP
    OBJECTS     { bwCurrentCallOverloadZone, 
                  bwNumCallYellowZoneOverloadTrans, 
                  bwNumCallRedZoneOverloadTrans, 
                  bwCurrentNonCallOverloadZone, 
                  bwNumNonCallYellowZoneOverloadTrans, 
                  bwNumNonCallRedZoneOverloadTrans, 
                  bwNumDiscardedMessage, bwTimeLastDiscardedMessage,
                  bwMemoryHighWaterMark, bwMemoryHighWaterMarkTimeMSB,
                  bwMemoryHighWaterMarkTimeLSB, bwOverloadStatsReset,
                  bwOverloadSampledDataIndex, bwOverloadSampledDataName,
                  bwOverloadSampledDelayMin, bwOverloadSampledDelayAvg,
                  bwOverloadSampledDelayMax, bwOverloadSampledDelayMaxTimeMSB,
                  bwOverloadSampledDelayMaxTimeLSB, bwOverloadNumSamples }
    STATUS      current
    DESCRIPTION 
        "This group defines the statistics for the Overload Control feature on the Application Server."
    ::= { bwExecutionMibGroups 83 }

  bwExecutionRedundancyStatsGroup OBJECT-GROUP
    OBJECTS     { nbOfMigratedUsers }
    STATUS      current
    DESCRIPTION 
        "This group defines the statistics for the Application Server Redundancy feature."
    ::= { bwExecutionMibGroups 84 }

  bwExecutionDatabaseStatsGroup OBJECT-GROUP
    OBJECTS     { bwXSAvgUpdateTime, bwXSAvgRowsUpdated, 
                  bwXSAvgRowsUpdated, bwXSAvgQueryTime, 
                  bwXSAvgRowsQueried, bwXSUpdateCount, bwXSQueryCount, 
                  bwXSTTHWMIndex, bwXSTTHWMName, bwXSTTHWMValue, 
                  bwXSTTHWMTimestamp, bwXSTTHWMStackTrace,
                  bwXSTimesTenNbOpenedTransactions, bwXSTimesTenNbCommittedTransactions,
                  bwXSTimesTenNbFailedTransactions, bwXSTimesTenNbCriticalErrors,
                  bwXSOracleNbOpenedTransactions, bwXSOracleNbFailedTransactions,
                  bwXSOracleNbFailedTransactions, bwXSOracleNbCriticalErrors,
                  bwXSOracleDbCount, bwXSOracleDbStatsIndex,
                  bwXSOracleDbName, bwXSOracleDbNbConnectionsCreated,
                  bwXSOracleDbConnectionPoolSize, bwXSOracleDbAvgUpdateTime,
                  bwXSOracleDbAvgRowsUpdated, bwXSOracleDbAvgQueryTime,
                  bwXSOracleDbAvgRowsQueried, bwXSOracleDbUpdateCount,
                  bwXSOracleDbQueryCount, bwXSOracleDbHWMIndex,
                  bwXSOracleDbHWMDbName, bwXSOracleDbHWMStatName,
                  bwXSOracleDbHWMStatValue, bwXSOracleDbHWMTimestamp,
                  bwXSOracleDbHWMStackTrace }
    STATUS      current
    DESCRIPTION 
        "This group defines the statistics for the Application Server Database feature."
    ::= { bwExecutionMibGroups 85 }

  bwExecutionCongestionManagementGroup OBJECT-GROUP
    OBJECTS     { bwCongestionManagementNeighborIndex, 
                  bwCongestionManagementNeighborIpAddress, 
                  bwCongestionManagementNeighborInviteIn, 
                  bwCongestionManagementNeighborInviteOut, 
                  bwCongestionManagementNeighborRegisterIn, 
                  bwCongestionManagementNeighborOptionsIn, 
                  bwCongestionManagementNeighborOptionsOut, 
                  bwCongestionManagementNeighborSubscribeNotifyIn, 
                  bwCongestionManagementNeighborSubscribeNotifyOut, 
                  bwCongestionManagementNeighbor5xxIn, 
                  bwCongestionManagementNeighborCallpMessageInRate, 
                  bwCongestionManagementNeighborCallpMessageOutRate, 
                  bwCongestionManagementNeighborCallpRequestInRate, 
                  bwCongestionManagementNeighborNonCallpMessageInRate, 
                  bwCongestionManagementNeighborNonCallpMessageOutRate, 
                  bwCongestionManagementNeighborNonCallpRequestInRate, 
                  bwCongestionManagementNeighborState, 
                  bwCongestionManagementNeighborCapability }
    STATUS      current
    DESCRIPTION 
        "This group defines the statistics for Congestion Management."
    ::= { bwExecutionMibGroups 86 }

  bwExecutionPhysicalLocationServiceGroup OBJECT-GROUP
    OBJECTS     { bwNbPhysicalLocationOriginationBlocked, 
                  bwPhysicalLocationSPIndex, bwPhysicalLocationSPID, 
                  bwPhysicalLocationSPOriginationBlocked, 
                  bwPhysicalLocationGroupIndex, 
                  bwPhysicalLocationGroupID, 
                  bwPhysicalLocationGroupOriginationBlocked }
    STATUS      current
    DESCRIPTION 
        "This group defines the statistics for the Physical Location Service."
    ::= { bwExecutionMibGroups 87 }

  bwExecutionFaxMessagingServiceGroup OBJECT-GROUP
    OBJECTS     { bwFaxMessagingReceived, bwFaxMessagingReceptionFailure, 
                  bwFaxMessagingPrinted, bwFaxMessagingPrintingFailure, 
                  bwFaxMessagingSPIndex, bwFaxMessagingSPID, 
                  bwFaxMessagingSPReceived, 
                  bwFaxMessagingSPReceptionFailure, 
                  bwFaxMessagingSPPrinted, 
                  bwFaxMessagingSPPrintingFailure, 
                  bwFaxMessagingGroupIndex, bwFaxMessagingGroupID, 
                  bwFaxMessagingGroupReceived, 
                  bwFaxMessagingGroupReceptionFailure, 
                  bwFaxMessagingGroupPrinted, 
                  bwFaxMessagingGroupPrintingFailure }
    STATUS      current
    DESCRIPTION 
        "This group defines the statistics for the Fax Messaging Service."
    ::= { bwExecutionMibGroups 88 }

  bwExecutionTwoStageDialingServiceGroup OBJECT-GROUP
    OBJECTS     { bwTwoStageDialingInvocation, bwTwoStageDialingSPIndex, 
                  bwTwoStageDialingSPID, bwTwoStageDialingSPInvocation, 
                  bwTwoStageDialingGroupIndex, bwTwoStageDialingGroupID, 
                  bwTwoStageDialingGroupInvocation }
    STATUS      current
    DESCRIPTION 
        "This group defines the statistics for the Two Stage Dialing Service."
    ::= { bwExecutionMibGroups 89 }

  bwExecutionCallForwardingNotReachableGroup OBJECT-GROUP
    OBJECTS     { bwCFNRcNumForwarded, bwCFNRcNumPhoneActivations, 
                  bwCFNRcNumPhoneDeactivations, 
                  bwCFNRcDestinationChanged, bwCFNRcSPIndex, bwCFNRcSPID, 
                  bwCFNRcSPNumForwarded, bwCFNRcSPNumPhoneActivations, 
                  bwCFNRcSPNumPhoneDeactivations, 
                  bwCFNRcSPDestinationChanged, bwCFNRcGroupIndex, 
                  bwCFNRcGroupID, bwCFNRcGroupNumForwarded, 
                  bwCFNRcGroupNumPhoneActivations, 
                  bwCFNRcGroupNumPhoneDeactivations, 
                  bwCFNRcGroupDestinationChanged,
                  bwCFNRcNumPhoneInterrogation,
                  bwCFNRcSPNumPhoneInterrogation,
                  bwCFNRcGroupNumPhoneInterrogation }
    STATUS      current
    DESCRIPTION 
        "This group defines the statistics for Call Forwarding Not Reachable."
    ::= { bwExecutionMibGroups 90 }

  bwExecutionExtEmergencyRtgStatsGroup OBJECT-GROUP
    OBJECTS     { bwExtEmergencyRtgQuerySent, 
                  bwExtEmergencyRtgQueryFailure, 
                  bwExtEmergencyRtgENServerTimeout }
    STATUS      current
    DESCRIPTION 
        "This group defines the statistics for the Automatic Hold And Retrieve Service."
    ::= { bwExecutionMibGroups 91 }

  bwExecutionSoapGroup OBJECT-GROUP
    OBJECTS     { bwSOAPMaxSessions, bwSOAPAvgSessions, bwSOAPMaxThreads, 
                  bwSOAPAvgThreads, bwSOAPMaxServiceTime, 
                  bwSOAPAvgServiceTime, bwSOAPNumDroppedRequests }
    STATUS      current
    DESCRIPTION 
        "This group defines the statistics for SOAP."
    ::= { bwExecutionMibGroups 92 }

  bwExecutionMWIDeliveryToMobileGroup OBJECT-GROUP
    OBJECTS     { bwMWISMSSent, bwMWISPIndex, bwMWISPID, bwSPMWISMSSent, 
                  bwMWIGroupIndex, bwMWIGroupID, bwGroupMWISMSSent }
    STATUS      current
    DESCRIPTION 
        "This group defines the statistics for MWI Delivery to Mobile."
    ::= { bwExecutionMibGroups 93 }

  bwExecutionExternalCustomRingbackGroup OBJECT-GROUP
    OBJECTS     { bwExternalCustomRingbackAttempts, 
                  bwExternalCustomRingbackFailures, 
                  bwExternalCustomRingbackSPIndex, 
                  bwExternalCustomRingbackSPID, 
                  bwExternalCustomRingbackSPAttempts, 
                  bwExternalCustomRingbackSPFailures, 
                  bwExternalCustomRingbackGroupIndex, 
                  bwExternalCustomRingbackGroupID, 
                  bwExternalCustomRingbackGroupAttempts, 
                  bwExternalCustomRingbackGroupFailures }
    STATUS      current
    DESCRIPTION 
        "This group defines the statistics for External Custom Ringback."
    ::= { bwExecutionMibGroups 95 }

  bwExecutionInCallServiceActivationGroup OBJECT-GROUP
    OBJECTS     { bwICSAMonitoringStarted, bwICSAMonitoringFailure, 
                  bwICSAFlashDigitsDetected, bwICSACallTransferInvocation, 
                  bwICSASPIndex, bwICSASPID, 
                  bwICSASPMonitoringStarted, bwICSASPMonitoringFailure, 
                  bwICSASPFlashDigitsDetected, bwICSASPCallTransferInvocation, 
                  bwICSAGroupIndex, bwICSAGroupID, bwICSAGroupMonitoringStarted, 
                  bwICSAGroupMonitoringFailure, bwICSAGroupFlashDigitsDetected,
                  bwICSAGroupCallTransferInvocation }
    STATUS      current
    DESCRIPTION 
        "This group defines the statistics for In Call Service Activation."
    ::= { bwExecutionMibGroups 96 }

  bwExecutionLocationControlGroup OBJECT-GROUP
    OBJECTS     { bwLocationControlActivationSuccess, 
                  bwLocationControlDeactivationSuccess, 
                  bwLocationControlSPIndex, bwLocationControlSPID, 
                  bwLocationControlSPActivationSuccess, 
                  bwLocationControlSPDeactivationSuccess, 
                  bwLocationControlGroupIndex, bwLocationControlGroupID, 
                  bwLocationControlGroupActivationSuccess, 
                  bwLocationControlGroupDeactivationSuccess }
    STATUS      current
    DESCRIPTION 
        "This group defines the location control service."
    ::= { bwExecutionMibGroups 97 }

  bwExecutionCallRetrieveGroup OBJECT-GROUP
    OBJECTS     { bwCallRetrieveSuccess, bwCallRetrieveSPIndex, 
                  bwCallRetrieveSPID, bwCallRetrieveSPSuccess, 
                  bwCallRetrieveGroupIndex, bwCallRetrieveGroupID, 
                  bwCallRetrieveGroupSuccess }
    STATUS      current
    DESCRIPTION 
        "This group defines the call retrieve service."
    ::= { bwExecutionMibGroups 98 }

  bwExecutionBroadworksAnywhereGroup OBJECT-GROUP
    OBJECTS     { bwBACallOriginations, bwBACallTerminations, 
                  bwBroadWorksAnywhereSPIndex, bwBroadWorksAnywhereSPID, 
                  bwBASPCallOriginations, bwBASPCallTerminations, 
                  bwBroadWorksAnywhereGroupIndex, 
                  bwBroadWorksAnywhereGroupID, bwBAGroupCallOriginations, 
                  bwBAGroupCallTerminations }
    STATUS      current
    DESCRIPTION 
        "This group defines the BroadWorks Anywhere service."
    ::= { bwExecutionMibGroups 99 }

  bwExecutionZoneCallingRestrictionsGroup OBJECT-GROUP
    OBJECTS     { bwZoneCallingRestrictionsRedirectionBlocked, 
                  bwZoneCallingRestrictionsConferenceBlocked, 
                  bwZoneCallingRestrictionsRoamingBlocked, 
                  bwZoneCallingRestrictionsSPIndex, 
                  bwZoneCallingRestrictionsSPID, 
                  bwZoneCallingRestrictionsSPRedirectionBlocked, 
                  bwZoneCallingRestrictionsSPConferenceBlocked, 
                  bwZoneCallingRestrictionsSPRoamingBlocked, 
                  bwZoneCallingRestrictionsGroupIndex, 
                  bwZoneCallingRestrictionsGroupID, 
                  bwZoneCallingRestrictionsGroupRedirectionBlocked, 
                  bwZoneCallingRestrictionsGroupConferenceBlocked, 
                  bwZoneCallingRestrictionsGroupRoamingBlocked }
    STATUS      current
    DESCRIPTION 
        "This group defines the Zone Calling Restrictions service."
    ::= { bwExecutionMibGroups 100 }

  bwExecutionOfflineChargingGroup OBJECT-GROUP
    OBJECTS     { bwOfflineChargingACROut, bwOfflineChargingACASuccessIn, 
                  bwOfflineChargingACAFailureIn, 
                  bwOfflineChargingACRTimeout, 
                  bwOfflineChargingUnknownServer, 
                  bwOfflineChargingInvalidServer, 
                  bwOfflineChargingServerUnreachable, 
                  bwOfflineChargingDFNDown, bwOfflineChargingAPNError, 
                  bwOfflineChargingQueued, 
                  bwOfflineChargingTransmittedFromQueue, 
                  bwOfflineChargingRetransmittedFromQueue }
    STATUS      current
    DESCRIPTION 
        "This group defins the Offline Charging service."
    ::= { bwExecutionMibGroups 101 }

  bwExecutionSmppGroup OBJECT-GROUP
    OBJECTS     { bwSmppSubmitSMRequestsSent, 
                  bwSmppInvalidSubmitSMResponsesReceived, 
                  bwSmppSubmitSMResponseTimeout }
    STATUS      current
    DESCRIPTION 
        "This group defines the statistics for SMPP."
    ::= { bwExecutionMibGroups 102 }

  bwExecutionExpensiveCallNotificationGroup OBJECT-GROUP
    OBJECTS     { bwECNWarningAnnouncementAttempts, 
                  bwECNExpensiveCallReleased }
    STATUS      current
    DESCRIPTION 
        "This group defines the statistics for expensive call notification."
    ::= { bwExecutionMibGroups 103 }

  bwExecutionCommunicationBarringGroup OBJECT-GROUP
    OBJECTS     { bwCommunicationBarringBlockedTreatment, bwCommunicationBarringBlockedTransfer, 
                  bwCommunicationBarringPromptedPIN, bwCommunicationBarringFailedPIN,
                  bwCommunicationBarringCallDurationExceeded, bwCommunicationBarringPhoneActivations, 
                  bwCommunicationBarringPhoneDeactivations, bwCommunicationBarringPhoneQueries, 
                  bwCommunicationBarringErroneousPinAttempts, bwCommunicationBarringLockouts, 
                  bwCommunicationBarringSPIndex, bwCommunicationBarringSPID, 
                  bwCommunicationBarringSPBlockedTreatment, bwCommunicationBarringSPBlockedTransfer, 
                  bwCommunicationBarringSPPromptedPIN, bwCommunicationBarringSPFailedPIN, 
                  bwCommunicationBarringSPCallDurationExceeded, bwCommunicationBarringSPPhoneActivations, 
                  bwCommunicationBarringSPPhoneDeactivations, bwCommunicationBarringSPPhoneQueries, 
                  bwCommunicationBarringSPErroneousPinAttempts, bwCommunicationBarringSPLockouts, 
                  bwCommunicationBarringGroupIndex, bwCommunicationBarringGroupID, 
                  bwCommunicationBarringGroupBlockedTreatment, bwCommunicationBarringGroupBlockedTransfer,
                  bwCommunicationBarringGroupPromptedPIN, bwCommunicationBarringGroupFailedPIN, 
                  bwCommunicationBarringGroupCallDurationExceeded, bwCommunicationBarringGroupPhoneActivations,
                  bwCommunicationBarringGroupPhoneDeactivations, bwCommunicationBarringGroupPhoneQueries,
                  bwCommunicationBarringGroupErroneousPinAttempts, bwCommunicationBarringGroupLockouts }
    STATUS      current
    DESCRIPTION 
        "This group defines the Communication Barring service."
    ::= { bwExecutionMibGroups 104 }

  bwExecutionOcicStatsGroup OBJECT-GROUP
    OBJECTS     { bwOCICNumOutgoingOverloadDiscard, 
                  bwOCICStatsEntryIndex, bwOCICApplicationId, 
                  bwOCICNumNoConnectionDiscard, 
                  bwOCICNumRouteExhaustionDiscard, 
                  bwOCICNumResponseTimeout }
    STATUS      current
    DESCRIPTION 
        "This group defines the OCI-C statistics."
    ::= { bwExecutionMibGroups 105 }

  bwExecutionOnlineChargingStatsGroup OBJECT-GROUP
    OBJECTS     { bwOnlineChargingCCROut, bwOnlineChargingCCASuccessIn, 
                  bwOnlineChargingCCAFailureIn, 
                  bwOnlineChargingCCRTimeout, 
                  bwOnlineChargingUnknownServer, 
                  bwOnlineChargingInvalidServer, 
                  bwOnlineChargingServerUnreachable, 
                  bwOnlineChargingDFNDown, bwOnlineChargingAPNError }
    STATUS      current
    DESCRIPTION 
        "This group defines the Online Charging statistics."
    ::= { bwExecutionMibGroups 106 }

  bwExecutionCallBridgeGroup OBJECT-GROUP
    OBJECTS     { bwCallBridgeSuccess, bwCallBridgeSPIndex, 
                  bwCallBridgeSPID, bwCallBridgeSPSuccess, 
                  bwCallBridgeGroupIndex, bwCallBridgeGroupID, 
                  bwCallBridgeGroupSuccess }
    STATUS      current
    DESCRIPTION 
        "This group defines the Call Bridge statistics."
    ::= { bwExecutionMibGroups 107 }

  bwExecutionDirectoryNumberHuntingGroup OBJECT-GROUP
    OBJECTS     { bwDirectoryNumberHuntingIncomingCalls, 
                  bwDirectoryNumberHuntingSPIndex, 
                  bwDirectoryNumberHuntingSPID, 
                  bwDirectoryNumberHuntingSPIncomingCalls, 
                  bwDirectoryNumberHuntingGroupIndex, 
                  bwDirectoryNumberHuntingGroupID, 
                  bwDirectoryNumberHuntingGroupIncomingCalls }
    STATUS      current
    DESCRIPTION 
        "This group defines the Directory Number Hunting statistics."
    ::= { bwExecutionMibGroups 108 }

  bwExecutionAoCGroup OBJECT-GROUP
    OBJECTS     { bwAoCIncompatibleTariff, bwAoCIncompatibleAoC, 
                  bwAoCUnsupportedCostUnit, bwAoCActivation, 
                  bwAoCSPIncompatibleTariff, bwAoCSPIncompatibleAoC, 
                  bwAoCSPActivation, bwAoCGroupIncompatibleTariff, 
                  bwAoCGroupIncompatibleAoC, bwAoCGroupActivation, 
                  bwAoCSPIndex, bwAoCSPID, bwAoCGroupIndex, bwAoCGroupID }
    STATUS      current
    DESCRIPTION 
        "This group defines the AoC statistics."
    ::= { bwExecutionMibGroups 109 }

  bwExecutionTcpStatsGroup OBJECT-GROUP
    OBJECTS     { bwXSTcpServersStatsIndex, bwXSTcpServersName, 
                  bwXSTcpServersNbConnectionsAccepted, 
                  bwXSTcpServersNbConnectionsRefused, 
                  bwXSTcpServersNbConnectionsClosed, 
                  bwXSTcpServersOutgoingQueueSize, 
                  bwXSTcpServersIncomingQueueSize, 
                  bwXSTcpServersNbBytesSentSecure, 
                  bwXSTcpServersNbBytesReceivedSecure, 
                  bwXSTcpServersNbConnectionsInitiated, 
                  bwXSTcpServersNbBytesSent, 
                  bwXSTcpServersNbBytesReceived }
    STATUS      current
    DESCRIPTION 
        "This group defines the statistics for the TCP server."
    ::= { bwExecutionMibGroups 110 }

  bwExecutionConcurrentFrameworkStatsGroup OBJECT-GROUP
    OBJECTS     { bwXSMonitoringExecutorIndex, 
                  bwXSMonitoringExecutorName, 
                  bwXSMonitoringExecutorCurrentPoolSize, 
                  bwXSMonitoringExecutorMaxPoolSize, 
                  bwXSMonitoringExecutorAvgActiveThreads, 
                  bwXSMonitoringExecutorTaskQueueSize, 
                  bwXSMonitoringExecutorNbTasksRun, 
                  bwXSMonitoringExecutorNbWarnings, 
                  bwXSMonitoringExecutorNbErrors, 
                  bwXSMonitoringExecutorLongestTaskMs, 
                  bwXSMonitoringExecutorLongestTaskName }
    STATUS      current
    DESCRIPTION 
        "This group defines the statistics for the Concurrent Framework."
    ::= { bwExecutionMibGroups 111 }

  bwExecutionDnsQueryGroup OBJECT-GROUP
    OBJECTS     { bwDnsQueryTimeMax, bwDnsQueryTimeMaxTimestampMSB, 
                  bwDnsQueryTimeMaxTimestampLSB, bwDnsQueryTimeAvg, 
                  bwDnsStatsQueryIndex, bwDnsStatsQueryType, 
                  bwDnsStatsQueries, bwDnsStatsQueryTimeouts, 
                  bwDnsStatsCallpQueryTimeouts, bwDnsStatsQueryErrorResponses,
                  bwDnsNumberPortabilityMaxThreads, bwDnsNumberPortabilityAvgThreads,
                  bwDnsNumberPortabilityQueryMaxTime, bwDnsNumberPortabilityQueryAvgTime,
                  bwDnsNumberPortabilityNumDroppedRequests }
    STATUS      current
    DESCRIPTION 
        "This group defines the statistics for DNS query."
    ::= { bwExecutionMibGroups 112 }

  bwExecutionMoCountersGroup OBJECT-GROUP
    OBJECTS     { resetAllCounters }
    STATUS      current
    DESCRIPTION 
        "This group defines statistics to perform managed object work for the Execution Server."
    ::= { bwExecutionMibGroups 113 }

  bwExecutionSACGroup OBJECT-GROUP
    OBJECTS { bwSACSessionCreationAttempts, bwSACSessionCreationExceeded, 
              bwSACSPIndex, bwSACSPID, bwSACSPSessionCreationAttempts, 
              bwSACSPSessionCreationExceeded, bwSACGroupIndex, bwSACGroupID, 
              bwSACGroupSessionCreationAttempts, bwSACGroupSessionCreationExceeded, 
              bwSACSessionGroupIndex, bwSACSessionGroupID, 
              bwSACSessionGroupSessionCreationAttempts,
              bwSACSessionGroupSessionCreationExceeded }
    STATUS current
    DESCRIPTION 
        "This group defines the SAC statistics."
    ::= { bwExecutionMibGroups 114 }

  bwExecutionDiameterGroup OBJECT-GROUP
    OBJECTS { bwInternalXSDiameterCommandCode,
              bwInternalXSDiameterRequestsOut,
              bwInternalXSDiameterInformationalAnswersIn,
              bwInternalXSDiameterSuccessAnswersIn,
              bwInternalXSDiameterFailureAnswersIn,
              bwInternalXSDiameterRequestTimeouts,
              bwInternalXSDiameterRequestsIn,
              bwInternalXSDiameterInformationalAnswersOut,
              bwInternalXSDiameterSuccessAnswersOut,
              bwInternalXSDiameterFailureAnswersOut,
              bwExternalXSDiameterCommandCode,
              bwExternalXSDiameterRequestsOut,
              bwExternalXSDiameterInformationalAnswersIn,
              bwExternalXSDiameterSuccessAnswersIn,
              bwExternalXSDiameterFailureAnswersIn,
              bwExternalXSDiameterRequestTimeouts,
              bwExternalXSDiameterRequestsIn,
              bwExternalXSDiameterInformationalAnswersOut,
              bwExternalXSDiameterSuccessAnswersOut,
              bwExternalXSDiameterFailureAnswersOut, 
              bwShRelayInterfaceServerUnreachable }
    STATUS current
    DESCRIPTION 
        "This group defines the Diameter statistics."
    ::= { bwExecutionMibGroups 115 }

  bwVirtualOnNetGroup OBJECT-GROUP
    OBJECTS { bwVirtualOnNetOriginationAttempts,
              bwVirtualOnNetTerminationAttempts,
              bwVirtualOnNetSPIndex, bwVirtualOnNetSPID,
              bwVirtualOnNetSPOriginationAttempts,
              bwVirtualOnNetSPTerminationAttempts,
              bwVirtualOnNetGroupIndex, bwVirtualOnNetGroupID,
              bwVirtualOnNetGroupOriginationAttempts,
              bwVirtualOnNetGroupTerminationAttempts }
    STATUS current
    DESCRIPTION 
        "This group defines the Virtual On Net statistics."
    ::= { bwExecutionMibGroups 116 }

  bwPreAlertingAnnouncementGroup OBJECT-GROUP
    OBJECTS { bwPreAlertingAnnouncementNumAttempts,
              bwPreAlertingAnnouncementSPIndex, bwPreAlertingAnnouncementSPID,
              bwPreAlertingAnnouncementSPNumAttempts,
              bwPreAlertingAnnouncementGroupIndex, bwPreAlertingAnnouncementGroupID,
              bwPreAlertingAnnouncementGroupNumAttempts }
    STATUS current
    DESCRIPTION 
        "This group defines the pre alerting announcement statistics."
    ::= { bwExecutionMibGroups 117 }

  bwLocationCallingRestrictionsGroup OBJECT-GROUP
    OBJECTS { bwLocationCallingRestrictionsOfficeZoneOriginations, bwLocationCallingRestrictionsOfficeZoneTerminations,
              bwLocationCallingRestrictionsPrimaryZoneOriginations, bwLocationCallingRestrictionsPrimaryZoneTerminations,
              bwLocationCallingRestrictionsRoamingOriginations, bwLocationCallingRestrictionsRoamingTerminations,
              bwLocationCallingRestrictionsSPIndex, bwLocationCallingRestrictionsSPID,
              bwLocationCallingRestrictionsSPOfficeZoneOriginations,
              bwLocationCallingRestrictionsSPOfficeZoneTerminations, bwLocationCallingRestrictionsSPPrimaryZoneOriginations,
              bwLocationCallingRestrictionsSPPrimaryZoneTerminations, bwLocationCallingRestrictionsSPRoamingOriginations,
              bwLocationCallingRestrictionsSPRoamingTerminations }
    STATUS current
    DESCRIPTION 
        "This group defines the pre alerting announcement statistics."
    ::= { bwExecutionMibGroups 118 }

  bwRoutePointGroup OBJECT-GROUP
    OBJECTS { bwRoutePointNumInboundCalls, bwRoutePointNumOutboundCalls, bwRoutePointNumSizeOverflow,
              bwRoutePointNumTimeOverflow, bwRoutePointNumBouncedCalls, bwRoutePointNumNightServiceMessage,
              bwRoutePointNumManualNightServiceMessage, bwRoutePointNumHolidayServiceMessage,
              bwRoutePointNumForcedForwardingMessage, bwRoutePointNumOverflowMessage, bwRoutePointNumExternalSystemFailure,
              bwRoutePointNumCallsFailed, bwRoutePointNumWhisperMessage, bwRoutePointNumSilenceMessage,
              bwRoutePointNumBusyMessage, bwRoutePointNumRingbackMessage, bwRoutePointNumMusicMessage,
              bwRoutePointNumTreatmentMessage, bwRoutePointNumSizeOverflow, bwRoutePointSPIndex, 
              bwRoutePointSPID, bwRoutePointSPNumInboundCalls, bwRoutePointSPNumOutboundCalls, bwRoutePointSPNumSizeOverflow,
              bwRoutePointSPNumTimeOverflow, bwRoutePointSPNumBouncedCalls, bwRoutePointSPNumNightServiceMessage, 
              bwRoutePointSPNumManualNightServiceMessage, bwRoutePointSPNumHolidayServiceMessage, 
              bwRoutePointSPNumForcedForwardingMessage, bwRoutePointSPNumOverflowMessage, bwRoutePointSPNumExternalSystemFailure,
              bwRoutePointSPNumCallsFailed, bwRoutePointSPNumWhisperMessage, bwRoutePointSPNumSilenceMessage,
              bwRoutePointSPNumBusyMessage, bwRoutePointSPNumRingbackMessage, bwRoutePointSPNumMusicMessage,
              bwRoutePointSPNumTreatmentMessage, bwRoutePointGroupIndex, bwRoutePointGroupID, bwRoutePointGroupNumInboundCalls,
              bwRoutePointGroupNumOutboundCalls, bwRoutePointGroupNumSizeOverflow, bwRoutePointGroupNumTimeOverflow, 
              bwRoutePointGroupNumBouncedCalls, bwRoutePointGroupNumNightServiceMessage, 
              bwRoutePointGroupNumManualNightServiceMessage, bwRoutePointGroupNumHolidayServiceMessage, 
              bwRoutePointGroupNumForcedForwardingMessage, bwRoutePointGroupNumOverflowMessage, 
              bwRoutePointGroupNumExternalSystemFailure, bwRoutePointGroupNumCallsFailed,
              bwRoutePointGroupNumWhisperMessage, bwRoutePointGroupNumSilenceMessage,
              bwRoutePointGroupNumBusyMessage, bwRoutePointGroupNumRingbackMessage,
              bwRoutePointGroupNumMusicMessage, bwRoutePointGroupNumTreatmentMessage }
    STATUS current
    DESCRIPTION 
        "This group defines the route point statistics."
    ::= { bwExecutionMibGroups 119 }

  bwGroupPagingGroup OBJECT-GROUP
    OBJECTS { bwGroupPagingNumInvocations, bwGroupPagingNumFailures, bwGroupPagingSPIndex,
              bwGroupPagingSPID, bwGroupPagingSPNumInvocations, bwGroupPagingSPNumFailures,
              bwGroupPagingGroupIndex, bwGroupPagingGroupID, bwGroupPagingGroupNumInvocations,
              bwGroupPagingGroupNumFailures  }
    STATUS current
    DESCRIPTION 
        "This group defines the group Paging statistics."
    ::= { bwExecutionMibGroups 120 }

  bwExecutionCallCenterReportingQueueServiceGroup OBJECT-GROUP
    OBJECTS     { 
                  bwCallCenterReportingQueueEventsReported,
                  bwCallCenterReportingQueueEventsIgnored,
                  bwCallCenterReportingQueueEventsFailed,
                  bwCallCenterReportingQueueDatabaseFailures,
                  bwCallCenterReportingQueueDatabaseInserts,
                  bwCallCenterReportingQueueDatabaseUpdates,
                  bwCallCenterReportingQueueDatabaseQueries,
                  bwCallCenterReportingQueueDatabaseDeletes,
                  bwCallCenterReportingQueueEventResets,
                  bwCallCenterReportingQueueEventIndex,
                  bwCallCenterReportingQueueEventName,
                  bwCallCenterReportingQueueEventCount
                }
    STATUS current
    DESCRIPTION 
        "This group defines the Call Center Reporting Queue statistics."
    ::= { bwExecutionMibGroups 121 }

  bwMeetMeConferencingGroup OBJECT-GROUP
    OBJECTS { bwMeetMeNumActiveConferences, bwMeetMeTotalConferences,
              bwMeetMeNumPortsInUse, bwMeetMeTotalParticipants,
              bwMeetMeTotalConferenceDuration, bwMeetMeNumJoinFailureLicensing,
              bwMeetMeNumJoinFailureMaxBridgeCapacity, bwMeetMeNumJoinFailureMediaServerBusy,
              bwMeetMeNumJoinFailureInvalidConferenceId, bwMeetMeNumJoinFailureOthers,
              bwMeetMeNumConferenceCreationFailure, bwMeetMeNumOutdialFailure,
              bwMeetMeSPIndex, bwMeetMeSPID, bwMeetMeSPNumActiveConferences,
              bwMeetMeSPNumPortsInUse, bwMeetMeGroupIndex, bwMeetMeGroupID,
              bwMeetMeGroupNumActiveConferences, bwMeetMeGroupNumPortsInUse }
    STATUS current
    DESCRIPTION 
        "This group defines the Meet Me Conferencing statistics."
    ::= { bwExecutionMibGroups 122 }

  bwMediaCrStatsGroup OBJECT-GROUP
    OBJECTS { bwMediaCrIncomingMessageCount, bwMediaCrOutgoingMessageCount,
              bwMediaCrConnectionIndex, bwMediaCrConnectionAddr, bwMediaCrIncomingMessageCountPerConnection,
              bwMediaCrOutgoingMessageCountPerConnection,
              bwMediaCrConnectionCount, bwMediaCrConnectionState,
              bwMediaCrModifyConferenceFailureCount, bwMediaCrReconnectionCountPerConnection,
              bwMediaCrReconnectionCount, bwMediaCrRecoveredConferencesCount }
    STATUS current
    DESCRIPTION 
        "This group defines the Media Cr Interface statistics."
    ::= { bwExecutionMibGroups 123 }

  bwShortMessageStatisticStatsGroup OBJECT-GROUP
    OBJECTS { bwShortMessageServiceOrigination, bwShortMessageServiceTermination,
              bwShortMessageServiceSPIndex, bwShortMessageServiceSPID,
              bwShortMessageServiceSPOrigination, bwShortMessageServiceSPTermination,
              bwShortMessageGroupIndex, bwShortMessageGroupID,
              bwShortMessageServiceGroupOrigination, bwShortMessageServiceGroupTermination }
    STATUS current
    DESCRIPTION 
        "This group defines the Short Message Service statistics."
    ::= { bwExecutionMibGroups 124 }

  bwMobilityStatisticStatsGroup OBJECT-GROUP
    OBJECTS { bwMobilityMobileOriginationTriggers, bwMobilityMobileTerminationTriggers,
              bwMobilityIMRNOriginations, bwMobilityIMRNTerminations,
              bwMobilityIMRNAllocationFailures, bwMobilityIMRNAllocationTimeOuts,
              bwMobilityOriginationCallDenies, bwMobilityTerminationCallDenies,
              bwMobilityIMRNMaxUsed, bwMobilityIMRNsInUse, bwMobilityIMRNMinHoldTime,
              bwMobilityIMRNMaxHoldTime, bwMobilityIMRNAvgHoldTime,
              bwMobilitySPIndex, bwMobilitySPID, bwMobilitySPOriginationCallDenies,
              bwMobilitySPTerminationCallDenies, bwMobilitySPIMRNAllocationFailures,
              bwMobilitySPIMRNAllocationTimeOuts, bwMobilitySPIMRNOriginations,
              bwMobilitySPIMRNMaxUsed, bwMobilitySPIMRNsInUse,
              bwMobilitySPIMRNMinHoldTime, bwMobilitySPIMRNMaxHoldTime,
              bwMobilitySPIMRNAvgHoldTime, bwMobilitySPCallsAnchored,
              bwMobilitySPCallsNotAnchored, bwMobilityGroupIndex,
              bwMobilityGroupID, bwMobilityGroupOriginationCallDenies, 
              bwMobilityGroupTerminationCallDenies, bwMobilityGroupIMRNAllocationFailures,
              bwMobilityGroupIMRNAllocationTimeOuts, bwMobilityGroupIMRNOriginations,
              bwMobilityGroupIMRNMaxUsed, bwMobilityGroupIMRNsInUse,
              bwMobilityGroupIMRNMinHoldTime, bwMobilityGroupIMRNMaxHoldTime,
              bwMobilityGroupIMRNAvgHoldTime, bwMobilityGroupCallsAnchored,
              bwMobilityGroupCallsNotAnchored }
    STATUS current
    DESCRIPTION 
        "This group defines the Short Message Service statistics."
    ::= { bwExecutionMibGroups 125 }

  bwCallMeNowStatisticStatsGroup OBJECT-GROUP
    OBJECTS { bwCallMeNowNumRequests, bwCallMeNowNumAttempts,
              bwCallMeNowNumSuccess,  bwCallMeNowSPIndex, 
              bwCallMeNowSPID, bwCallMeNowSPNumRequests, 
              bwCallMeNowSPNumAttempts, bwCallMeNowSPNumSuccess,
              bwCallMeNowGroupIndex,  bwCallMeNowGroupID,
              bwCallMeNowGroupNumRequests, bwCallMeNowGroupNumAttempts,
              bwCallMeNowGroupNumSuccess }
    STATUS current
    DESCRIPTION 
        "This group defines the Call Me Now Service statistics."
    ::= { bwExecutionMibGroups 126 }

   bwCallLogStatisticStatsGroup OBJECT-GROUP
     OBJECTS { bwCallLogEventsReported, bwCallLogEventsIgnored,
               bwCallLogEventsFailed, bwCallLogDatabaseInserts,
               bwCallLogDatabaseUpdates, bwCallLogDatabaseQueries, 
               bwCallLogDatabaseDeletes, bwCallLogDatabaseFailures,
               bwCallLogEventResets, bwCallLogEventIndex,
               bwCallLogEventName, bwCallLogEventCount,
               bwCallLogProcessorResets, bwCallLogProcessorIndex,
               bwCallLogProcessorEventCount }
     STATUS current
     DESCRIPTION 
         "This group defines the Call Log statistics."
     ::= { bwExecutionMibGroups 127 }

   bwCallForwardingGroupNotReachableStatisticStatsGroup OBJECT-GROUP
     OBJECTS { bwCFGNRcForward, bwCFGNRcNoForward, bwCFGNRcSPIndex,
               bwCFGNRcSPID, bwCFGNRcSPForward, bwCFGNRcSPNoForward,
               bwCFGNRcGroupIndex, bwCFGNRcGroupID, bwCFGNRcGroupForward,
               bwCFGNRcGroupNoForward }
     STATUS current
     DESCRIPTION 
         "This group defines the Call Forwarding Group Not Reachable."
     ::= { bwExecutionMibGroups 128 }

   bwCallRecordingStatisticStatsGroup OBJECT-GROUP
     OBJECTS { bwCallRecordingAutoRecordings, bwCallRecordingOnDemandRecordings,
               bwCallRecordingOnDemandEnabled, bwCallRecordingPaused,
               bwCallRecordingResumed, bwCallRecordingSPIndex, bwCallRecordingSPID,
               bwCallRecordingSPAutoRecordings, bwCallRecordingSPOnDemandRecordings,
               bwCallRecordingSPOnDemandEnabled, bwCallRecordingSPPaused,
               bwCallRecordingSPResumed, bwCallRecordingGroupPaused,
               bwCallRecordingGroupResumed, bwCallRecordingGroupIndex,
               bwCallRecordingGroupID, bwCallRecordingGroupAutoRecordings, 
               bwCallRecordingGroupOnDemandRecordings, bwCallRecordingGroupOnDemandEnabled,
               bwCallRecordingVoicemailRecording, bwCallRecordingVoicemailRecordingAbandoned,
               bwCallRecordingSPVoicemailRecording, bwCallRecordingSPVoicemailRecordingAbandoned,
               bwCallRecordingGroupVoicemailRecording, bwCallRecordingGroupVoicemailRecordingAbandoned,
               bwCallRecordingVideoRecordings, bwCallRecordingSPVideoRecordings,
               bwCallRecordingGroupVideoRecordings, bwCallRecordingMSReconnected,
               bwCallRecordingSPMSReconnected, bwCallRecordingGroupMSReconnected }
     STATUS current
     DESCRIPTION 
         "This group defines the Call Recording."
     ::= { bwExecutionMibGroups 129 }

   bwFMFMStatisticStatsGroup OBJECT-GROUP
     OBJECTS { bwFMFMCall, bwFMFMCallPush, bwFMFMSPIndex, bwFMFMSPID, 
               bwFMFMSPCall, bwFMFMSPCallPush, bwFMFMGroupIndex, 
               bwFMFMGroupID, bwFMFMGroupCall, bwFMFMGroupCallPush }
     STATUS current
     DESCRIPTION 
         "This group defines the Find Me Follow Me."
     ::= { bwExecutionMibGroups 130 }

   bwGroupNightForwardingStatisticStatsGroup OBJECT-GROUP
     OBJECTS { bwGroupNightForwardingNumInvocations, bwGroupNightForwardingSPIndex,
               bwGroupNightForwardingSPID, bwGroupNightForwardingSPNumInvocations,
               bwGroupNightForwardingGroupIndex, bwGroupNightForwardingGroupID,
               bwGroupNightForwardingGroupNumInvocations }
     STATUS current
     DESCRIPTION 
         "This group defines the Group Night Forwarding."
     ::= { bwExecutionMibGroups 131 }

   bwExecutiveStatisticStatsGroup OBJECT-GROUP
     OBJECTS { bwExecutiveNumCallsFiltered, bwExecutiveSPIndex, bwExecutiveSPID,
               bwExecutiveSPNumCallsFiltered, bwExecutiveGroupIndex,
               bwExecutiveGroupID, bwExecutiveGroupNumCallsFiltered }
     STATUS current
     DESCRIPTION 
         "This group defines the Executive."
     ::= { bwExecutionMibGroups 132 }

   bwFlexibleSeatingStatisticStatsGroup OBJECT-GROUP
     OBJECTS { bwFlexibleSeatingAssociate, bwFlexibleSeatingDisassociate,
               bwFlexibleSeatingTimeout, bwFlexibleSeatingSPIndex,
               bwFlexibleSeatingSPID, bwFlexibleSeatingSPAssociate,
               bwFlexibleSeatingSPDisassociate, bwFlexibleSeatingSPTimeout,
               bwFlexibleSeatingGroupIndex, bwFlexibleSeatingGroupID,
               bwFlexibleSeatingGroupAssociate, bwFlexibleSeatingGroupDisassociate,
               bwFlexibleSeatingGroupTimeout }
     STATUS current
     DESCRIPTION 
         "This group defines the Executive."
     ::= { bwExecutionMibGroups 133 }

   bwNumberPortabilityStatisticStatsGroup OBJECT-GROUP
     OBJECTS { bwNumberPortabilityDatabaseQueries, bwNumberPortabilityDatabaseQueriesForOutboundCalls, 
               bwNumberPortabilityDatabaseQueriesForInboundCalls, bwNumberPortabilityDatabaseResponses, 
               bwNumberPortabilityDatabaseQueriesTimeout, bwNumberPortabilityDatabaseQueriesFailure }
     STATUS current
     DESCRIPTION 
         "This group defines the Number Portability Service."
     ::= { bwExecutionMibGroups 134 }

   bwNumberPortabilityAnncStatisticStatsGroup OBJECT-GROUP
     OBJECTS { bwNumberPortabilityAnncPhoneActivations, bwNumberPortabilityAnncPhoneDeactivations,
               bwNumberPortabilityAnncSPIndex, bwNumberPortabilityAnncSPID,
               bwNumberPortabilityAnncSPPhoneActivations, bwNumberPortabilityAnncSPPhoneDeactivations,
               bwNumberPortabilityAnncGroupIndex, bwNumberPortabilityAnncGroupID,
               bwNumberPortabilityAnncGroupPhoneActivations, bwNumberPortabilityAnncGroupPhoneDeactivations }
     STATUS current
     DESCRIPTION 
         "This group defines the Number Portability Announcement Service."
     ::= { bwExecutionMibGroups 135 }

   bwPersonalAssistantStatisticStatsGroup OBJECT-GROUP
       OBJECTS { bwPersonalAssistantActivations, bwPersonalAssistantSPIndex,
                 bwPersonalAssistantSPID, bwPersonalAssistantSPActivations,
                 bwPersonalAssistantGroupIndex, bwPersonalAssistantGroupID,
                 bwPersonalAssistantGroupActivations }
     STATUS current
     DESCRIPTION 
         "This group defines the Personal Assistant Service."
     ::= { bwExecutionMibGroups 136 }

   bwCollaborateStatisticStatsGroup OBJECT-GROUP
       OBJECTS { bwCollaborateNumActiveMyRooms, bwCollaborateNumActiveInstantRooms,
                 bwCollaborateNumActiveProjectRooms, bwCollaborateNumActiveAudioPorts,
                 bwCollaborateNumActiveVideoPorts, bwCollaborateTotalSessions,
                 bwCollaborateVideoEnabledSessions, bwCollaborateTotalDuration,
                 bwCollaborateNumVideoParticipantsDowngradedToAudio, bwCollaborateNumInvalidRoomIDJoinFailures,
                 bwCollaborateNumSessionCreationFailures, bwCollaborateNumNoResourceJoinFailures,
                 bwCollaborateNumOutDialFailures, bwCollaborateSPIndex, 
                 bwCollaborateSPID, bwCollaborateSPNumActiveMyRooms,
                 bwCollaborateSPNumActiveInstantRooms, bwCollaborateSPNumActiveProjectRooms,
                 bwCollaborateSPNumActiveAudioPorts, bwCollaborateSPNumActiveVideoPorts,
                 bwCollaborateSPTotalSessions, bwCollaborateSPVideoEnabledSessions,
                 bwCollaborateSPTotalDuration, bwCollaborateSPNumVideoParticipantsDowngradedToAudio,
                 bwCollaborateSPNumInvalidRoomIDJoinFailures, bwCollaborateSPNumSessionCreationFailures,
                 bwCollaborateSPNumNoResourceJoinFailures, bwCollaborateSPNumOutDialFailures,
                 bwCollaborateGroupIndex, bwCollaborateGroupID,
                 bwCollaborateGroupNumActiveMyRooms, bwCollaborateGroupNumActiveInstantRooms,
                 bwCollaborateGroupNumActiveProjectRooms, bwCollaborateGroupNumActiveAudioPorts,
                 bwCollaborateGroupNumActiveVideoPorts, bwCollaborateGroupTotalSessions,
                 bwCollaborateGroupVideoEnabledSessions, bwCollaborateGroupTotalDuration,
                 bwCollaborateGroupNumVideoParticipantsDowngradedToAudio, bwCollaborateGroupNumInvalidRoomIDJoinFailures,
                 bwCollaborateGroupNumSessionCreationFailures, bwCollaborateGroupNumNoResourceJoinFailures,
                 bwCollaborateGroupNumOutDialFailures
               }
     STATUS current
     DESCRIPTION 
         "This group defines the Collaborate Service."
     ::= { bwExecutionMibGroups 137 }
 
   bwCallForwardAlwaysSecondaryStatisticStatsGroup OBJECT-GROUP
       OBJECTS { bwCFASNumForwarded, bwCallForwardingAlwaysSecondarySPIndex,
                 bwCallForwardingAlwaysSecondarySPID, bwCFASSPNumForwarded,
                 bwCallForwardingAlwaysSecondaryGroupIndex, bwCallForwardingAlwaysSecondaryGroupID,
                 bwCFASGroupNumForwarded }
     STATUS current
     DESCRIPTION 
         "This group defines the Call Forward Always Secondary Service."
     ::= { bwExecutionMibGroups 138 }

  bwExecutionBasicCompliance MODULE-COMPLIANCE
    STATUS      current
    DESCRIPTION 
        "BroadWorks Execution MIB compliance"

    MODULE      -- this module

        MANDATORY-GROUPS        { bwExecutionMgcpGroup, 
                  bwExecutionImsGroup, bwExecutionCapGroup, 
                  bwExecutionSmdiGroup, bwExecutionMediaResourceGroup, 
                  bwExecutionWholeSalesGroup, 
                  bwExecutionRealTimeAccntGroup, 
                  bwExecutionExtCallLogsGroup, bwExecutionXsBcctGroup, 
                  bwExecutionCallpGroup, bwExecutionSmtpGroup, 
                  bwExecutionSipGroup, bwExecutionAccntCodeServiceGroup, 
                  bwExecutionAnonymousCallRejectionServiceGroup, 
                  bwExecutionAuthenticationServiceGroup, 
                  bwExecutionAutoAttendantServiceGroup, 
                  bwExecutionCallCapacityServiceGroup, 
                  bwExecutionCFAlwaysServiceGroup, 
                  bwExecutionCFBusyServiceGroup, 
                  bwExecutionCFNoAnswerServiceGroup, 
                  bwExecutionCallNotifyServiceGroup, 
                  bwExecutionCallParkServiceGroup, 
                  bwExecutionCallPickupServiceGroup, 
                  bwExecutionCallReturnServiceGroup, 
                  bwExecutionCompilotCallMgrServiceGroup, 
                  bwExecutionDoNotDisturbServiceGroup, 
                  bwExecutionFlashCallXferServiceGroup, 
                  bwExecutionFlashCallWaitingServiceGroup, 
                  bwExecutionFlashConsultationServiceGroup, 
                  bwExecutionFlash3wcServiceGroup, 
                  bwExecutionHuntGroupServiceGroup, 
                  bwExecutionIcpServiceGroup, 
                  bwExecutionIpPhoneServiceGroup, 
                  bwExecutionLastNumberRedialServiceGroup, 
                  bwExecutionOcpServiceGroup, 
                  bwExecutionPriorityAlertServiceGroup, 
                  bwExecutionSelectiveCallAcceptanceServiceGroup, 
                  bwExecutionSelectiveCallForwardServiceGroup, 
                  bwExecutionSelectiveCallRejectionServiceGroup, 
                  bwExecutionSimRingServiceGroup, 
                  bwExecutionVoiceMessagingServiceGroup, 
                  bwExecutionSeriesCompletionServiceGroup, 
                  bwExecutionInterceptServiceGroup, 
                  bwExecutionInstantConferencingServiceGroup, 
                  bwExecutionCallingLineIdBlockingServiceGroup, 
                  bwExecutionSessionAuditServiceGroup, 
                  bwExecutionWindowsMessagingServiceGroup, 
                  bwExecutionCalWaitingServiceGroup, 
                  bwExecutionAlternateNumberServiceGroup, 
                  bwExecutionCustomerOriginatedTraceServiceGroup, 
                  bwExecutionSpeedDialing8ServiceGroup, 
                  bwExecutionMusicOnHoldServiceGroup, 
                  bwExecutionCallingNameQueriesServiceGroup, 
                  bwExecutionThirdPartyMWIControlServiceGroup,
                  bwExecutionCallCenterServiceGroup, 
                  bwExecutionCallForwardGroupNoAnswerServiceGroup, 
                  bwExecutionSpeedDialing100ServiceGroup, 
                  bwExecutionThirdPartyVoiceMailServiceGroup, 
                  bwExecutionDirectedCallPickupServiceGroup, 
                  bwExecutionFlashCallHoldServiceGroup, 
                  bwExecutionEmergencyZoneServiceGroup, 
                  bwExecutionDirectedCallPickupWithBargeInServiceGroup, 
                  bwExecutionAutomaticCallBackServiceGroup, 
                  bwExecutionRingTimeoutServiceGroup, 
                  bwExecutionSequentialRingServiceGroup, 
                  bwExecutionVideoAddOnServiceGroup, 
                  bwExecutionMaliciousCallTraceServiceGroup, 
                  bwExecutionPushToTalkServiceGroup, 
                  bwExecutionHotelingServiceGroup, 
                  bwExecutionPreferredCarrierServiceGroup, 
                  bwExecutionFamilySimRingServiceGroup, 
                  bwExecutionDiversionInhibitorServiceGroup, 
                  bwExecutionInstantGroupCallServiceGroup, 
                  bwExecutionAutomaticHoldAndRetrieveServiceGroup, 
                  bwExecutionBusinessTrunkGroupServiceGroup, 
                  bwExecutionCustomRingbackServiceGroup, 
                  bwExecutionMssGroup, bwExecutionNrsGroup, 
                  bwExecutionXsPersistencyGroup, 
                  bwExecutionProtocolMonitorGroup, 
                  bwExecutionSystemStatsGroup, 
                  bwExecutionQueueStatsGroup, 
                  bwExecutionOverloadControlStatsGroup, 
                  bwExecutionRedundancyStatsGroup, 
                  bwExecutionMoCountersGroup, 
                  bwExecutionPhysicalLocationServiceGroup, 
                  bwExecutionFaxMessagingServiceGroup, 
                  bwExecutionTcpStatsGroup, 
                  bwExecutionConcurrentFrameworkStatsGroup, 
                  bwExecutionExtEmergencyRtgStatsGroup, 
                  bwExecutionTwoStageDialingServiceGroup, 
                  bwExecutionSoapGroup, 
                  bwExecutionCallForwardingNotReachableGroup, 
                  bwExecutionMWIDeliveryToMobileGroup, 
                  bwExecutionExternalCustomRingbackGroup, 
                  bwExecutionInCallServiceActivationGroup, 
                  bwExecutionCongestionManagementGroup, 
                  bwExecutionDnsQueryGroup, 
                  bwExecutionExpensiveCallNotificationGroup, 
                  bwExecutionLocationControlGroup, 
                  bwExecutionCallRetrieveGroup, 
                  bwExecutionBroadworksAnywhereGroup, 
                  bwExecutionZoneCallingRestrictionsGroup, 
                  bwExecutionOfflineChargingGroup, bwExecutionSmppGroup, 
                  bwExecutionOcicStatsGroup, 
                  bwExecutionCommunicationBarringGroup, 
                  bwExecutionOnlineChargingStatsGroup, 
                  bwExecutionCallBridgeGroup, 
                  bwExecutionDirectoryNumberHuntingGroup, 
                  bwExecutionAoCGroup,
                  bwExecutionSACGroup,
                  bwExecutionDiameterGroup,
                  bwVirtualOnNetGroup,
                  bwPreAlertingAnnouncementGroup,
                  bwLocationCallingRestrictionsGroup, bwRoutePointGroup,
                  bwGroupPagingGroup, bwExecutionCallCenterReportingQueueServiceGroup,
                  bwMeetMeConferencingGroup, bwMediaCrStatsGroup,
                  bwShortMessageStatisticStatsGroup, bwMobilityStatisticStatsGroup,
                  bwCallMeNowStatisticStatsGroup, bwCallLogStatisticStatsGroup, 
                  bwCallForwardingGroupNotReachableStatisticStatsGroup,
                  bwCallRecordingStatisticStatsGroup, bwFMFMStatisticStatsGroup,
                  bwGroupNightForwardingStatisticStatsGroup,
                  bwExecutiveStatisticStatsGroup, bwFlexibleSeatingStatisticStatsGroup,
                  bwNumberPortabilityStatisticStatsGroup, bwNumberPortabilityAnncStatisticStatsGroup,
                  bwPersonalAssistantStatisticStatsGroup, bwCollaborateStatisticStatsGroup,
                  bwCallForwardAlwaysSecondaryStatisticStatsGroup }

    ::= { bwExecutionMibCompliancy 1 }
END

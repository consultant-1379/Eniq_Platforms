--===============================================================
-- File Name : BW-ECLRepos.mib
-- Author    : BroadSoft Inc.
-- Copyright 2000-2014, BroadSoft, Inc. All rights reserved. 
-- Proprietary Property of BroadSoft, Inc. Gaithersburg, MD.
--===============================================================

BW-ECLRepos DEFINITIONS ::= BEGIN
    IMPORTS
      DisplayString 
        FROM SNMPv2-TC
      MODULE-COMPLIANCE, OBJECT-GROUP          
        FROM SNMPv2-CONF
      enterprises, MODULE-IDENTITY, OBJECT-TYPE, Gauge32, Counter32, Unsigned32
        FROM SNMPv2-SMI;

  broadsoft MODULE-IDENTITY
    LAST-UPDATED  "201404250000Z"
    ORGANIZATION  "Broadsoft, Inc"
    CONTACT-INFO  "Broadsoft, Inc.
9737 Washingtonian Blvd
Suite 350
Gaithersburg , MD 20878
Tel: +1-301-977-9440"
    DESCRIPTION
      "This is the MIB for the ECL Reporting Repository application."
    REVISION    "201404250000Z"
      DESCRIPTION     "Creation."
    ::= { enterprises 6431 }

  broadworks OBJECT IDENTIFIER
    ::= { broadsoft 1 }

  eclRepos OBJECT IDENTIFIER
    ::= { broadworks 41 }

  replication OBJECT IDENTIFIER
    ::= { eclRepos 1 }

  bwECLReposMibConformance OBJECT IDENTIFIER
    ::= { eclRepos 1000 }

-- ECL Repos Replication ::  ...............................

  bwECLReposReplicationStatsTable OBJECT-TYPE
    SYNTAX      SEQUENCE OF BwECLReposReplicationStatsEntry
    MAX-ACCESS  not-accessible
    STATUS      current
    DESCRIPTION
        ""
-- @feature:206184              
    ::= { replication 1 }
  
  bwECLReposReplicationStatsEntry OBJECT-TYPE
      SYNTAX      BwECLReposReplicationStatsEntry
      MAX-ACCESS  not-accessible
      STATUS      current
      DESCRIPTION
          "An entry containing statistics information applicable to a particular replication entry."
      INDEX   { bwECLReposReplicationStatsIndex }
-- @feature:206184            
    ::= { bwECLReposReplicationStatsTable 1 }
    
  BwECLReposReplicationStatsEntry ::= SEQUENCE {
    bwECLReposReplicationStatsIndex   Unsigned32,
    bwECLReposReplicationPeer         DisplayString,
    bwECLReposReplicationRxSuccessful Counter32,
    bwECLReposReplicationRxFailed     Counter32,
    bwECLReposReplicationTxSuccessful Counter32,
    bwECLReposReplicationTxFailed     Counter32
  }
  
   bwECLReposReplicationStatsIndex OBJECT-TYPE
     SYNTAX      Unsigned32
     MAX-ACCESS  read-only
     STATUS      current
     DESCRIPTION 
         "This integer represents a replication peer index in the table."
-- @feature:206184               
   ::= { bwECLReposReplicationStatsEntry 1 }
   
   bwECLReposReplicationPeer OBJECT-TYPE
     SYNTAX      DisplayString
     MAX-ACCESS  read-only
     STATUS      current
     DESCRIPTION 
         "This is the peer identifier."
-- @feature:206184               
   ::= { bwECLReposReplicationStatsEntry 2 }
   
   bwECLReposReplicationRxSuccessful OBJECT-TYPE
      SYNTAX      Counter32
      MAX-ACCESS  read-write
      STATUS      current
      DESCRIPTION 
          "This is the number of successful replication requests."
-- @feature:206184                
   ::= { bwECLReposReplicationStatsEntry 3 }
   
   bwECLReposReplicationRxFailed OBJECT-TYPE
      SYNTAX      Counter32
      MAX-ACCESS  read-write
      STATUS      current
      DESCRIPTION 
          "This is the number of failed replication requests."
-- @feature:206184                
   ::= { bwECLReposReplicationStatsEntry 4 }
   
   bwECLReposReplicationTxSuccessful OBJECT-TYPE
      SYNTAX      Counter32
      MAX-ACCESS  read-write
      STATUS      current
      DESCRIPTION 
          "This is the number of successful replication attempts."
-- @feature:206184                
   ::= { bwECLReposReplicationStatsEntry 5 }

   bwECLReposReplicationTxFailed OBJECT-TYPE
      SYNTAX      Counter32
      MAX-ACCESS  read-write
      STATUS      current
      DESCRIPTION 
          "This is the number of failed replication attempts."
-- @feature:206184                
   ::= { bwECLReposReplicationStatsEntry 6 }

-- BroadWorks ECL Repos MIB Conformance Definition  ...........................................

  bwECLReposMibGroups     OBJECT IDENTIFIER ::= { bwECLReposMibConformance 1 }
  bwECLReposMibCompliancy OBJECT IDENTIFIER ::= { bwECLReposMibConformance 2 }

  bwECLReposReplicationStatsGroup OBJECT-GROUP
    OBJECTS { bwECLReposReplicationStatsIndex, bwECLReposReplicationPeer,
              bwECLReposReplicationRxSuccessful, bwECLReposReplicationRxFailed,
              bwECLReposReplicationTxSuccessful, bwECLReposReplicationTxFailed }
  STATUS  current
  DESCRIPTION
     "This group defines statistics for the ECL Repos."
  ::= { bwECLReposMibGroups 1 }

  bwECLReposBasicCompliance MODULE-COMPLIANCE
    STATUS      current
    DESCRIPTION 
        "BroadWorks ECL Repos MIB compliance"
    MODULE
        MANDATORY-GROUPS        { bwECLReposReplicationStatsGroup }
    ::= { bwECLReposMibCompliancy 1 }

END

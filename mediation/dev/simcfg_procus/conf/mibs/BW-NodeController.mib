--===============================================================
-- File Name : BW-NodeController.mib
-- Author    : BroadSoft Inc.
-- Copyright 2000-2014, BroadSoft, Inc. All rights reserved. 
-- Proprietary Property of BroadSoft, Inc. Gaithersburg, MD.
--===============================================================

BW-NodeController DEFINITIONS ::= BEGIN
  IMPORTS
    DisplayString, DateAndTime, TimeStamp
      FROM SNMPv2-TC
    MODULE-COMPLIANCE, OBJECT-GROUP          
      FROM SNMPv2-CONF
    enterprises, MODULE-IDENTITY, OBJECT-TYPE, Gauge32, Counter32, Integer32, Unsigned32
      FROM SNMPv2-SMI;
  broadsoft MODULE-IDENTITY
    LAST-UPDATED  "201409100000Z"
    ORGANIZATION  "Broadsoft, Inc"
    CONTACT-INFO  "Broadsoft, Inc
220 Perry Parkway
Gaithersburg, MD  20877
301-977-9440"
    DESCRIPTION
      "This is the MIB for the BroadWorks NodeContrller application."
      
    REVISION    "201409100000Z"
      DESCRIPTION     "Creation."
    ::= { enterprises 6431 }

  broadworks OBJECT IDENTIFIER
    ::= { broadsoft 1 }

  nodeController OBJECT IDENTIFIER
    ::= { broadworks 47 }  

-- Reserved for future
--  nodeStats OBJECT IDENTIFIER
--    ::= { nodeController 1 }  

  executors OBJECT IDENTIFIER
    ::= { nodeController 2 }  

  ssh OBJECT IDENTIFIER
    ::= { nodeController 3 }  

  bwNodeControllerMibConformance OBJECT IDENTIFIER
    ::= { nodeController 1000 }

-- Executors Counters  ...........................................

bwNCExecutorReset OBJECT-TYPE
    SYNTAX           Counter32
    MAX-ACCESS       read-write
    STATUS           current
    DESCRIPTION
          "When set to a value other than '0', all statistics stored under executorTable are reset to '0'."
-- @feature:217550
      ::= { executors 1 }

  bwNCExecutorTable  OBJECT-TYPE
    SYNTAX  SEQUENCE  OF  BwNCExecutorTableEntry
    MAX-ACCESS  not-accessible
    STATUS      current
    DESCRIPTION	
      "This table exposes the NodeController executor statistics."
      ::=  {  executors  2 }

  bwNCExecutorTableEntry  OBJECT-TYPE
    SYNTAX      BwNCExecutorTableEntry
    MAX-ACCESS  not-accessible
    STATUS      current
    DESCRIPTION	
      "This row contains information about a NodeController executor."
    INDEX       {  bwNCExecutorIndex  }
      ::=  { bwNCExecutorTable 1 }

  BwNCExecutorTableEntry  ::=  SEQUENCE {
    bwNCExecutorIndex                             Unsigned32,
    bwNCExecutorName                              DisplayString,
    bwNCExecutorQueueCapacity                     Gauge32,
    bwNCExecutorQueueSize                         Gauge32,
    bwNCExecutorQueueWaitingTimeAvg               Gauge32,
    bwNCExecutorQueueWaitingTimeMin               Gauge32,
    bwNCExecutorQueueWaitingTimeMax               Gauge32,
    bwNCExecutorQueueWaitingTimeMaxTimestamp      DateAndTime,
    bwNCExecutorMinPoolSize                       Gauge32,
    bwNCExecutorMaxPoolSize                       Gauge32,
    bwNCExecutorThreadsBusy                       Gauge32,
    bwNCExecutorCompletedTaskCount                Counter32,
    bwNCExecutorThreadsAlive                      Gauge32,
    bwNCExecutorThreadsAliveMax                   Gauge32,
    bwNCExecutorTaskProcessingTimeAvg             Gauge32,
    bwNCExecutorTaskProcessingTimeMin             Gauge32,
    bwNCExecutorTaskProcessingTimeMax             Gauge32,
    bwNCExecutorTaskProcessingTimeMaxTimestamp    DateAndTime
    }

  bwNCExecutorIndex OBJECT-TYPE
    SYNTAX           Unsigned32
    MAX-ACCESS       read-only
    STATUS           current
    DESCRIPTION
          "This integer represents an index to a given executor."
-- @feature:217550
      ::= { bwNCExecutorTableEntry 1 }

  bwNCExecutorName OBJECT-TYPE
    SYNTAX           DisplayString
    MAX-ACCESS       read-only
    STATUS           current
    DESCRIPTION
          "This is the name of this executor."
-- @feature:217550
      ::= { bwNCExecutorTableEntry 2 }

  bwNCExecutorQueueCapacity OBJECT-TYPE
    SYNTAX           Gauge32
    MAX-ACCESS       read-only
    STATUS           current
    DESCRIPTION
          "This is the initial capacity of the executor queue."
-- @feature:217550
      ::= { bwNCExecutorTableEntry 3 }

  bwNCExecutorQueueSize OBJECT-TYPE
    SYNTAX           Gauge32
    MAX-ACCESS       read-only
    STATUS           current
    DESCRIPTION
          "This is the current size of the executor queue."
-- @feature:217550
      ::= { bwNCExecutorTableEntry 4 }

  bwNCExecutorQueueWaitingTimeAvg OBJECT-TYPE
    SYNTAX           Gauge32
    MAX-ACCESS       read-only
    STATUS           current
    DESCRIPTION
          "This is the average time spent waiting in the executor queue since the last reset."
-- @feature:217550
      ::= { bwNCExecutorTableEntry 5 }

  bwNCExecutorQueueWaitingTimeMin OBJECT-TYPE
    SYNTAX           Gauge32
    MAX-ACCESS       read-only
    STATUS           current
    DESCRIPTION
          "This is the minimum amount of time spent waiting in the executor queue since the last reset."
-- @feature:217550
      ::= { bwNCExecutorTableEntry 6 }

  bwNCExecutorQueueWaitingTimeMax OBJECT-TYPE
    SYNTAX           Gauge32
    MAX-ACCESS       read-only
    STATUS           current
    DESCRIPTION
          "This is the maximum amount of time spent waiting in the executor queue since the last reset."
-- @feature:217550
      ::= { bwNCExecutorTableEntry 7 }

  bwNCExecutorQueueWaitingTimeMaxTimestamp OBJECT-TYPE
    SYNTAX           DateAndTime
    MAX-ACCESS       read-only
    STATUS           current
    DESCRIPTION
          "This is the time stamp indicating when executorQueueWaitingTime was obtained."
-- @feature:217550
      ::= { bwNCExecutorTableEntry 8 }

  bwNCExecutorMinPoolSize OBJECT-TYPE
    SYNTAX           Gauge32
    MAX-ACCESS       read-only
    STATUS           current
    DESCRIPTION
          "This is the number of threads to keep in the pool, even if they are idle."
-- @feature:217550
      ::= { bwNCExecutorTableEntry 9 }

  bwNCExecutorMaxPoolSize OBJECT-TYPE
    SYNTAX           Gauge32
    MAX-ACCESS       read-only
    STATUS       current
    DESCRIPTION
          "This is the maximum number of threads to allow in the pool."
-- @feature:217550
      ::= { bwNCExecutorTableEntry 10 }

  bwNCExecutorThreadsBusy OBJECT-TYPE
    SYNTAX           Gauge32
    MAX-ACCESS       read-only
    STATUS           current
    DESCRIPTION
          "This is the approximate number of threads that are actively executing tasks."
-- @feature:217550
      ::= { bwNCExecutorTableEntry 11 }

  bwNCExecutorCompletedTaskCount OBJECT-TYPE
    SYNTAX           Counter32
    MAX-ACCESS       read-only
    STATUS           current
    DESCRIPTION
          "This is the approximate total number of tasks that have completed execution.  Because the states of tasks and threads may change dynamically during computation, the returned value is only an approximation; however, it does not ever decrease across successive calls."
-- @feature:217550
      ::= { bwNCExecutorTableEntry 12 }

  bwNCExecutorThreadsAlive OBJECT-TYPE
    SYNTAX           Gauge32
    MAX-ACCESS       read-only
    STATUS       current
    DESCRIPTION
          "This is the current number of threads instantiated."
-- @feature:217550
      ::= { bwNCExecutorTableEntry 13 }

  bwNCExecutorThreadsAliveMax OBJECT-TYPE
    SYNTAX           Gauge32
    MAX-ACCESS       read-only
    STATUS       current
    DESCRIPTION
          "This is the maximum number of threads that can be allocated at the same time."
-- @feature:217550
      ::= { bwNCExecutorTableEntry 14 }

  bwNCExecutorTaskProcessingTimeAvg OBJECT-TYPE
    SYNTAX           Gauge32
    MAX-ACCESS       read-only
    STATUS           current
    DESCRIPTION
          "This is the average processing time spent by this executor."
-- @feature:217550
      ::= { bwNCExecutorTableEntry 15 }

  bwNCExecutorTaskProcessingTimeMin OBJECT-TYPE
    SYNTAX           Gauge32
    MAX-ACCESS       read-only
    STATUS           current
    DESCRIPTION
          "This is the minimum amount of processing time spent by this executor."
-- @feature:217550
      ::= { bwNCExecutorTableEntry 16 }

  bwNCExecutorTaskProcessingTimeMax OBJECT-TYPE
    SYNTAX           Gauge32
    MAX-ACCESS       read-only
    STATUS           current
    DESCRIPTION
          "This is the maximum amount of processing time spent by this executor."
-- @feature:217550
      ::= { bwNCExecutorTableEntry 17 }

  bwNCExecutorTaskProcessingTimeMaxTimestamp OBJECT-TYPE
    SYNTAX           DateAndTime
    MAX-ACCESS       read-only
    STATUS           current
    DESCRIPTION
          "This is the time stamp indicating when taskProcessingTimeMax was obtained."
-- @feature:217550
      ::= { bwNCExecutorTableEntry 18 }

-- SSH Counters  ...........................................

  bwNCSshResetStats OBJECT-TYPE
    SYNTAX           Counter32
    MAX-ACCESS       read-write
    STATUS           current
    DESCRIPTION
          "When set to a value other than '0', all statistics stored under SshSubsystem  are reset to '0'."
-- @feature:217550
      ::= { ssh 1 }

  bwNCSshSessionConnectionRequests OBJECT-TYPE
    SYNTAX           Counter32
    MAX-ACCESS       read-only
    STATUS           current
    DESCRIPTION
          "Total number of outbound SSH connection requests."
-- @feature:217550
      ::= { ssh 2 }

  bwNCSshSessionConnectedEvents OBJECT-TYPE
    SYNTAX           Counter32
    MAX-ACCESS       read-only
    STATUS           current
    DESCRIPTION
          "Total number of outbound SSH connection events."
-- @feature:217550
      ::= { ssh 3 }

  bwNCSshSessionDisconnectedEvents OBJECT-TYPE
    SYNTAX           Counter32
    MAX-ACCESS       read-only
    STATUS           current
    DESCRIPTION
          "Total number of outbound SSH connection termination events."
-- @feature:217550
      ::= { ssh 4 }

  bwNCSshSessionAuthenticationFailureEvents OBJECT-TYPE
    SYNTAX           Counter32
    MAX-ACCESS       read-only
    STATUS           current
    DESCRIPTION
          "Total number of authentication failures detected by the internal SSH client."
-- @feature:217550
      ::= { ssh 5 }

  bwNCSshSessionConnectionFailureEvents OBJECT-TYPE
    SYNTAX           Counter32
    MAX-ACCESS       read-only
    STATUS           current
    DESCRIPTION
          "Total number of connection failures detected by the internal SSH client."
-- @feature:217550
      ::= { ssh 6 }

  bwNCSshChannelOpenRequestEvents OBJECT-TYPE
    SYNTAX           Counter32
    MAX-ACCESS       read-only
    STATUS           current
    DESCRIPTION
          "Total number of SSH channel open attempts."
-- @feature:217550
      ::= { ssh 7 }

  bwNCSshChannelOpenedEvents OBJECT-TYPE
    SYNTAX           Counter32
    MAX-ACCESS       read-only
    STATUS           current
    DESCRIPTION
          "Total number of SSH channels successfully opened."
-- @feature:217550
      ::= { ssh 8 }

  bwNCSshChannelOpenFailedEvents OBJECT-TYPE
    SYNTAX           Counter32
    MAX-ACCESS       read-only
    STATUS           current
    DESCRIPTION
          "Total number of failures to open an SSH channel."
-- @feature:217550
      ::= { ssh 9 }

  bwNCSshChannelInputAvailableEvents OBJECT-TYPE
    SYNTAX           Counter32
    MAX-ACCESS       read-only
    STATUS           current
    DESCRIPTION
          "Total number of times the SSH client was notified that input was available for I/O read operation."
-- @feature:217550
      ::= { ssh 10 }

  bwNCSshChannelOutputReadyEvents OBJECT-TYPE
    SYNTAX           Counter32
    MAX-ACCESS       read-only
    STATUS           current
    DESCRIPTION
          "Total number of times the SSH client was notified that it could issue an I/O write operation."
-- @feature:217550
      ::= { ssh 11 }

  bwNCSshChannelDisconnectedEvents OBJECT-TYPE
    SYNTAX           Counter32
    MAX-ACCESS       read-only
    STATUS           current
    DESCRIPTION
          "Total number of SSH channels disconnected."
-- @feature:217550
      ::= { ssh 12 }

  bwNCSshCommandStartedEvents OBJECT-TYPE
    SYNTAX           Counter32
    MAX-ACCESS       read-only
    STATUS           current
    DESCRIPTION
          "Total number of SSH commands started."
-- @feature:217550
      ::= { ssh 13 }

  bwNCSshCommandFailedEvents OBJECT-TYPE
    SYNTAX           Counter32
    MAX-ACCESS       read-only
    STATUS           current
    DESCRIPTION
          "Total number of failed SSH commands."
-- @feature:217550
      ::= { ssh 14 }

  bwNCSshCommandTimeoutEvents OBJECT-TYPE
    SYNTAX           Counter32
    MAX-ACCESS       read-only
    STATUS           current
    DESCRIPTION
          "Total number of SSH command time-outs."
-- @feature:217550
      ::= { ssh 15 }

  bwNCSshCommandCompletedEvents OBJECT-TYPE
    SYNTAX           Counter32
    MAX-ACCESS       read-only
    STATUS           current
    DESCRIPTION
          "Total number of SSH commands that were completed."
-- @feature:217550
      ::= { ssh 16 }

  bwNCSshCmdAvgConnectionTime OBJECT-TYPE
    SYNTAX           Gauge32
    MAX-ACCESS       read-only
    STATUS           current
    DESCRIPTION
          "Average time spent waiting for an SSH connection to complete."
-- @feature:217550
      ::= { ssh 17 }

  bwNCSshCmdMinConnectionTime OBJECT-TYPE
    SYNTAX           Gauge32
    MAX-ACCESS       read-only
    STATUS           current
    DESCRIPTION
          "Minimum time spent waiting for an SSH connection to complete."
-- @feature:217550
      ::= { ssh 18 }

  bwNCSshCmdMaxConnectionTime OBJECT-TYPE
    SYNTAX           Gauge32
    MAX-ACCESS       read-only
    STATUS           current
    DESCRIPTION
          "Maximum time spent waiting for an SSH connection to complete."
-- @feature:217550
      ::= { ssh 19 }

  bwNCSshCmdTotalConnectionTime OBJECT-TYPE
    SYNTAX           Gauge32
    MAX-ACCESS       read-only
    STATUS           current
    DESCRIPTION
          "Total time spent waiting for an SSH connection to complete."
-- @feature:217550
      ::= { ssh 20 }

  bwNCSshCmdAvgProcessingTime OBJECT-TYPE
    SYNTAX           Gauge32
    MAX-ACCESS       read-only
    STATUS           current
    DESCRIPTION
          "Average time spent waiting for an SSH process to complete."
-- @feature:217550
      ::= { ssh 21 }

  bwNCSshCmdMinProcessingTime OBJECT-TYPE
    SYNTAX           Gauge32
    MAX-ACCESS       read-only
    STATUS           current
    DESCRIPTION
          "Minimum time spent waiting for an SSH process to complete."
-- @feature:217550
      ::= { ssh 22 }

  bwNCSshCmdMaxProcessingTime OBJECT-TYPE
    SYNTAX           Gauge32
    MAX-ACCESS       read-only
    STATUS           current
    DESCRIPTION
          "Maximum time spent waiting for an SSH process to complete."
-- @feature:217550
      ::= { ssh 23 }

  bwNCSshCmdTotalProcessingTime OBJECT-TYPE
    SYNTAX           Gauge32
    MAX-ACCESS       read-only
    STATUS           current
    DESCRIPTION
          "Maximum time spent waiting for an SSH process to complete."
-- @feature:217550
      ::= { ssh 24 }

-- BroadWorks UVS MIB Conformance Definition  ......................................

  bwNodeControllerMibGroups OBJECT IDENTIFIER 
    ::= { bwNodeControllerMibConformance 1 }

  bwNodeControllerMibCompliancy OBJECT IDENTIFIER
    ::= { bwNodeControllerMibConformance 2 }

  bwNodeControllerExecutorStatsGroup OBJECT-GROUP
      OBJECTS { bwNCExecutorReset, bwNCExecutorIndex, bwNCExecutorName,
                bwNCExecutorQueueCapacity, bwNCExecutorQueueSize,
                bwNCExecutorQueueWaitingTimeAvg, bwNCExecutorQueueWaitingTimeMin,
                bwNCExecutorQueueWaitingTimeMax, bwNCExecutorQueueWaitingTimeMaxTimestamp,
                bwNCExecutorMinPoolSize,
                bwNCExecutorMaxPoolSize, bwNCExecutorThreadsBusy,
                bwNCExecutorCompletedTaskCount, bwNCExecutorThreadsAlive,
                bwNCExecutorThreadsAliveMax, bwNCExecutorTaskProcessingTimeAvg,
                bwNCExecutorTaskProcessingTimeMin, bwNCExecutorTaskProcessingTimeMax,
                bwNCExecutorTaskProcessingTimeMaxTimestamp
               }
    STATUS current
    DESCRIPTION 
        "This group defines the NodeController executor statistics."
    ::= { bwNodeControllerMibGroups 1 }

  bwNodeControllerSshStatsGroup OBJECT-GROUP
      OBJECTS { bwNCSshResetStats, bwNCSshSessionConnectionRequests,
                bwNCSshSessionConnectedEvents, bwNCSshSessionDisconnectedEvents,
                bwNCSshSessionAuthenticationFailureEvents, bwNCSshSessionConnectionFailureEvents,
                bwNCSshChannelOpenRequestEvents, bwNCSshChannelOpenedEvents,
                bwNCSshChannelOpenFailedEvents, bwNCSshChannelInputAvailableEvents,
                bwNCSshChannelOutputReadyEvents, bwNCSshChannelDisconnectedEvents,
                bwNCSshCommandStartedEvents, bwNCSshCommandFailedEvents,
                bwNCSshCommandTimeoutEvents, bwNCSshCommandCompletedEvents,
                bwNCSshCmdAvgConnectionTime, bwNCSshCmdMinConnectionTime,
                bwNCSshCmdMaxConnectionTime, bwNCSshCmdTotalConnectionTime,
                bwNCSshCmdAvgProcessingTime, bwNCSshCmdMinProcessingTime,
                bwNCSshCmdMaxProcessingTime, bwNCSshCmdTotalProcessingTime
               }
    STATUS current
    DESCRIPTION 
        "This group defines the NodeController SSH statistics."
    ::= { bwNodeControllerMibGroups 2 }

  bwNodeControllerBasicCompliance MODULE-COMPLIANCE
    STATUS      current
    DESCRIPTION 
        "BroadWorks Node Controller MIB compliance"

    MODULE

        MANDATORY-GROUPS        
        { bwNodeControllerExecutorStatsGroup,
          bwNodeControllerSshStatsGroup}

    ::= { bwNodeControllerMibCompliancy 1 }

END

-- File Name : BW-DMSFault.mib
BW-DMSFault DEFINITIONS ::= BEGIN
  IMPORTS
    NOTIFICATION-TYPE, MODULE-IDENTITY
      FROM SNMPv2-SMI
    common, identifier, timeStamp, alarmName, systemName, severity, alarmState, component, subcomponent, problemText, recommendedActionsText, npWebAppName, npErrorMessage
      FROM BroadworksFault;

  systemFaults MODULE-IDENTITY
    LAST-UPDATED  "201310080000Z"
    ORGANIZATION  "Broadsoft, Inc"
    CONTACT-INFO  "Broadsoft, Inc.
9737 Washingtonian Blvd
Suite 350
Gaithersburg , MD 20878
Tel: +1-301-977-9440"
    DESCRIPTION
        "This MIB defines the faults for the BroadWorks DMS Application."
    REVISION    "201310080000Z"
                DESCRIPTION     "Creation of the Fault MIB."
    ::=  {  common  1  }

  bwBroadworksDmsDiskCipherError  NOTIFICATION-TYPE
    OBJECTS     { identifier, timeStamp, alarmName, systemName, severity, component, subcomponent, problemText, recommendedActionsText, npWebAppName, npErrorMessage }
    STATUS      current
    DESCRIPTION
        "An error occurred in the disk cipher functionality that prevents encryption and decryption functionality.
@severity:high
@subcomponent:security"
-- @feature:175154
    ::=  {  systemFaults 13301  }
    
END

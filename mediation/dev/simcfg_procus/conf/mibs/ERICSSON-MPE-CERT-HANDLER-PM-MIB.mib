ERICSSON-MPE-CERT-HANDLER-PM-MIB DEFINITIONS ::= BEGIN

IMPORTS
     MODULE-IDENTITY, OBJECT-TYPE, Gauge32 
          FROM SNMPv2-SMI

     MODULE-COMPLIANCE, OBJECT-GROUP
          FROM SNMPv2-CONF

     applIndex
          FROM NETWORK-SERVICES-MIB

     ItuPerceivedSeverity
          FROM ITU-ALARM-TC

     mpeModules
          FROM ERICSSON-MPE-REGISTRY-MIB ;

mpeCertHandlerPmModule MODULE-IDENTITY
   LAST-UPDATED    "201312111700Z"
   ORGANIZATION    "Ericsson AB"
   CONTACT-INFO    "        Ericsson AB

                    Postal: Ericsson AB
                            Kistagangen 26
                            SE - 164 80 Stockholm
                            Sweden

                       Tel: +46 8 7571500
                       Fax:

                    E-Mail: support@ericsson.com"
   DESCRIPTION     "Counters and events used by the WAP Secure Connection 
                    functionality."
::= { mpeModules 14 }

certHandlerPmObjects  OBJECT IDENTIFIER ::= { mpeCertHandlerPmModule 1 }

certHandlerApi  OBJECT IDENTIFIER ::= { certHandlerPmObjects 1 }

certHandlerServer  OBJECT IDENTIFIER ::= { certHandlerPmObjects 2 }

certHandlerPmConformance  OBJECT IDENTIFIER ::= { mpeCertHandlerPmModule 3 }

certHandlerPmGroups  OBJECT IDENTIFIER ::= { certHandlerPmConformance 1 }

certHandlerPmCompliances  OBJECT IDENTIFIER ::= { certHandlerPmConformance 2 }

certHandlerApiTable OBJECT-TYPE
   SYNTAX          SEQUENCE OF CertHandlerApiEntry
   MAX-ACCESS      not-accessible
   STATUS          current
   DESCRIPTION     "One entry is created for each application that 
                    contains the WTLS layer of the WAP stack module 
                    (1=Secure Connection Oriented, 2=Secure 
                    Connectionless)."
::= { certHandlerApi 1 } 

certHandlerApiEntry OBJECT-TYPE
   SYNTAX          CertHandlerApiEntry
   MAX-ACCESS      not-accessible
   STATUS          current
   DESCRIPTION     "The counters and events for the Certificate Handler 
                    API."
   INDEX { applIndex }
::= { certHandlerApiTable  1 }

CertHandlerApiEntry  ::= SEQUENCE
{
   certHandlerApiCommunicationError ItuPerceivedSeverity,
   certHandlerApiInterworkingError  ItuPerceivedSeverity,
   certHandlerApiConfigError        ItuPerceivedSeverity,
   certHandlerApiOutstCertRevChecks Gauge32
}

certHandlerApiCommunicationError  OBJECT-TYPE
   SYNTAX          ItuPerceivedSeverity
   MAX-ACCESS      read-only
   STATUS          current
   DESCRIPTION     "The connection to the Certificate Handler process has 
                    been lost."
::= { certHandlerApiEntry 1 }

certHandlerApiInterworkingError  OBJECT-TYPE
   SYNTAX          ItuPerceivedSeverity
   MAX-ACCESS      read-only
   STATUS          current
   DESCRIPTION     "There is a mismatch between the WAP Stack and the 
                    Certificate Handler."
::= { certHandlerApiEntry 2 }

certHandlerApiConfigError  OBJECT-TYPE
   SYNTAX          ItuPerceivedSeverity
   MAX-ACCESS      read-only
   STATUS          current
   DESCRIPTION     "An error occured when accessing a configuration 
                    parameter or its value."
::= { certHandlerApiEntry 4 }

certHandlerApiOutstCertRevChecks  OBJECT-TYPE
   SYNTAX          Gauge32
   MAX-ACCESS      read-only
   STATUS          current
   DESCRIPTION     "Specifies the number of outstanding requests issued 
                    to the Certificate Handler to determine if a 
                    certificate has been revoked."
::= { certHandlerApiEntry 5 }

certHandlerServerCorruptRootCert  OBJECT-TYPE
   SYNTAX          ItuPerceivedSeverity
   MAX-ACCESS      read-only
   STATUS          current
   DESCRIPTION     "There was an error in a root certificate file or the 
                    file could not be found."
::= { certHandlerServer 1 }

certHandlerServerCrlNotFound  OBJECT-TYPE
   SYNTAX          ItuPerceivedSeverity
   MAX-ACCESS      read-only
   STATUS          current
   DESCRIPTION     "The Certificate Handler could not find a certificate 
                    revocation list."
::= { certHandlerServer 2 }

certHandlerServerCrlCorrupt  OBJECT-TYPE
   SYNTAX          ItuPerceivedSeverity
   MAX-ACCESS      read-only
   STATUS          current
   DESCRIPTION     "The Certificate Handler retrieved a corrupt 
                    certificate revocation list."
::= { certHandlerServer 3 }

certHandlerServerConfigError  OBJECT-TYPE
   SYNTAX          ItuPerceivedSeverity
   MAX-ACCESS      read-only
   STATUS          current
   DESCRIPTION     "An error occured when accessing a configuration 
                    parameter or its value."
::= { certHandlerServer 4 }

-- Compliance Statements

certHandlerCompliance MODULE-COMPLIANCE
   STATUS          current
   DESCRIPTION     "The compliance statement for wap public key 
                    infrastructure."
   MODULE          -- this module
   MANDATORY-GROUPS {certHandlerConfGroup}
::= { certHandlerPmCompliances 1 }

-- Units of Conformance

certHandlerConfGroup OBJECT-GROUP
   OBJECTS { certHandlerApiCommunicationError,
             certHandlerApiInterworkingError,
             certHandlerApiConfigError,
             certHandlerApiOutstCertRevChecks,
             certHandlerServerCorruptRootCert,
             certHandlerServerCrlNotFound,
             certHandlerServerCrlCorrupt,
             certHandlerServerConfigError}
   STATUS          current
   DESCRIPTION     "A collection of objects providing performance and 
                    fault management information about a wap public key 
                    infrastructure."
::= { certHandlerPmGroups 1 }
END

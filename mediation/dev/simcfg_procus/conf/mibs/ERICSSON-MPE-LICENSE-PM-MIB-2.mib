ERICSSON-MPE-LICENSE-PM-MIB-2 DEFINITIONS ::= BEGIN

IMPORTS
     MODULE-IDENTITY, OBJECT-TYPE, Gauge32 , Counter32 
          FROM SNMPv2-SMI

     MODULE-COMPLIANCE, OBJECT-GROUP
          FROM SNMPv2-CONF

     TEXTUAL-CONVENTION
          FROM SNMPv2-TC

     ItuPerceivedSeverity
          FROM ITU-ALARM-TC

     mpeModules
          FROM ERICSSON-MPE-REGISTRY-MIB ;

mpeLicensePmModule MODULE-IDENTITY
   LAST-UPDATED    "201312111700Z"
   ORGANIZATION    "Ericsson AB"
   CONTACT-INFO    "        Ericsson AB

                    Postal: Ericsson AB
                            Kistagangen 26
                            SE - 164 80 Stockholm
                            Sweden

                       Tel: +46 8 7571500
                       Fax:

                    E-Mail: support@ericsson.com"
   DESCRIPTION     "The counters and states used by the License Handling 
                    and Traffic Regulation functionality."
::= { mpeModules 7 }

licensePmObjects  OBJECT IDENTIFIER ::= { mpeLicensePmModule 1 }

licenseStates  OBJECT IDENTIFIER ::= { licensePmObjects 1 }

licensePePpg  OBJECT IDENTIFIER ::= { licensePmObjects 2 }

trafficRegulation  OBJECT IDENTIFIER ::= { licensePmObjects 10 }

rtspTraffic  OBJECT IDENTIFIER ::= { licensePmObjects 11 }

ccuRegulator  OBJECT IDENTIFIER ::= { licensePmObjects 12 }

licensePmConformance  OBJECT IDENTIFIER ::= { mpeLicensePmModule 3 }

licensePmGroups  OBJECT IDENTIFIER ::= { licensePmConformance 1 }

licensePmCompliances  OBJECT IDENTIFIER ::= { licensePmConformance 2 }

MpeTrafficType ::= TEXTUAL-CONVENTION
   STATUS          current
   DESCRIPTION     "The value of this object identifies the traffic type."
   SYNTAX          INTEGER { pullTraffic(1),
                             pushTraffic(2),
                             mmsPushTraffic(3),
                             reverseProxyPullTraffic(4) }

licenseExpiry  OBJECT-TYPE
   SYNTAX          ItuPerceivedSeverity
   MAX-ACCESS      read-only
   STATUS          current
   DESCRIPTION     "The license key is close to expiration. Contact 
                    Customer Support to renew the license."
::= { licenseStates 2 }

licenseServerError  OBJECT-TYPE
   SYNTAX          ItuPerceivedSeverity
   MAX-ACCESS      read-only
   STATUS          current
   DESCRIPTION     "Problem to request/release an authorization license 
                    code for a specific feature. Probably communication 
                    problem with the license server. Check that the 
                    configuration parameter 'apsLicenseServerHost', is equal to the 
                    hostname or IP address of the computer where the 
                    License Server is running. Check also that the license 
                    server is up and running. Finally, check the 
                    troubleshooter log and operator log for more detailed information. 
                    If the problem remains, please contact Customer 
                    Support."
::= { licenseStates 3 }

licenseInternalError  OBJECT-TYPE
   SYNTAX          ItuPerceivedSeverity
   MAX-ACCESS      read-only
   STATUS          current
   DESCRIPTION     "Failed to initialize the client, to request for a 
                    license or to receive the expiration time. If the problem 
                    remains, please contact Customer Support."
::= { licenseStates 4 }

licenseTrafficReqProcess  OBJECT-TYPE
   SYNTAX          ItuPerceivedSeverity
   MAX-ACCESS      read-only
   STATUS          current
   DESCRIPTION     "The Traffic Regulator process has terminated 
                    abnormally."
::= { licenseStates 6 }

licenseUseCapPull  OBJECT-TYPE
   SYNTAX          ItuPerceivedSeverity
   MAX-ACCESS      read-only
   STATUS          current
   DESCRIPTION     "The number of performed Pull transactions has reached 
                    the configured limit."
::= { licenseStates 7 }

licenseUseCapPush  OBJECT-TYPE
   SYNTAX          ItuPerceivedSeverity
   MAX-ACCESS      read-only
   STATUS          current
   DESCRIPTION     "The number of performed Push transactions has reached 
                    the configured limit."
::= { licenseStates 8 }

licenseUseCapRevP  OBJECT-TYPE
   SYNTAX          ItuPerceivedSeverity
   MAX-ACCESS      read-only
   STATUS          current
   DESCRIPTION     "The number of performed Reverse Proxy transactions 
                    has reached the configured limit."
::= { licenseStates 9 }

licenseUseCapRtsp  OBJECT-TYPE
   SYNTAX          ItuPerceivedSeverity
   MAX-ACCESS      read-only
   STATUS          current
   DESCRIPTION     "The number of concurrent Streaming Sessions has 
                    reached the configured limit."
::= { licenseStates 10 }

licenseUseCapCcu  OBJECT-TYPE
   SYNTAX          ItuPerceivedSeverity
   MAX-ACCESS      read-only
   STATUS          current
   DESCRIPTION     "The number of concurrently connected users (CCU) has 
                    reached the configured limit."
::= { licenseStates 11 }

licensePePpgMMSPushLimit  OBJECT-TYPE
   SYNTAX          ItuPerceivedSeverity
   MAX-ACCESS      read-only
   STATUS          current
   DESCRIPTION     "The number of performed PE-PPG MMS Push transactions 
                    has reached the limit of allowed number of 
                    transactions."
::= { licensePePpg 1 }

trafficRegulationTable OBJECT-TYPE
   SYNTAX          SEQUENCE OF TrafficRegulationEntry
   MAX-ACCESS      not-accessible
   STATUS          current
   DESCRIPTION     "The counters for the number of accepted and rejected 
                    requests, and the capacity usage as a percentage."
::= { trafficRegulation 1 } 

trafficRegulationEntry OBJECT-TYPE
   SYNTAX          TrafficRegulationEntry
   MAX-ACCESS      not-accessible
   STATUS          current
   DESCRIPTION     "The counters for the number of accepted and rejected 
                    requests, and the capacity usage as a percentage."
   INDEX { trafficRegulationTrafficType }
::= { trafficRegulationTable  1 }

TrafficRegulationEntry  ::= SEQUENCE
{
   trafficRegulationTrafficType    MpeTrafficType,
   trafficRegulationAcceptedReq    Counter32,
   trafficRegulationRejectedReq    Counter32,
   trafficRegulationCapacityUsage  Gauge32,
   trafficRegulationCapacityTps    Gauge32,
   trafficRegulationCapacityAvg    Gauge32,
   trafficRegulationCapacityTpsAvg Gauge32
}

trafficRegulationTrafficType  OBJECT-TYPE
   SYNTAX          MpeTrafficType 
   MAX-ACCESS      not-accessible
   STATUS          current
   DESCRIPTION     "An integer used to uniquely identify a traffic 
                    regulation table entry."
::= { trafficRegulationEntry 1 }

trafficRegulationAcceptedReq  OBJECT-TYPE
   SYNTAX          Counter32
   MAX-ACCESS      read-only
   STATUS          current
   DESCRIPTION     "Counter holding the number of accepted requests 
                    during the period specified by the configuration parameter 
                    'apsCheckCapacityUsageInterval'.
                    The applUptime epoch of the application should be 
                    used as reference point for this counter."
::= { trafficRegulationEntry 2 }

trafficRegulationRejectedReq  OBJECT-TYPE
   SYNTAX          Counter32
   MAX-ACCESS      read-only
   STATUS          current
   DESCRIPTION     "Counter holding the number of rejected requests 
                    during the period specified by the configuration parameter 
                    'apsCheckCapacityUsageInterval'.
                    The applUptime epoch of the application should be 
                    used as reference point for this counter."
::= { trafficRegulationEntry 3 }

trafficRegulationCapacityUsage  OBJECT-TYPE
   SYNTAX          Gauge32
   MAX-ACCESS      read-only
   STATUS          current
   DESCRIPTION     "Counter holding the peak capacity usage, expressed as 
                    a percentage of the license limit."
::= { trafficRegulationEntry 4 }

trafficRegulationCapacityTps  OBJECT-TYPE
   SYNTAX          Gauge32
   MAX-ACCESS      read-only
   STATUS          current
   DESCRIPTION     "Counter holding the peak value of the number of TPS 
                    during the sampling interval This value is an abolute 
                    value."
::= { trafficRegulationEntry 5 }

trafficRegulationCapacityAvg  OBJECT-TYPE
   SYNTAX          Gauge32
   MAX-ACCESS      read-only
   STATUS          current
   DESCRIPTION     "Counter holding the average capacity usage, expressed 
                    as a percentage of the license limit."
::= { trafficRegulationEntry 6 }

trafficRegulationCapacityTpsAvg  OBJECT-TYPE
   SYNTAX          Gauge32
   MAX-ACCESS      read-only
   STATUS          current
   DESCRIPTION     "Counter holding the average value of the number of 
                    TPS during the sampling interval. This value is an 
                    abolute value."
::= { trafficRegulationEntry 7 }

rtspAcceptedSess  OBJECT-TYPE
   SYNTAX          Counter32
   MAX-ACCESS      read-only
   STATUS          current
   DESCRIPTION     "Counter holding the number of accepted session 
                    establishments.
                    The applUptime epoch of the application should be 
                    used as reference point for this counter."
::= { rtspTraffic 2 }

rtspRejectedSess  OBJECT-TYPE
   SYNTAX          Counter32
   MAX-ACCESS      read-only
   STATUS          current
   DESCRIPTION     "Counter holding the number of rejected session 
                    establishments.
                    The applUptime epoch of the application should be 
                    used as reference point for this counter."
::= { rtspTraffic 3 }

rtspUsage  OBJECT-TYPE
   SYNTAX          Gauge32
   MAX-ACCESS      read-only
   STATUS          current
   DESCRIPTION     "Counter holding the RTSP Concurrent Sessions, 
                    expressed as a percentage of the license limit. This counter 
                    is updated upon each opened or closed session."
::= { rtspTraffic 4 }

rtspUsageSess  OBJECT-TYPE
   SYNTAX          Gauge32
   MAX-ACCESS      read-only
   STATUS          current
   DESCRIPTION     "Counter holding the RTSP Concurrent Sessions, 
                    expressed in number of sessions. This counter is updated upon 
                    each opened or closed session."
::= { rtspTraffic 5 }

rtspPeakUsage  OBJECT-TYPE
   SYNTAX          Gauge32
   MAX-ACCESS      read-only
   STATUS          current
   DESCRIPTION     "Counter holding the peak value of RTSP Concurrent 
                    Sessions during the sampling interval, expressed as a 
                    percentage of the license limit. This counter is updated 
                    at the interval set by Check capacity usage interval."
::= { rtspTraffic 6 }

rtspPeakUsageSess  OBJECT-TYPE
   SYNTAX          Gauge32
   MAX-ACCESS      read-only
   STATUS          current
   DESCRIPTION     "Counter holding the peak value of RTSP Concurrent 
                    Sessions during the sampling interval, expressed in 
                    number of sessions. This counter is updated at the interval 
                    set by Check capacity usage interval."
::= { rtspTraffic 7 }

ccuRegulatorCcu  OBJECT-TYPE
   SYNTAX          Gauge32
   MAX-ACCESS      read-only
   STATUS          current
   DESCRIPTION     "Counter holding the CCU (Concurrently Connected 
                    Users), expressed as a positive integer."
::= { ccuRegulator 1 }

ccuRegulatorCcuUsage  OBJECT-TYPE
   SYNTAX          Gauge32
   MAX-ACCESS      read-only
   STATUS          current
   DESCRIPTION     "Counter holding the CCU (Concurrently Connected 
                    Users), expressed as a percentage of the license limit."
::= { ccuRegulator 2 }

-- Compliance Statements

licenseCompliance MODULE-COMPLIANCE
   STATUS          current
   DESCRIPTION     "The compliance statement for license handling."
   MODULE          -- this module
   MANDATORY-GROUPS {licenseConfGroup}
::= { licensePmCompliances 1 }

-- Units of Conformance

licenseConfGroup OBJECT-GROUP
   OBJECTS { licenseExpiry,
             licenseServerError,
             licenseInternalError,
             licenseTrafficReqProcess,
             licenseUseCapPull,
             licenseUseCapPush,
             licenseUseCapRevP,
             licenseUseCapRtsp,
             licenseUseCapCcu,
             licensePePpgMMSPushLimit,
             trafficRegulationAcceptedReq,
             trafficRegulationRejectedReq,
             trafficRegulationCapacityUsage,
             trafficRegulationCapacityTps,
             trafficRegulationCapacityAvg,
             trafficRegulationCapacityTpsAvg,
             rtspAcceptedSess,
             rtspRejectedSess,
             rtspUsage,
             rtspUsageSess,
             rtspPeakUsage,
             rtspPeakUsageSess,
             ccuRegulatorCcu,
             ccuRegulatorCcuUsage}
   STATUS          current
   DESCRIPTION     "A collection of objects providing performance and 
                    fault management information about a license handling."
::= { licensePmGroups 1 }
END

-- File Name : BW-SS7StackFault.mib

BW-SS7StackFault DEFINITIONS ::= BEGIN
  IMPORTS
    enterprises, MODULE-IDENTITY, NOTIFICATION-TYPE
      FROM SNMPv2-SMI
common, faultFields, identifier, timeStamp, alarmName, systemName, severity, alarmState, component, subcomponent, problemText, recommendedActionsText, correlationParameter, sccpObjId, sccpState, sccpAffectedSsn, sccpAffectedSsnSp, sccpAffectedSsnSsn, sccpConnectionId, sccpResetReason,  sccpOriginator, sccpModuleId,sccpSubModuleId, sccpMtpSap, sccpErrorCode, sccpBitMask, sccpDroppedApiId,  sccpErrorLevel, sccpErrorFlag, sccpPointCode, m3uaAsId, m3uaLocalSpId, m3uaRemSpId, m3uaState, m3uaNwSpId, m3uaAspId, m3uaOptIndParams, m3uaOptIndParamsBitmap, m3uaOptIndParamsDownCause, m3uaSgId, m3uaAssocId, m3uaNumInStreams, m3uaNumOutStreams, m3uaErrSrc, m3uaEcode, m3uaInfoLength, m3uaPInfoStr, m3uaRegStatus, m3uaDeregStatus, m3uaNewAs, m3uaDelAs, ss7pInstanceId, ss7pStackType, ss7pEcode, ss7pEntityStatus, ss7pFailureEcode, ss7pTierId, ss7pPc, ss7pPcType, ss7pSpId, ss7pNi, ss7pVariant, ss7pSapId, ss7pSsn, ss7pSsId, ss7pNumBitsInstanceId, ss7pFlag, ss7pEmStatus, ss7pEmInfoAddr, ss7pEmInfoServerPort, ss7pEmInfoMinClientPort, ss7pEmInfoMaxClientPort, ss7pInstanceType, ss7pIp, ss7pPort, ss7pIpStr, mapInstId, mapTierLevel, mapErrorCode, mapInfoLen, mapInfoStr, mapStatus, mapInstanceType, mapVariant, mapIp, mapPort, mapEmStatus, mapEmInfoAddr, mapEmInfoServerPort, mapEmInfoMinClientPort, mapEmInfoMaxClientPort, npSS7SubsystemNumber
      FROM BroadworksFault;

  broadsoft MODULE-IDENTITY
    LAST-UPDATED  "201103240000Z"
    ORGANIZATION  "Broadsoft, Inc"
    CONTACT-INFO  "Broadsoft, Inc.
220 Perry Parkway
Gaithersburg, MD  20877
301-977-9440"
    DESCRIPTION
        "This MIB defines management information that is common to all elements in a Broadworks system."
    REVISION    "201103240000Z"
                DESCRIPTION     "Creating the mib."
    ::=  {  enterprises  6431  }

  broadworks  OBJECT IDENTIFIER
    ::=  {  broadsoft  1  }

  common  OBJECT IDENTIFIER
    ::=  {  broadworks  1  }

  systemFaults  OBJECT IDENTIFIER
    ::=  {  common  1  }

  bwPMemSS7PlatformLaunched  NOTIFICATION-TYPE
    OBJECTS     { identifier, timeStamp, alarmName, systemName, severity, component, subcomponent, problemText, recommendedActionsText }
    STATUS      current
    DESCRIPTION
        "This notification indicates that the emSS7Platform process has been started.
@severity:informational
@subcomponent:processmonitor
@correlationrules:bwPMemSS7PlatformLaunched, bwPMemSS7PlatformShutDown, bwPMemSS7PlatformStarted, and bwPMemSS7PlatformDeath can be correlated into a single notification.  These events have to be considered as a transition of the state machine for the management of the emSS7Platform process running on some of the BroadWorks servers."
-- @feature:158606
    ::=  {  systemFaults 10501  }

  bwPMemSS7PlatformShutDown  NOTIFICATION-TYPE
    OBJECTS     { identifier, timeStamp, alarmName, systemName, severity, component, subcomponent, problemText, recommendedActionsText }
    STATUS      current
    DESCRIPTION
        "This notification indicates that the emSS7Platform process has been manually shut down.
@severity:informational
@subcomponent:processmonitor
@correlationrules:bwPMemSS7PlatformLaunched, bwPMemSS7PlatformShutDown, bwPMemSS7PlatformStarted, and bwPMemSS7PlatformDeath can be correlated into a single notification.  These events have to be considered as a transition of the state machine for the management of the emSS7Platform process running on some of the BroadWorks servers."
-- @feature:158606
    ::=  {  systemFaults 10502  }

  bwPMemSS7PlatformRestarted  NOTIFICATION-TYPE
    OBJECTS     { identifier, timeStamp, alarmName, systemName, severity, component, subcomponent, problemText, recommendedActionsText }
    STATUS      current
    DESCRIPTION
        "This notification provides the date and time of the emSS7Platform process restart.
@severity:informational
@subcomponent:processmonitor
@correlationrules:bwPMemSS7PlatformLaunched, bwPMemSS7PlatformShutDown, bwPMemSS7PlatformStarted, and bwPMemSS7PlatformDeath can be correlated into a single notification.  These events have to be considered as a transition of the state machine for the management of the emSS7Platform process running on some of the BroadWorks servers."
-- @feature:158606
    ::=  {  systemFaults 10503  }

  bwPMemSS7PlatformDeath  NOTIFICATION-TYPE
    OBJECTS     { identifier, timeStamp, alarmName, systemName, severity, component, subcomponent, problemText, recommendedActionsText }
    STATUS      current
    DESCRIPTION
        "This notification provides the date and time of the emSS7Platform process death.
@severity:critical
@subcomponent:processmonitor
@correlationrules:bwPMemSS7PlatformLaunched, bwPMemSS7PlatformShutDown, bwPMemSS7PlatformStarted, and bwPMemSS7PlatformDeath can be correlated into a single notification.  These events have to be considered as a transition of the state machine for the management of the emSS7Platform process running on some of the BroadWorks servers."
-- @feature:158606
    ::=  {  systemFaults 10504  }

  bwPMss7PlatformLaunched  NOTIFICATION-TYPE
    OBJECTS     { identifier, timeStamp, alarmName, systemName, severity, component, subcomponent, problemText, recommendedActionsText }
    STATUS      current
    DESCRIPTION
        "This notification indicates that the ss7Platform process has been started.
@severity:informational
@subcomponent:processmonitor
@correlationrules:bwPMss7PlatformLaunched, bwPMss7PlatformShutDown, bwPMss7PlatformStarted, and bwPMss7PlatformDeath can be correlated into a single notification.  These events have to be considered as a transition of the state machine for the management of the ss7Platform process running on some of the BroadWorks servers."
-- @feature:158606
    ::=  {  systemFaults 10505  }

  bwPMss7PlatformShutDown  NOTIFICATION-TYPE
    OBJECTS     { identifier, timeStamp, alarmName, systemName, severity, component, subcomponent, problemText, recommendedActionsText }
    STATUS      current
    DESCRIPTION
        "This notification indicates that the ss7Platform process has been manually shut down.
@severity:informational
@subcomponent:processmonitor
@correlationrules:bwPMss7PlatformLaunched, bwPMss7PlatformShutDown, bwPMss7PlatformStarted, and bwPMss7PlatformDeath can be correlated into a single notification.  These events have to be considered as a transition of the state machine for the management of the ss7Platform process running on some of the BroadWorks servers."
-- @feature:158606
    ::=  {  systemFaults 10506  }

  bwPMss7PlatformRestarted  NOTIFICATION-TYPE
    OBJECTS     { identifier, timeStamp, alarmName, systemName, severity, component, subcomponent, problemText, recommendedActionsText }
    STATUS      current
    DESCRIPTION
        "This notification provides the date and time of the ss7Platform process restart.
@severity:informational
@subcomponent:processmonitor
@correlationrules:bwPMss7PlatformLaunched, bwPMss7PlatformShutDown, bwPMss7PlatformStarted, and bwPMss7PlatformDeath can be correlated into a single notification.  These events have to be considered as a transition of the state machine for the management of the ss7Platform process running on some of the BroadWorks servers."
-- @feature:158606
    ::=  {  systemFaults 10507  }

  bwPMss7PlatformDeath  NOTIFICATION-TYPE
    OBJECTS     { identifier, timeStamp, alarmName, systemName, severity, component, subcomponent, problemText, recommendedActionsText }
    STATUS      current
    DESCRIPTION
        "This notification provides the date and time of the ss7Platform process death.
@severity:critical
@subcomponent:processmonitor
@correlationrules:bwPMss7PlatformLaunched, bwPMss7PlatformShutDown, bwPMss7PlatformStarted, and bwPMss7PlatformDeath can be correlated into a single notification.  These events have to be considered as a transition of the state machine for the management of the ss7Platform process running on some of the BroadWorks servers."
-- @feature:158606
    ::=  {  systemFaults 10508  }

  bwSS7StackSccpSsInd  NOTIFICATION-TYPE
    OBJECTS     { identifier, timeStamp, alarmName, systemName, severity, component, subcomponent, problemText, recommendedActionsText, sccpObjId, sccpState, sccpAffectedSsnSp, sccpAffectedSsnSsn }
    STATUS      current
    DESCRIPTION
        "This notification provides information about an sccp Sub System.
@severity:low
@subcomponent:sccp"
-- @feature:158606
    ::=  {  systemFaults 10533  }

  bwSS7StackSccpDeInit  NOTIFICATION-TYPE
    OBJECTS     { identifier, timeStamp, alarmName, systemName, severity, component, subcomponent, problemText, recommendedActionsText, sccpObjId, sccpState }
    STATUS      current
    DESCRIPTION
        "This notification provides information about an sccp de-init.
@severity:low
@subcomponent:sccp"
-- @feature:158606
    ::=  {  systemFaults 10534  }

  bwSS7StackSccpConnectionInd  NOTIFICATION-TYPE
    OBJECTS     { identifier, timeStamp, alarmName, systemName, severity, component, subcomponent, problemText, recommendedActionsText, sccpObjId, sccpState, sccpConnectionId, sccpResetReason, sccpOriginator }
    STATUS      current
    DESCRIPTION
        "This notification provides information about an sccp connection.
@severity:low
@subcomponent:sccp"
-- @feature:158606
    ::=  {  systemFaults 10535  }

  bwSS7StackSccpErrorInd  NOTIFICATION-TYPE
    OBJECTS     { identifier, timeStamp, alarmName, systemName, severity, component, subcomponent, problemText, recommendedActionsText, sccpObjId, sccpModuleId, sccpSubModuleId, sccpMtpSap, sccpErrorCode, sccpBitMask, sccpDroppedApiId, sccpErrorLevel, sccpErrorFlag, sccpState }
    STATUS      current
    DESCRIPTION
        "This notification provides information about an sccp error.
@severity:medium
@subcomponent:sccp"
-- @feature:158606
    ::=  {  systemFaults 10536  }

  bwSS7StackSccpSpInd  NOTIFICATION-TYPE
    OBJECTS     { identifier, timeStamp, alarmName, systemName, severity, component, subcomponent, problemText, recommendedActionsText, sccpObjId, sccpState, sccpPointCode }
    STATUS      current
    DESCRIPTION
        "This notification provides information about an sccp Self Point Code.
@severity:low
@subcomponent:sccp"
-- @feature:158606
    ::=  {  systemFaults 10537  }

  bwSS7StackM3uaRemoteAsStateInd  NOTIFICATION-TYPE
    OBJECTS     { identifier, timeStamp, alarmName, systemName, severity, component, subcomponent, problemText, recommendedActionsText, m3uaAsId, m3uaLocalSpId, m3uaState }
    STATUS      current
    DESCRIPTION
        "This notification provides information about m3ua remote AS state change.
@severity:low
@subcomponent:m3ua"
-- @feature:158606
    ::=  {  systemFaults 10538  }

  bwSS7StackM3uaLocalAsStateInd  NOTIFICATION-TYPE
    OBJECTS     { identifier, timeStamp, alarmName, systemName, severity, component, subcomponent, problemText, recommendedActionsText, m3uaAsId, m3uaRemSpId, m3uaNwSpId, m3uaState }
    STATUS      current
    DESCRIPTION
        "This notification provides information about m3ua local AS state change.
@severity:low
@subcomponent:m3ua"
-- @feature:158606
    ::=  {  systemFaults 10539  }

  bwSS7StackM3uaLocalAspStateInd  NOTIFICATION-TYPE
    OBJECTS     { identifier, timeStamp, alarmName, systemName, severity, component, subcomponent, problemText, recommendedActionsText, m3uaAspId, m3uaRemSpId, m3uaAsId, m3uaState, m3uaOptIndParamsBitmap, m3uaOptIndParamsDownCause }
    STATUS      current
    DESCRIPTION
        "This notification provides information about m3ua local ASP state change.
When issued with m3uaAsId set to 65535, the notification provides the global state of the ASP within all AS instances.
@severity:low
@subcomponent:m3ua"
-- @feature:158606
    ::=  {  systemFaults 10540  }

  bwSS7StackM3uaConnectionStateInd  NOTIFICATION-TYPE
    OBJECTS     { identifier, timeStamp, alarmName, systemName, severity, component, subcomponent, problemText, recommendedActionsText, m3uaAspId, m3uaSgId, m3uaState, m3uaAssocId, m3uaNumInStreams, m3uaNumOutStreams }
    STATUS      current
    DESCRIPTION
        "This notification provides information about m3ua connection state change.
@severity:low
@subcomponent:m3ua"
-- @feature:158606
    ::=  {  systemFaults 10541  }

  bwSS7StackM3uaErrorInd  NOTIFICATION-TYPE
    OBJECTS     { identifier, timeStamp, alarmName, systemName, severity, component, subcomponent, problemText, recommendedActionsText, m3uaAspId, m3uaSgId, m3uaErrSrc, m3uaEcode, m3uaPInfoStr }
    STATUS      current
    DESCRIPTION
        "This notification provides information about m3ua error.
@severity:medium
@subcomponent:m3ua"
-- @feature:158606
    ::=  {  systemFaults 10542  }

  bwSS7StackM3uaRemoteAspStateInd  NOTIFICATION-TYPE
    OBJECTS     { identifier, timeStamp, alarmName, systemName, severity, component, subcomponent, problemText, recommendedActionsText, m3uaAspId, m3uaLocalSpId, m3uaAsId, m3uaState }
    STATUS      current
    DESCRIPTION
        "This notification provides information about m3ua remote ASP state change.
@severity:low
@subcomponent:m3ua"
-- @feature:158606
    ::=  {  systemFaults 10543  }

  bwSS7StackM3uaRegRspInd  NOTIFICATION-TYPE
    OBJECTS     { identifier, timeStamp, alarmName, systemName, severity, component, subcomponent, problemText, recommendedActionsText, m3uaLocalSpId, m3uaRemSpId, m3uaAsId, m3uaRegStatus }
    STATUS      current
    DESCRIPTION
        "This notification provides information about m3ua registration response indication.
@severity:low
@subcomponent:m3ua"
-- @feature:158606
    ::=  {  systemFaults 10544  }

  bwSS7StackM3uaDeRegRspInd  NOTIFICATION-TYPE
    OBJECTS     { identifier, timeStamp, alarmName, systemName, severity, component, subcomponent, problemText, recommendedActionsText, m3uaLocalSpId, m3uaRemSpId, m3uaAsId, m3uaDeregStatus }
    STATUS      current
    DESCRIPTION
        "This notification provides information about m3ua de-registration response indication.
@severity:low
@subcomponent:m3ua"
-- @feature:158606
    ::=  {  systemFaults 10545  }

  bwSS7StackM3uaRegInd  NOTIFICATION-TYPE
    OBJECTS     { identifier, timeStamp, alarmName, systemName, severity, component, subcomponent, problemText, recommendedActionsText, m3uaLocalSpId, m3uaRemSpId, m3uaAsId, m3uaNewAs }
    STATUS      current
    DESCRIPTION
        "This notification provides information about m3ua registration indication.
@severity:low
@subcomponent:m3ua"
-- @feature:158606
    ::=  {  systemFaults 10546  }

  bwSS7StackM3uaDeRegInd  NOTIFICATION-TYPE
    OBJECTS     { identifier, timeStamp, alarmName, systemName, severity, component, subcomponent, problemText, recommendedActionsText, m3uaLocalSpId, m3uaRemSpId, m3uaAsId, m3uaNewAs }
    STATUS      current
    DESCRIPTION
        "This notification provides information about m3ua de-registration indicaton.
@severity:low
@subcomponent:m3ua"
-- @feature:158606
    ::=  {  systemFaults 10547  }

  bwSS7StackSs7pStackInitFail  NOTIFICATION-TYPE
    OBJECTS     { identifier, timeStamp, alarmName, systemName, severity, component, subcomponent, problemText, recommendedActionsText, ss7pInstanceId, ss7pVariant, ss7pStackType, ss7pEcode }
    STATUS      current
    DESCRIPTION
        "This notification provides information about ss7 stack initialization faillure.
@severity:high
@subcomponent:ss7p"
-- @feature:158606
    ::=  {  systemFaults 10548  }

  bwSS7StackSs7pInstanceStatus  NOTIFICATION-TYPE
    OBJECTS     { identifier, timeStamp, alarmName, systemName, severity, component, subcomponent, problemText, recommendedActionsText, ss7pEntityStatus, ss7pTierId, ss7pInstanceType, ss7pInstanceId, ss7pVariant, ss7pIp, ss7pPort }
    STATUS      current
    DESCRIPTION
        "This notification provides information about ss7 instance status.
@severity:low
@subcomponent:ss7p"
-- @feature:158606
    ::=  {  systemFaults 10549  }

  bwSS7StackSs7pInitFailure  NOTIFICATION-TYPE
    OBJECTS     { identifier, timeStamp, alarmName, systemName, severity, component, subcomponent, problemText, recommendedActionsText, ss7pFailureEcode, ss7pInstanceId, ss7pTierId }
    STATUS      current
    DESCRIPTION
        "This notification provides information about ss7p process initialization failure.
@severity:high
@subcomponent:ss7p"
-- @feature:158606
    ::=  {  systemFaults 10550  }

  bwSS7StackSs7pT2Bits  NOTIFICATION-TYPE
    OBJECTS     { identifier, timeStamp, alarmName, systemName, severity, component, subcomponent, problemText, recommendedActionsText, ss7pNumBitsInstanceId }
    STATUS      current
    DESCRIPTION
        "This notification provides information about ss7p T2 bits.
@severity:low
@subcomponent:ss7p"
-- @feature:158606
   ::=  {  systemFaults 10551  }

  bwSS7StackSs7pLoggingFail  NOTIFICATION-TYPE
    OBJECTS     { identifier, timeStamp, alarmName, systemName, severity, component, subcomponent, problemText, recommendedActionsText, ss7pFlag, ss7pInstanceId, ss7pTierId }
    STATUS      current
    DESCRIPTION
        "This notification provides information about ss7p, informing of logging failure.
@severity:high
@subcomponent:ss7p"
-- @feature:158606
    ::=  {  systemFaults 10552  }

  bwSS7StackSs7pTwoActiveEm  NOTIFICATION-TYPE
    OBJECTS     { identifier, timeStamp, alarmName, systemName, severity, component, subcomponent, problemText, recommendedActionsText }
    STATUS      current
    DESCRIPTION
        "This notification provides information about ss7p, informing that there are two active EM.
@severity:low
@subcomponent:ss7p"
-- @feature:158606
    ::=  {  systemFaults 10553  }

  bwSS7StackSs7pClibEmStatus  NOTIFICATION-TYPE
    OBJECTS     { identifier, timeStamp, alarmName, systemName, severity, component, subcomponent, problemText, recommendedActionsText, ss7pEmStatus, ss7pEmInfoAddr, ss7pEmInfoServerPort, ss7pEmInfoMinClientPort, ss7pEmInfoMaxClientPort }
    STATUS      current
    DESCRIPTION
        "This notification provides information about ss7p EM status.
@severity:low
@subcomponent:ss7p"
-- @feature:158606
    ::=  {  systemFaults 10554  }

  bwSS7StackMapNotifyError  NOTIFICATION-TYPE
    OBJECTS     { identifier, timeStamp, alarmName, systemName, severity, component, subcomponent, problemText, recommendedActionsText, mapTierLevel, mapInstId, mapErrorCode, mapInfoLen, mapInfoStr }
    STATUS      current
    DESCRIPTION
        "This notification provides information about map error.
@severity:high
@subcomponent:map"
-- @feature:158606
    ::=  {  systemFaults 10555  }

  bwSS7StackMapInstanceStatusInd  NOTIFICATION-TYPE
    OBJECTS     { identifier, timeStamp, alarmName, systemName, severity, component, subcomponent, problemText, recommendedActionsText, mapStatus,  mapTierLevel, mapInstanceType, mapInstId, mapVariant, mapIp, mapPort }
    STATUS      current
    DESCRIPTION
        "This notification provides information about map instance status indication.
@severity:low
@subcomponent:map"
-- @feature:158606
    ::=  {  systemFaults 10556  }

  bwSS7StackMapClibEmStatus  NOTIFICATION-TYPE
    OBJECTS     { identifier, timeStamp, alarmName, systemName, severity, component, subcomponent, problemText, recommendedActionsText, mapEmStatus, mapEmInfoAddr, mapEmInfoServerPort, mapEmInfoMinClientPort, mapEmInfoMaxClientPort }
    STATUS      current
    DESCRIPTION
        "This notification provides information about status of the map EM.
@severity:low
@subcomponent:map"
-- @feature:158606
    ::=  {  systemFaults 10557  }
   
  bwPMss7OAMBridgeLaunched  NOTIFICATION-TYPE
    OBJECTS     { identifier, timeStamp, alarmName, systemName, severity, component, subcomponent, problemText, recommendedActionsText }
    STATUS      current
    DESCRIPTION
        "This notification indicates that the ss7OAMBridge process has been started.
@severity:informational
@subcomponent:processmonitor
@correlationrules:bwPMss7OAMBridgeLaunched, bwPMss7OAMBridgeShutDown, bwPMss7OAMBridgeStarted, and bwPMss7OAMBridgeDeath can be correlated into a single notification.  These events have to be considered as a transition of the state machine for the management of the ss7OAMBridge process running on some of the BroadWorks servers."
-- @feature:158606
    ::=  {  systemFaults 10560  }

  bwPMss7OAMBridgeShutDown  NOTIFICATION-TYPE
    OBJECTS     { identifier, timeStamp, alarmName, systemName, severity, component, subcomponent, problemText, recommendedActionsText }
    STATUS      current
    DESCRIPTION
        "This notification indicates that the ss7OAMBridge process has been manually shut down.
@severity:informational
@subcomponent:processmonitor
@correlationrules:bwPMss7OAMBridgeLaunched, bwPMss7OAMBridgeShutDown, bwPMss7OAMBridgeStarted, and bwPMss7OAMBridgeDeath can be correlated into a single notification.  These events have to be considered as a transition of the state machine for the management of the ss7OAMBridge process running on some of the BroadWorks servers."
-- @feature:158606
    ::=  {  systemFaults 10561  }

  bwPMss7OAMBridgeRestarted  NOTIFICATION-TYPE
    OBJECTS     { identifier, timeStamp, alarmName, systemName, severity, component, subcomponent, problemText, recommendedActionsText }
    STATUS      current
    DESCRIPTION
        "This notification provides the date and time of the ss7OAMBridge process restart.
@severity:informational
@subcomponent:processmonitor
@correlationrules:bwPMss7OAMBridgeLaunched, bwPMss7OAMBridgeShutDown, bwPMss7OAMBridgeStarted, and bwPMss7OAMBridgeDeath can be correlated into a single notification.  These events have to be considered as a transition of the state machine for the management of the ss7OAMBridge process running on some of the BroadWorks servers."
-- @feature:158606
    ::=  {  systemFaults 10562  }

  bwPMss7OAMBridgeDeath  NOTIFICATION-TYPE
    OBJECTS     { identifier, timeStamp, alarmName, systemName, severity, component, subcomponent, problemText, recommendedActionsText }
    STATUS      current
    DESCRIPTION
        "This notification provides the date and time of the ss7OAMBridge process death.
@severity:critical
@subcomponent:processmonitor
@correlationrules:bwPMss7OAMBridgeLaunched, bwPMss7OAMBridgeShutDown, bwPMss7OAMBridgeStarted, and bwPMss7OAMBridgeDeath can be correlated into a single notification.  These events have to be considered as a transition of the state machine for the management of the ss7OAMBridge process running on some of the BroadWorks servers."
-- @feature:158606
    ::=  {  systemFaults 10563  }
    
END

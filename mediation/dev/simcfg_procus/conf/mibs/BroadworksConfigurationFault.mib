--===============================================================
-- File Name : BroadworksConfigurationFault.mib
-- Date      : 02/09/2009
-- Author    : BroadSoft Inc.
--===============================================================
BroadworksConfigurationFault DEFINITIONS ::= BEGIN
  IMPORTS
    NOTIFICATION-TYPE, MODULE-IDENTITY
      FROM SNMPv2-SMI
    common, faultFields, identifier, timeStamp, alarmName, systemName, severity, alarmState, 
    component, subcomponent, problemText, recommendedActionsText, npConfigVersion
      FROM BroadworksFault;

  systemFaults MODULE-IDENTITY
    LAST-UPDATED  "200902090000Z"
    ORGANIZATION  "Broadsoft, Inc"
    CONTACT-INFO  "Broadsoft, Inc.
9737 Washingtonian Blvd
Suite 350
Gaithersburg , MD 20878
Tel: +1-301-977-9440"
    DESCRIPTION
        "The MIB defines the faults for the Configuration subsystem. "
    REVISION    "200902090000Z"
    DESCRIPTION
        "MIB Creation"
    ::=  {  common  1  }

  bwPMconfigdLaunched  NOTIFICATION-TYPE
    OBJECTS     { identifier, timeStamp, alarmName, systemName, severity, component, subcomponent, problemText, recommendedActionsText }
    STATUS      current
    DESCRIPTION
        "This notification indicates that the configuration agent has been started.
@severity:informational
@subcomponent:processmonitor
@correlationrules:bwPMconfigdLaunched, bwPMconfigdShutDown, bwPMconfigdRestarted, bwPMconfigdDeath, and bwPMconfigdOutOfMemory can be correlated into a single alarm.  These events have to be considered as a transition of the state machine for the management of the configd process."
    ::=  {  systemFaults 6101  }

  bwPMconfigdShutDown  NOTIFICATION-TYPE
    OBJECTS     { identifier, timeStamp, alarmName, systemName, severity, component, subcomponent, problemText, recommendedActionsText }
    STATUS      current
    DESCRIPTION
        "This notification indicates that the configuration agent has been shutdown.
@severity:informational
@subcomponent:processmonitor
@correlationrules:bwPMconfigdLaunched, bwPMconfigdShutDown, bwPMconfigdRestarted, bwPMconfigdDeath, and bwPMconfigdOutOfMemory can be correlated into a single alarm.  These events have to be considered as a transition of the state machine for the management of the configd process."
    ::=  {  systemFaults 6102  }

  bwPMconfigdRestarted  NOTIFICATION-TYPE
    OBJECTS     { identifier, timeStamp, alarmName, systemName, severity, component, subcomponent, problemText, recommendedActionsText }
    STATUS      current
    DESCRIPTION
        "This notification indicates that the configuration agent has been restarted.
@severity:informational
@subcomponent:processmonitor
@correlationrules:bwPMconfigdLaunched, bwPMconfigdShutDown, bwPMconfigdRestarted, bwPMconfigdDeath, and bwPMconfigdOutOfMemory can be correlated into a single alarm.  These events have to be considered as a transition of the state machine for the management of the configd process."
    ::=  {  systemFaults 6103  }

  bwPMconfigdDeath  NOTIFICATION-TYPE
    OBJECTS     { identifier, timeStamp, alarmName, systemName, severity, component, subcomponent, problemText, recommendedActionsText }
    STATUS      current
    DESCRIPTION
        "This notification indicates that the configuration agent as abnormally terminated.
@severity:critical
@subcomponent:processmonitor
@correlationrules:bwPMconfigdLaunched, bwPMconfigdShutDown, bwPMconfigdRestarted, bwPMconfigdDeath, and bwPMconfigdOutOfMemory can be correlated into a single alarm.  These events have to be considered as a transition of the state machine for the management of the configd process."
    ::=  {  systemFaults 6104  }

  bwConfigurationChanged  NOTIFICATION-TYPE
    OBJECTS     { identifier ,timeStamp ,alarmName ,systemName ,severity ,component ,subcomponent ,problemText ,recommendedActionsText, npConfigVersion }
    STATUS      current
    DESCRIPTION
        "This notification indicates that the configuration agent as loaded a new configuration version.
@severity:informational
@subcomponent:configd"
    ::=  {  systemFaults 6105  }

  bwConfigurationFailed  NOTIFICATION-TYPE
    OBJECTS     { identifier ,timeStamp ,alarmName ,systemName ,severity ,component ,subcomponent ,problemText ,recommendedActionsText, npConfigVersion }
    STATUS      current
    DESCRIPTION
        "This notification indicates that the configuration agent as failed to loaded a new configuration version.
@severity:high
@subcomponent:configd"
    ::=  {  systemFaults 6106  }

  bwPMconfigdOutOfMemory  NOTIFICATION-TYPE
    OBJECTS     { identifier, timeStamp, alarmName, systemName, severity, component, subcomponent, problemText, recommendedActionsText }
    STATUS      current
    DESCRIPTION
        "This notification indicates that the configuration agent ran out of memory.
@severity:high
@subcomponent:processmonitor
@correlationrules:bwPMconfigdLaunched, bwPMconfigdShutDown, bwPMconfigdRestarted, bwPMconfigdDeath, and bwPMconfigdOutOfMemory can be correlated into a single alarm.  These events have to be considered as a transition of the state machine for the management of the configd process."
-- @feature:165352
    ::=  {  systemFaults 6107  }

  bwConfigReplicationOffline  NOTIFICATION-TYPE
    OBJECTS     { identifier ,timeStamp ,alarmName ,systemName ,severity ,component ,subcomponent ,problemText ,recommendedActionsText }
    STATUS      current
    DESCRIPTION
        "This alarm indicates that the configuration replication is currently offline.
@severity:high
@subcomponent:configd"
-- @feature:158606
    ::=  {  systemFaults 6108  }

  bwConfigReplicationFailed  NOTIFICATION-TYPE
    OBJECTS     { identifier ,timeStamp ,alarmName ,systemName ,severity ,component ,subcomponent ,problemText ,recommendedActionsText }
    STATUS      current
    DESCRIPTION
        "This notification indicates that the master's configuration could not be properly replicated.
@severity:high
@subcomponent:configd"
-- @feature:158606
    ::=  {  systemFaults 6109  }

END

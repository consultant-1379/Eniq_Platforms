--===============================================================
-- File Name : BW-EnhancedCallLogsDBManagement-XS-TAS.mib
-- Author    : BroadSoft Inc.
-- Copyright 2000-2012, BroadSoft, Inc. All rights reserved. 
-- Proprietary Property of BroadSoft, Inc. Gaithersburg, MD.
--===============================================================

BW-EnhancedCallLogsDBManagement-XS-TAS DEFINITIONS ::= BEGIN
  IMPORTS
    DateAndTime, DisplayString 
      FROM SNMPv2-TC
    MODULE-COMPLIANCE, OBJECT-GROUP 
      FROM SNMPv2-CONF
    enterprises, MODULE-IDENTITY, OBJECT-TYPE, Gauge32, Counter32, Integer32, Unsigned32 
      FROM SNMPv2-SMI;

  broadsoft MODULE-IDENTITY
    LAST-UPDATED  "201303050000Z"
    ORGANIZATION  "Broadsoft, Inc"
    CONTACT-INFO  "Broadsoft, Inc.
9737 Washingtonian Blvd
Suite 350
Gaithersburg , MD 20878
Tel: +1-301-977-9440"
    DESCRIPTION
      "This is the MIB for the Enhanced Call Logs DB Management XS-TAS application."
    REVISION    "201303050000Z"
      DESCRIPTION     "Created from BW-EnhancedCallLogsDBManagement for XS TAS"
    REVISION    "201008230000Z"
      DESCRIPTION     "Creation."
    ::= { enterprises 6431 }

  broadworks OBJECT IDENTIFIER
    ::= { broadsoft 1 }

  eclDBManagement OBJECT IDENTIFIER
    ::= { broadworks 33 }

  ecldbDatabaseModule OBJECT IDENTIFIER
    ::= { eclDBManagement 1 }

  ecldbDatabaseStats OBJECT IDENTIFIER
    ::= { ecldbDatabaseModule 1 }

  ecldbOracle OBJECT IDENTIFIER
    ::= { ecldbDatabaseStats 1 }

  bwEnhancedCallLogsDBManagementXSTASMibConformance OBJECT IDENTIFIER
    ::= { eclDBManagement 1000 }

-- ecldbOracle ::  ...............................

   bwEnhancedCallLogsDBManagementXSTASOpenedTransactions  OBJECT-TYPE
      SYNTAX         Gauge32
      MAX-ACCESS     read-only
      STATUS         current
      DESCRIPTION
            "This counter reflects the total number of opened transaction with the database."
-- @feature:162466                  
      ::=  {  ecldbOracle  1  }

   bwEnhancedCallLogsDBManagementXSTASCommittedTransactions  OBJECT-TYPE
      SYNTAX         Counter32
      MAX-ACCESS     read-write
      STATUS         current
      DESCRIPTION
            "This counter reflects the total number of committed transactions to the database since the last restart."
-- @feature:162466                  
      ::=  {  ecldbOracle  2  }

   bwEnhancedCallLogsDBManagementXSTASFailedTransactions  OBJECT-TYPE
      SYNTAX         Counter32
      MAX-ACCESS     read-write
      STATUS         current
      DESCRIPTION
            "This counter reflects the total number of failed transactions with the database."
-- @feature:162466                  
      ::=  {  ecldbOracle  3  }

   bwEnhancedCallLogsDBManagementXSTASCriticalErrors  OBJECT-TYPE
      SYNTAX         Counter32
      MAX-ACCESS     read-write
      STATUS         current
      DESCRIPTION
            "This counter reflects the total number of critical errors encountered during processing with the database."
-- @feature:162466                  
      ::=  {  ecldbOracle  4  }
      
  bwEnhancedCallLogsDBManagementXSTASOracleDbCount  OBJECT-TYPE
    SYNTAX      Integer32
    MAX-ACCESS  read-only
    STATUS      current
    DESCRIPTION
        "The number of oracle database defined for this application"
-- @feature:162466              
    ::= { ecldbOracle 5 }
  
  bwEnhancedCallLogsDBManagementXSTASOracleDbStatsTable OBJECT-TYPE
    SYNTAX      SEQUENCE OF BwEnhancedCallLogsDBManagementXSTASOracleDbStatsEntry
    MAX-ACCESS  not-accessible
    STATUS      current
    DESCRIPTION
        "A list of oracle database entries.  The number of entries is given by the value of bwEnhancedCallLogsDBManagementXSTASOracleDbCount."
-- @feature:162466              
    ::= { ecldbOracle 6 }
  
  bwEnhancedCallLogsDBManagementXSTASOracleDbStatsEntry OBJECT-TYPE
      SYNTAX      BwEnhancedCallLogsDBManagementXSTASOracleDbStatsEntry
      MAX-ACCESS  not-accessible
      STATUS      current
      DESCRIPTION
          "An entry containing statistics information applicable to a particular oracle database."
      INDEX   { bwEnhancedCallLogsDBManagementXSTASOracleDbStatsIndex }
-- @feature:162466            
    ::= { bwEnhancedCallLogsDBManagementXSTASOracleDbStatsTable 1 }
    
  BwEnhancedCallLogsDBManagementXSTASOracleDbStatsEntry ::= SEQUENCE {
    bwEnhancedCallLogsDBManagementXSTASOracleDbStatsIndex           Unsigned32,
    bwEnhancedCallLogsDBManagementXSTASOracleDbName                 DisplayString,
    bwEnhancedCallLogsDBManagementXSTASOracleDbNbConnectionsCreated Counter32,
    bwEnhancedCallLogsDBManagementXSTASOracleDbConnectionPoolSize   Gauge32,
    bwEnhancedCallLogsDBManagementXSTASOracleDbAvgUpdateTime        Gauge32,
    bwEnhancedCallLogsDBManagementXSTASOracleDbAvgRowsUpdated       Gauge32,
    bwEnhancedCallLogsDBManagementXSTASOracleDbAvgQueryTime         Gauge32,
    bwEnhancedCallLogsDBManagementXSTASOracleDbAvgRowsQueried       Gauge32,
    bwEnhancedCallLogsDBManagementXSTASOracleDbUpdateCount          Counter32,
    bwEnhancedCallLogsDBManagementXSTASOracleDbQueryCount           Counter32
  }
  
   bwEnhancedCallLogsDBManagementXSTASOracleDbStatsIndex OBJECT-TYPE
     SYNTAX      Unsigned32
     MAX-ACCESS  read-only
     STATUS      current
     DESCRIPTION 
         "This integer represents an OracleDb database index in the table."
-- @feature:162466               
   ::= { bwEnhancedCallLogsDBManagementXSTASOracleDbStatsEntry 1 }
   
   bwEnhancedCallLogsDBManagementXSTASOracleDbName OBJECT-TYPE
     SYNTAX      DisplayString
     MAX-ACCESS  read-only
     STATUS      current
     DESCRIPTION 
         "This string represents the oracle database name."
-- @feature:162466               
   ::= { bwEnhancedCallLogsDBManagementXSTASOracleDbStatsEntry 2 }
   
   bwEnhancedCallLogsDBManagementXSTASOracleDbNbConnectionsCreated OBJECT-TYPE
      SYNTAX      Counter32
      MAX-ACCESS  read-only
      STATUS      current
      DESCRIPTION 
          "Number of total connection created to the oracle database."
-- @feature:162466                
   ::= { bwEnhancedCallLogsDBManagementXSTASOracleDbStatsEntry 3 }
   
   bwEnhancedCallLogsDBManagementXSTASOracleDbConnectionPoolSize OBJECT-TYPE
      SYNTAX      Gauge32
      MAX-ACCESS  read-only
      STATUS      current
      DESCRIPTION 
          "Number of connections residing in the oracle database connection pool."
-- @feature:162466                
   ::= { bwEnhancedCallLogsDBManagementXSTASOracleDbStatsEntry 4 }
   
   bwEnhancedCallLogsDBManagementXSTASOracleDbAvgUpdateTime OBJECT-TYPE
      SYNTAX      Gauge32
      MAX-ACCESS  read-only
      STATUS      current
      DESCRIPTION 
          "Average oracle DB update time in milliseconds."
-- @feature:162466                
   ::= { bwEnhancedCallLogsDBManagementXSTASOracleDbStatsEntry 5 }
   
   bwEnhancedCallLogsDBManagementXSTASOracleDbAvgRowsUpdated OBJECT-TYPE
      SYNTAX      Gauge32
      MAX-ACCESS  read-only
      STATUS      current
      DESCRIPTION 
          "Average number of rows affected in oracle DB updates."
-- @feature:162466                
   ::= { bwEnhancedCallLogsDBManagementXSTASOracleDbStatsEntry 6 }
   
   bwEnhancedCallLogsDBManagementXSTASOracleDbAvgQueryTime OBJECT-TYPE
      SYNTAX      Gauge32
      MAX-ACCESS  read-only
      STATUS      current
      DESCRIPTION 
          "Average oracle DB query time in milliseconds."
-- @feature:162466                
   ::= { bwEnhancedCallLogsDBManagementXSTASOracleDbStatsEntry 7 }
   
   bwEnhancedCallLogsDBManagementXSTASOracleDbAvgRowsQueried OBJECT-TYPE
      SYNTAX      Gauge32
      MAX-ACCESS  read-only
      STATUS      current
      DESCRIPTION 
          "Average number of rows processed in oracle DB queries."
-- @feature:162466                
   ::= { bwEnhancedCallLogsDBManagementXSTASOracleDbStatsEntry 8 }
   
   bwEnhancedCallLogsDBManagementXSTASOracleDbUpdateCount OBJECT-TYPE
      SYNTAX      Counter32
      MAX-ACCESS  read-only
      STATUS      current
      DESCRIPTION 
          "Number of oracle DB updates performed since the application started."
-- @feature:162466                
   ::= { bwEnhancedCallLogsDBManagementXSTASOracleDbStatsEntry 9 }
   
   bwEnhancedCallLogsDBManagementXSTASOracleDbQueryCount OBJECT-TYPE
      SYNTAX      Counter32
      MAX-ACCESS  read-only
      STATUS      current
      DESCRIPTION 
          "Number of oracle DB queries performed since the application started."
-- @feature:162466                
   ::= { bwEnhancedCallLogsDBManagementXSTASOracleDbStatsEntry 10 }
      
   bwEnhancedCallLogsDBManagementXSTASOracleDbHWMTable OBJECT-TYPE
       SYNTAX      SEQUENCE OF BwEnhancedCallLogsDBManagementXSTASOracleDbHWMEntry
       MAX-ACCESS  not-accessible
       STATUS      current
       DESCRIPTION
           "A list of oracle database High Water Mark entries.  The number of entries is given by the value of bwEnhancedCallLogsDBManagementXSTASOracleDbCount."
-- @feature:162466                 
   ::= { ecldbOracle 7 }
     
   bwEnhancedCallLogsDBManagementXSTASOracleDbHWMEntry OBJECT-TYPE
       SYNTAX      BwEnhancedCallLogsDBManagementXSTASOracleDbHWMEntry
       MAX-ACCESS  not-accessible
       STATUS      current
       DESCRIPTION
           "An entry containing high water mark information applicable to a particular oracle database."
       INDEX   { bwEnhancedCallLogsDBManagementXSTASOracleDbHWMIndex }
-- @feature:162466             
    ::= { bwEnhancedCallLogsDBManagementXSTASOracleDbHWMTable 1 }
    
    BwEnhancedCallLogsDBManagementXSTASOracleDbHWMEntry ::= SEQUENCE {
        bwEnhancedCallLogsDBManagementXSTASOracleDbHWMIndex           Unsigned32,
        bwEnhancedCallLogsDBManagementXSTASOracleDbHWMDbName          DisplayString,
        bwEnhancedCallLogsDBManagementXSTASOracleDbHWMStatName        DisplayString,
        bwEnhancedCallLogsDBManagementXSTASOracleDbHWMStatValue       Gauge32,
        bwEnhancedCallLogsDBManagementXSTASOracleDbHWMTimestamp       DisplayString,
        bwEnhancedCallLogsDBManagementXSTASOracleDbHWMStackTrace      DisplayString
    }
    
    bwEnhancedCallLogsDBManagementXSTASOracleDbHWMIndex OBJECT-TYPE
         SYNTAX      Unsigned32
         MAX-ACCESS  read-only
         STATUS      current
         DESCRIPTION 
             "This integer represents an OracleDb database index in the table."
-- @feature:162466                   
    ::= { bwEnhancedCallLogsDBManagementXSTASOracleDbHWMEntry 1 }
       
    bwEnhancedCallLogsDBManagementXSTASOracleDbHWMDbName OBJECT-TYPE
         SYNTAX      DisplayString
         MAX-ACCESS  read-only
         STATUS      current
         DESCRIPTION 
             "This string represents the oracle database name."
-- @feature:162466                   
    ::= { bwEnhancedCallLogsDBManagementXSTASOracleDbHWMEntry 2 }
    
    bwEnhancedCallLogsDBManagementXSTASOracleDbHWMStatName OBJECT-TYPE
         SYNTAX      DisplayString
         MAX-ACCESS  read-only
         STATUS      current
         DESCRIPTION 
             "This string represents the statistic name."
-- @feature:162466                   
   ::= { bwEnhancedCallLogsDBManagementXSTASOracleDbHWMEntry 3 }
   
    bwEnhancedCallLogsDBManagementXSTASOracleDbHWMStatValue OBJECT-TYPE
         SYNTAX      Gauge32
         MAX-ACCESS  read-only
         STATUS      current
         DESCRIPTION 
             "This is the statistic value."
-- @feature:162466                   
   ::= { bwEnhancedCallLogsDBManagementXSTASOracleDbHWMEntry 4 }
   
    bwEnhancedCallLogsDBManagementXSTASOracleDbHWMTimestamp OBJECT-TYPE
         SYNTAX      DisplayString
         MAX-ACCESS  read-only
         STATUS      current
         DESCRIPTION 
             "This string represents the timestamp of the high water mark."
-- @feature:162466                   
   ::= { bwEnhancedCallLogsDBManagementXSTASOracleDbHWMEntry 5 }
   
    bwEnhancedCallLogsDBManagementXSTASOracleDbHWMStackTrace OBJECT-TYPE
         SYNTAX      DisplayString
         MAX-ACCESS  read-only
         STATUS      current
         DESCRIPTION 
             "This string represents the stack trace when the high water mark occured."
-- @feature:162466                   
   ::= { bwEnhancedCallLogsDBManagementXSTASOracleDbHWMEntry 6 }
        

-- BroadWorks CC Reporting DB Management MIB Conformance Definition  ...........................................

bwEnhancedCallLogsDbManagementMibGroups     OBJECT IDENTIFIER ::= { bwEnhancedCallLogsDBManagementXSTASMibConformance 1 }
bwEnhancedCallLogsDbManagementMibCompliancy OBJECT IDENTIFIER ::= { bwEnhancedCallLogsDBManagementXSTASMibConformance 2 }

bwEnhancedCallLogsDbManagementStatsGroup OBJECT-GROUP
    OBJECTS { bwEnhancedCallLogsDBManagementXSTASOpenedTransactions,
              bwEnhancedCallLogsDBManagementXSTASCommittedTransactions,
              bwEnhancedCallLogsDBManagementXSTASFailedTransactions,
              bwEnhancedCallLogsDBManagementXSTASCriticalErrors,
              bwEnhancedCallLogsDBManagementXSTASOracleDbCount,
              bwEnhancedCallLogsDBManagementXSTASOracleDbStatsIndex,
              bwEnhancedCallLogsDBManagementXSTASOracleDbName,
              bwEnhancedCallLogsDBManagementXSTASOracleDbNbConnectionsCreated,
              bwEnhancedCallLogsDBManagementXSTASOracleDbConnectionPoolSize,
              bwEnhancedCallLogsDBManagementXSTASOracleDbAvgUpdateTime,
              bwEnhancedCallLogsDBManagementXSTASOracleDbAvgRowsUpdated,
              bwEnhancedCallLogsDBManagementXSTASOracleDbAvgQueryTime,
              bwEnhancedCallLogsDBManagementXSTASOracleDbAvgRowsQueried,
              bwEnhancedCallLogsDBManagementXSTASOracleDbUpdateCount,
              bwEnhancedCallLogsDBManagementXSTASOracleDbQueryCount,
              bwEnhancedCallLogsDBManagementXSTASOracleDbHWMIndex,
              bwEnhancedCallLogsDBManagementXSTASOracleDbHWMDbName,
              bwEnhancedCallLogsDBManagementXSTASOracleDbHWMStatName,
              bwEnhancedCallLogsDBManagementXSTASOracleDbHWMStatValue,
              bwEnhancedCallLogsDBManagementXSTASOracleDbHWMTimestamp,
              bwEnhancedCallLogsDBManagementXSTASOracleDbHWMStackTrace }
  STATUS  current
  DESCRIPTION
     "This group defines statistics for the ECL DB Management."
  ::= { bwEnhancedCallLogsDbManagementMibGroups 1 }

  bwEnhancedCallLogsDBManagementXSTASBasicCompliance MODULE-COMPLIANCE
    STATUS      current
    DESCRIPTION 
        "BroadWorks ECL XS-TAS DB Management MIB compliance"

    MODULE

        MANDATORY-GROUPS        { bwEnhancedCallLogsDbManagementStatsGroup }

    ::= { bwEnhancedCallLogsDbManagementMibCompliancy 1 }

END

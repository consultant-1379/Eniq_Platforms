-- File Name : BW-MessageArchiveFault.mib
BW-MessageArchiveFault DEFINITIONS ::= BEGIN
  IMPORTS
    NOTIFICATION-TYPE, MODULE-IDENTITY
      FROM SNMPv2-SMI
    common, identifier, timeStamp, alarmName, systemName, severity, alarmState, component, subcomponent, problemText, recommendedActionsText, npProfileServer, npWebAppContextPath, npRepositoryUri
      FROM BroadworksFault;

  systemFaults MODULE-IDENTITY
    LAST-UPDATED  "201406170000Z"
    ORGANIZATION  "Broadsoft, Inc"
    CONTACT-INFO  "Broadsoft, Inc.
9737 Washingtonian Blvd
Suite 350
Gaithersburg , MD 20878
Tel: +1-301-977-9440"
    DESCRIPTION
        "This MIB defines the faults for the BroadWorks Message Archive Application."
    REVISION    "201406170000Z"
                DESCRIPTION     "Creation of the Fault MIB."
    ::=  {  common  1  }

  bwMessageArchiveReplicationFailure  NOTIFICATION-TYPE
    OBJECTS     { identifier, timeStamp, alarmName, systemName, severity, component, subcomponent, problemText, recommendedActionsText, npProfileServer, npWebAppContextPath }
    STATUS      current
    DESCRIPTION
        "A replication failure occurred.
@severity:high
@subcomponent:filerepos"
-- @feature:218189
    ::=  {  systemFaults 15151  }
    
  bwMessageArchiveReplicationOffline  NOTIFICATION-TYPE
    OBJECTS     { identifier, timeStamp, alarmName, systemName, severity, component, subcomponent, problemText, recommendedActionsText, npWebAppContextPath, npProfileServer }
    STATUS      current
    DESCRIPTION
        "The replication stopped for one of the Profile Server peer. This was caused by exceeding the replication queue capacity.
@severity:high
@subcomponent:filerepos"
-- @feature:218189
    ::=  {  systemFaults 15152  }
    
  bwMessageArchiverRepositoryCommunicationFailure  NOTIFICATION-TYPE
    OBJECTS     { identifier, timeStamp, alarmName, systemName, severity, alarmState, component, subcomponent, problemText, recommendedActionsText, npRepositoryUri }
    STATUS      current
    DESCRIPTION
        "The MessageArchiver is unable to send files to the configured file repository..
@severity:high
@subcomponent:messageArchiver"
-- @feature:218189
    ::=  {  systemFaults 15153  }
    
END

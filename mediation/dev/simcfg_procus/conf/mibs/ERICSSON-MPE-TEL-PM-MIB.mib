ERICSSON-MPE-TEL-PM-MIB DEFINITIONS ::= BEGIN

IMPORTS
     MODULE-IDENTITY, OBJECT-TYPE, Gauge32 , Counter32 
          FROM SNMPv2-SMI

     MODULE-COMPLIANCE, OBJECT-GROUP
          FROM SNMPv2-CONF

     applIndex
          FROM NETWORK-SERVICES-MIB

     ItuPerceivedSeverity
          FROM ITU-ALARM-TC

     mpeModules
          FROM ERICSSON-MPE-REGISTRY-MIB ;

mpeTelPmModule MODULE-IDENTITY
   LAST-UPDATED    "201511200053Z"
   ORGANIZATION    "Ericsson AB"
   CONTACT-INFO    "        Ericsson AB

                    Postal: Ericsson AB
                            Kistagangen 26
                            SE - 164 80 Stockholm
                            Sweden

                       Tel: +46 8 7571500
                       Fax:

                    E-Mail: support@ericsson.com"
   DESCRIPTION     "Parameters for Traffic event logger."
::= { mpeModules 18 }

telPmObjects  OBJECT IDENTIFIER ::= { mpeTelPmModule 1 }

telApi  OBJECT IDENTIFIER ::= { telPmObjects 1 }

telSrvGrps  OBJECT IDENTIFIER ::= { telPmObjects 2 }

telSrv  OBJECT IDENTIFIER ::= { telPmObjects 3 }

telFtpClt  OBJECT IDENTIFIER ::= { telPmObjects 4 }

gtpp  OBJECT IDENTIFIER ::= { telPmObjects 5 }

gtppCgfEvents  OBJECT IDENTIFIER ::= { telPmObjects 6 }

gtppEvents  OBJECT IDENTIFIER ::= { telPmObjects 7 }

telPmConformance  OBJECT IDENTIFIER ::= { mpeTelPmModule 3 }

telPmGroups  OBJECT IDENTIFIER ::= { telPmConformance 1 }

telPmCompliances  OBJECT IDENTIFIER ::= { telPmConformance 2 }

telApiTable OBJECT-TYPE
   SYNTAX          SEQUENCE OF TelApiEntry
   MAX-ACCESS      not-accessible
   STATUS          current
   DESCRIPTION     "One entry is created for each application that uses 
                    Tel Api 
                    (1=Secure Connection Oriented, 2=Secure 
                    Connectionless, 3=Connection-Oriented, 4=Connectionless, 5=W-HTTP, 
                    6=Push Request Server,
                    7=Push Delivery)."
::= { telApi 1 } 

telApiEntry OBJECT-TYPE
   SYNTAX          TelApiEntry
   MAX-ACCESS      not-accessible
   STATUS          current
   DESCRIPTION     "The counters and events for Traffic Event Logger Api"
   INDEX { applIndex }
::= { telApiTable  1 }

TelApiEntry  ::= SEQUENCE
{
   telApiRecError          ItuPerceivedSeverity,
   telApiConfError         ItuPerceivedSeverity,
   telApiSuccessfulRecords Counter32,
   telApiFailedRecords     Counter32
}

telApiRecError  OBJECT-TYPE
   SYNTAX          ItuPerceivedSeverity
   MAX-ACCESS      read-only
   STATUS          current
   DESCRIPTION     "Too many counter errors."
::= { telApiEntry 1 }

telApiConfError  OBJECT-TYPE
   SYNTAX          ItuPerceivedSeverity
   MAX-ACCESS      read-only
   STATUS          current
   DESCRIPTION     "Too many configuration errors."
::= { telApiEntry 2 }

telApiSuccessfulRecords  OBJECT-TYPE
   SYNTAX          Counter32
   MAX-ACCESS      read-only
   STATUS          current
   DESCRIPTION     "Successful traffic event records.
                    The applUptime epoch of the application instance 
                    should be used as reference point for this counter."
::= { telApiEntry 3 }

telApiFailedRecords  OBJECT-TYPE
   SYNTAX          Counter32
   MAX-ACCESS      read-only
   STATUS          current
   DESCRIPTION     "Failed traffic event records.
                    The applUptime epoch of the application instance 
                    should be used as reference point for this counter."
::= { telApiEntry 4 }

telSrvGrpsTable OBJECT-TYPE
   SYNTAX          SEQUENCE OF TelSrvGrpsEntry
   MAX-ACCESS      not-accessible
   STATUS          current
   DESCRIPTION     "One entry is created for each Traffic Event Logger 
                    group."
::= { telSrvGrps 1 } 

telSrvGrpsEntry OBJECT-TYPE
   SYNTAX          TelSrvGrpsEntry
   MAX-ACCESS      not-accessible
   STATUS          current
   DESCRIPTION     "The events for Traffic Event Logger server groups."
   INDEX { applIndex }
::= { telSrvGrpsTable  1 }

TelSrvGrpsEntry  ::= SEQUENCE
{
   telSrvGrpsDirError ItuPerceivedSeverity,
   telSrvGrpsDirVolEr ItuPerceivedSeverity
}

telSrvGrpsDirError  OBJECT-TYPE
   SYNTAX          ItuPerceivedSeverity
   MAX-ACCESS      read-only
   STATUS          current
   DESCRIPTION     "Error has occurred when accessing directory."
::= { telSrvGrpsEntry 1 }

telSrvGrpsDirVolEr  OBJECT-TYPE
   SYNTAX          ItuPerceivedSeverity
   MAX-ACCESS      read-only
   STATUS          current
   DESCRIPTION     "Directory volume usage is greater than maximum 
                    allowed."
::= { telSrvGrpsEntry 2 }

telSrvVolumeError  OBJECT-TYPE
   SYNTAX          ItuPerceivedSeverity
   MAX-ACCESS      read-only
   STATUS          current
   DESCRIPTION     "A volume alarm has been generated by Traffic Event 
                    Logger server."
::= { telSrv 1 }

telFtpCltTable OBJECT-TYPE
   SYNTAX          SEQUENCE OF TelFtpCltEntry
   MAX-ACCESS      not-accessible
   STATUS          current
   DESCRIPTION     "One entry is created for each Traffic Event Logger 
                    group."
::= { telFtpClt 1 } 

telFtpCltEntry OBJECT-TYPE
   SYNTAX          TelFtpCltEntry
   MAX-ACCESS      not-accessible
   STATUS          current
   DESCRIPTION     "The events for Tel FTP Client."
   INDEX { applIndex }
::= { telFtpCltTable  1 }

TelFtpCltEntry  ::= SEQUENCE
{
   telFtpCltComError ItuPerceivedSeverity,
   telFtpCltDirError ItuPerceivedSeverity,
   telFtpCltSysError ItuPerceivedSeverity
}

telFtpCltComError  OBJECT-TYPE
   SYNTAX          ItuPerceivedSeverity
   MAX-ACCESS      read-only
   STATUS          current
   DESCRIPTION     "Too many errors when trying to FTP."
::= { telFtpCltEntry 1 }

telFtpCltDirError  OBJECT-TYPE
   SYNTAX          ItuPerceivedSeverity
   MAX-ACCESS      read-only
   STATUS          current
   DESCRIPTION     "Too many directory or file errors."
::= { telFtpCltEntry 2 }

telFtpCltSysError  OBJECT-TYPE
   SYNTAX          ItuPerceivedSeverity
   MAX-ACCESS      read-only
   STATUS          current
   DESCRIPTION     "Too many system errors."
::= { telFtpCltEntry 3 }

gtppTable OBJECT-TYPE
   SYNTAX          SEQUENCE OF GtppEntry
   MAX-ACCESS      not-accessible
   STATUS          current
   DESCRIPTION     "One entry is created for each CGF"
::= { gtpp 1 } 

gtppEntry OBJECT-TYPE
   SYNTAX          GtppEntry
   MAX-ACCESS      not-accessible
   STATUS          current
   DESCRIPTION     "Counters for GTP Prime"
   INDEX { applIndex }
::= { gtppTable  1 }

GtppEntry  ::= SEQUENCE
{
   gtppEchoReqSent     Counter32,
   gtppEchoRspRcv      Counter32,
   gtppEchoReqRcv      Counter32,
   gtppEchoRspSent     Counter32,
   gtppNodeReqSent     Counter32,
   gtppNodeRspRcv      Counter32,
   gtppNodeReqRcv      Counter32,
   gtppNodeRspSent     Counter32,
   gtppRedirReqRcv     Counter32,
   gtppRedirRspSent    Counter32,
   gtppVerNsupRcv      Counter32,
   gtppVerNsupSent     Counter32,
   gtppDataReqSent     Counter32,
   gtppDuplDataReqSent Counter32,
   gtppDataReqRelSent  Counter32,
   gtppDataReqCanSent  Counter32,
   gtppSucAccDtr       Counter32,
   gtppUnSucAccDtr     Counter32,
   gtppSucAccDuplDtr   Counter32,
   gtppUnSucAccDuplDtr Counter32,
   gtppSucAccCanDtr    Counter32,
   gtppUnSucAccCanDtr  Counter32,
   gtppSucAccRelDtr    Counter32,
   gtppUnSucAccRelDtr  Counter32,
   gtppTransferredCdr  Counter32,
   gtppReSentPack      Counter32,
   gtppTimeOutPack     Counter32,
   gtppReSentPathPack  Counter32,
   gtppTimeOutPathPack Counter32,
   gtppStartCount      Counter32,
   gtppCgfAvgRespTime  Gauge32,
   gtppCgfMaxRespTime  Gauge32,
   gtppCgfUnackDtr     Gauge32
}

gtppEchoReqSent  OBJECT-TYPE
   SYNTAX          Counter32
   MAX-ACCESS      read-only
   STATUS          current
   DESCRIPTION     "Sent Echo Requests.
                    The applUptime epoch of the application instance 
                    should be used as reference point for this counter."
::= { gtppEntry 1 }

gtppEchoRspRcv  OBJECT-TYPE
   SYNTAX          Counter32
   MAX-ACCESS      read-only
   STATUS          current
   DESCRIPTION     "Received Echo Responses.
                    The applUptime epoch of the application instance 
                    should be used as reference point for this counter."
::= { gtppEntry 2 }

gtppEchoReqRcv  OBJECT-TYPE
   SYNTAX          Counter32
   MAX-ACCESS      read-only
   STATUS          current
   DESCRIPTION     "Received Echo Requests.
                    The applUptime epoch of the application instance 
                    should be used as reference point for this counter."
::= { gtppEntry 3 }

gtppEchoRspSent  OBJECT-TYPE
   SYNTAX          Counter32
   MAX-ACCESS      read-only
   STATUS          current
   DESCRIPTION     "Sent Echo Responses.
                    The applUptime epoch of the application instance 
                    should be used as reference point for this counter."
::= { gtppEntry 4 }

gtppNodeReqSent  OBJECT-TYPE
   SYNTAX          Counter32
   MAX-ACCESS      read-only
   STATUS          current
   DESCRIPTION     "Sent Node Alive Requests.
                    The applUptime epoch of the application instance 
                    should be used as reference point for this counter."
::= { gtppEntry 5 }

gtppNodeRspRcv  OBJECT-TYPE
   SYNTAX          Counter32
   MAX-ACCESS      read-only
   STATUS          current
   DESCRIPTION     "Received Node Alive Responses.
                    The applUptime epoch of the application instance 
                    should be used as reference point for this counter."
::= { gtppEntry 6 }

gtppNodeReqRcv  OBJECT-TYPE
   SYNTAX          Counter32
   MAX-ACCESS      read-only
   STATUS          current
   DESCRIPTION     "Received Node Alive Requests.
                    The applUptime epoch of the application instance 
                    should be used as reference point for this counter."
::= { gtppEntry 7 }

gtppNodeRspSent  OBJECT-TYPE
   SYNTAX          Counter32
   MAX-ACCESS      read-only
   STATUS          current
   DESCRIPTION     "Sent Node Alive Responses.
                    The applUptime epoch of the application instance 
                    should be used as reference point for this counter."
::= { gtppEntry 8 }

gtppRedirReqRcv  OBJECT-TYPE
   SYNTAX          Counter32
   MAX-ACCESS      read-only
   STATUS          current
   DESCRIPTION     "Received Redirection Requests.
                    The applUptime epoch of the application instance 
                    should be used as reference point for this counter."
::= { gtppEntry 9 }

gtppRedirRspSent  OBJECT-TYPE
   SYNTAX          Counter32
   MAX-ACCESS      read-only
   STATUS          current
   DESCRIPTION     "Sent Redirection Responses.
                    The applUptime epoch of the application instance 
                    should be used as reference point for this counter."
::= { gtppEntry 10 }

gtppVerNsupRcv  OBJECT-TYPE
   SYNTAX          Counter32
   MAX-ACCESS      read-only
   STATUS          current
   DESCRIPTION     "Received Version Not Supported.
                    The applUptime epoch of the application instance 
                    should be used as reference point for this counter."
::= { gtppEntry 11 }

gtppVerNsupSent  OBJECT-TYPE
   SYNTAX          Counter32
   MAX-ACCESS      read-only
   STATUS          current
   DESCRIPTION     "Sent Version Not Supported.
                    The applUptime epoch of the application instance 
                    should be used as reference point for this counter."
::= { gtppEntry 12 }

gtppDataReqSent  OBJECT-TYPE
   SYNTAX          Counter32
   MAX-ACCESS      read-only
   STATUS          current
   DESCRIPTION     "Sent Data Record Transfer Requests.
                    The applUptime epoch of the application instance 
                    should be used as reference point for this counter."
::= { gtppEntry 13 }

gtppDuplDataReqSent  OBJECT-TYPE
   SYNTAX          Counter32
   MAX-ACCESS      read-only
   STATUS          current
   DESCRIPTION     "Sent Duplicated Data Record Transfer Requests.
                    The applUptime epoch of the application instance 
                    should be used as reference point for this counter."
::= { gtppEntry 14 }

gtppDataReqRelSent  OBJECT-TYPE
   SYNTAX          Counter32
   MAX-ACCESS      read-only
   STATUS          current
   DESCRIPTION     "Sent Data Record Transfer Release Requests.
                    The applUptime epoch of the application instance 
                    should be used as reference point for this counter."
::= { gtppEntry 15 }

gtppDataReqCanSent  OBJECT-TYPE
   SYNTAX          Counter32
   MAX-ACCESS      read-only
   STATUS          current
   DESCRIPTION     "Sent Data Record Transfer Cancellation Requests.
                    The applUptime epoch of the application instance 
                    should be used as reference point for this counter."
::= { gtppEntry 16 }

gtppSucAccDtr  OBJECT-TYPE
   SYNTAX          Counter32
   MAX-ACCESS      read-only
   STATUS          current
   DESCRIPTION     "Successfully Acknowledged Data Record Transfer 
                    Requests.
                    The applUptime epoch of the application instance 
                    should be used as reference point for this counter."
::= { gtppEntry 17 }

gtppUnSucAccDtr  OBJECT-TYPE
   SYNTAX          Counter32
   MAX-ACCESS      read-only
   STATUS          current
   DESCRIPTION     "Unsuccessfully Acknowledged Data Record Transfer 
                    Requests.
                    The applUptime epoch of the application instance 
                    should be used as reference point for this counter."
::= { gtppEntry 18 }

gtppSucAccDuplDtr  OBJECT-TYPE
   SYNTAX          Counter32
   MAX-ACCESS      read-only
   STATUS          current
   DESCRIPTION     "Successfully Acknowledged Duplicated Data Record 
                    Transfer Requests.
                    The applUptime epoch of the application instance 
                    should be used as reference point for this counter."
::= { gtppEntry 19 }

gtppUnSucAccDuplDtr  OBJECT-TYPE
   SYNTAX          Counter32
   MAX-ACCESS      read-only
   STATUS          current
   DESCRIPTION     "Unsuccessfully Acknowledged Duplicated Data Record 
                    Transfer Requests.
                    The applUptime epoch of the application instance 
                    should be used as reference point for this counter."
::= { gtppEntry 20 }

gtppSucAccCanDtr  OBJECT-TYPE
   SYNTAX          Counter32
   MAX-ACCESS      read-only
   STATUS          current
   DESCRIPTION     "Successfully Acknowledged Cancel Data Record Transfer 
                    Requests.
                    The applUptime epoch of the application instance 
                    should be used as reference point for this counter."
::= { gtppEntry 21 }

gtppUnSucAccCanDtr  OBJECT-TYPE
   SYNTAX          Counter32
   MAX-ACCESS      read-only
   STATUS          current
   DESCRIPTION     "Unsuccessfully Acknowledged Cancel Data Record 
                    Transfer Requests.
                    The applUptime epoch of the application instance 
                    should be used as reference point for this counter."
::= { gtppEntry 22 }

gtppSucAccRelDtr  OBJECT-TYPE
   SYNTAX          Counter32
   MAX-ACCESS      read-only
   STATUS          current
   DESCRIPTION     "Successfully Acknowledged Release Data Record 
                    Transfer Requests.
                    The applUptime epoch of the application instance 
                    should be used as reference point for this counter."
::= { gtppEntry 23 }

gtppUnSucAccRelDtr  OBJECT-TYPE
   SYNTAX          Counter32
   MAX-ACCESS      read-only
   STATUS          current
   DESCRIPTION     "Unsuccessfully Acknowledged Release Data Record 
                    Transfer Requests.
                    The applUptime epoch of the application instance 
                    should be used as reference point for this counter."
::= { gtppEntry 24 }

gtppTransferredCdr  OBJECT-TYPE
   SYNTAX          Counter32
   MAX-ACCESS      read-only
   STATUS          current
   DESCRIPTION     "Number of Call Detail Records transferred over GTP 
                    Prime.
                    The applUptime epoch of the application instance 
                    should be used as reference point for this counter."
::= { gtppEntry 25 }

gtppReSentPack  OBJECT-TYPE
   SYNTAX          Counter32
   MAX-ACCESS      read-only
   STATUS          current
   DESCRIPTION     "Number of packets resent over GTP Prime.
                    The applUptime epoch of the application instance 
                    should be used as reference point for this counter."
::= { gtppEntry 26 }

gtppTimeOutPack  OBJECT-TYPE
   SYNTAX          Counter32
   MAX-ACCESS      read-only
   STATUS          current
   DESCRIPTION     "Number of packets timed out over GTP Prime.
                    The applUptime epoch of the application instance 
                    should be used as reference point for this counter."
::= { gtppEntry 27 }

gtppReSentPathPack  OBJECT-TYPE
   SYNTAX          Counter32
   MAX-ACCESS      read-only
   STATUS          current
   DESCRIPTION     "Number of Path Management packets resent over GTP 
                    Prime.
                    The applUptime epoch of the application instance 
                    should be used as reference point for this counter."
::= { gtppEntry 28 }

gtppTimeOutPathPack  OBJECT-TYPE
   SYNTAX          Counter32
   MAX-ACCESS      read-only
   STATUS          current
   DESCRIPTION     "Number of Path Management packets timed out over GTP 
                    Prime.
                    The applUptime epoch of the application instance 
                    should be used as reference point for this counter."
::= { gtppEntry 29 }

gtppStartCount  OBJECT-TYPE
   SYNTAX          Counter32
   MAX-ACCESS      read-only
   STATUS          current
   DESCRIPTION     "Number of start-ups of the TEL server.
                    The applUptime epoch of the application instance 
                    should be used as reference point for this counter."
::= { gtppEntry 30 }

gtppCgfAvgRespTime  OBJECT-TYPE
   SYNTAX          Gauge32
   MAX-ACCESS      read-only
   STATUS          current
   DESCRIPTION     "Shows the average response time from the CGF in 
                    milliseconds during the last minute."
::= { gtppEntry 31 }

gtppCgfMaxRespTime  OBJECT-TYPE
   SYNTAX          Gauge32
   MAX-ACCESS      read-only
   STATUS          current
   DESCRIPTION     "Shows the maximum response time from the CGF in 
                    milliseconds during the last minute."
::= { gtppEntry 32 }

gtppCgfUnackDtr  OBJECT-TYPE
   SYNTAX          Gauge32
   MAX-ACCESS      read-only
   STATUS          current
   DESCRIPTION     "Shows the current number of unacknowldged data 
                    transfer requests to this CGF."
::= { gtppEntry 33 }

gtppCgfEventsTable OBJECT-TYPE
   SYNTAX          SEQUENCE OF GtppCgfEventsEntry
   MAX-ACCESS      not-accessible
   STATUS          current
   DESCRIPTION     "One entry is created for each CGF"
::= { gtppCgfEvents 1 } 

gtppCgfEventsEntry OBJECT-TYPE
   SYNTAX          GtppCgfEventsEntry
   MAX-ACCESS      not-accessible
   STATUS          current
   DESCRIPTION     "The CGF events for GTP Prime."
   INDEX { applIndex }
::= { gtppCgfEventsTable  1 }

GtppCgfEventsEntry  ::= SEQUENCE
{
   gtppCgfEventsComCgfError   ItuPerceivedSeverity,
   gtppCgfEventsComCgfRspTime ItuPerceivedSeverity
}

gtppCgfEventsComCgfError  OBJECT-TYPE
   SYNTAX          ItuPerceivedSeverity
   MAX-ACCESS      read-only
   STATUS          current
   DESCRIPTION     "CGF does not respond."
::= { gtppCgfEventsEntry 1 }

gtppCgfEventsComCgfRspTime  OBJECT-TYPE
   SYNTAX          ItuPerceivedSeverity
   MAX-ACCESS      read-only
   STATUS          current
   DESCRIPTION     "CGF does not respond fast enough."
::= { gtppCgfEventsEntry 2 }

gtppEventsTable OBJECT-TYPE
   SYNTAX          SEQUENCE OF GtppEventsEntry
   MAX-ACCESS      not-accessible
   STATUS          current
   DESCRIPTION     "One entry is created for the GTP Prime Stack"
::= { gtppEvents 1 } 

gtppEventsEntry OBJECT-TYPE
   SYNTAX          GtppEventsEntry
   MAX-ACCESS      not-accessible
   STATUS          current
   DESCRIPTION     "The events for GTP Prime."
   INDEX { applIndex }
::= { gtppEventsTable  1 }

GtppEventsEntry  ::= SEQUENCE
{
   gtppEventsChgBufError ItuPerceivedSeverity
}

gtppEventsChgBufError  OBJECT-TYPE
   SYNTAX          ItuPerceivedSeverity
   MAX-ACCESS      read-only
   STATUS          current
   DESCRIPTION     "CGF communication is either slow or malfunctioning."
::= { gtppEventsEntry 1 }

-- Compliance Statements

telCompliance MODULE-COMPLIANCE
   STATUS          current
   DESCRIPTION     "The compliance statement for tel."
   MODULE          -- this module
   MANDATORY-GROUPS {telConfGroup}
::= { telPmCompliances 1 }

-- Units of Conformance

telConfGroup OBJECT-GROUP
   OBJECTS { telApiRecError,
             telApiConfError,
             telApiSuccessfulRecords,
             telApiFailedRecords,
             telSrvGrpsDirError,
             telSrvGrpsDirVolEr,
             telSrvVolumeError,
             telFtpCltComError,
             telFtpCltDirError,
             telFtpCltSysError,
             gtppEchoReqSent,
             gtppEchoRspRcv,
             gtppEchoReqRcv,
             gtppEchoRspSent,
             gtppNodeReqSent,
             gtppNodeRspRcv,
             gtppNodeReqRcv,
             gtppNodeRspSent,
             gtppRedirReqRcv,
             gtppRedirRspSent,
             gtppVerNsupRcv,
             gtppVerNsupSent,
             gtppDataReqSent,
             gtppDuplDataReqSent,
             gtppDataReqRelSent,
             gtppDataReqCanSent,
             gtppSucAccDtr,
             gtppUnSucAccDtr,
             gtppSucAccDuplDtr,
             gtppUnSucAccDuplDtr,
             gtppSucAccCanDtr,
             gtppUnSucAccCanDtr,
             gtppSucAccRelDtr,
             gtppUnSucAccRelDtr,
             gtppTransferredCdr,
             gtppReSentPack,
             gtppTimeOutPack,
             gtppReSentPathPack,
             gtppTimeOutPathPack,
             gtppStartCount,
             gtppCgfAvgRespTime,
             gtppCgfMaxRespTime,
             gtppCgfUnackDtr,
             gtppCgfEventsComCgfError,
             gtppCgfEventsComCgfRspTime,
             gtppEventsChgBufError}
   STATUS          current
   DESCRIPTION     "A collection of objects providing performance and 
                    fault management information about a tel."
::= { telPmGroups 1 }
END

-- File Name : BW-FileReposExtdCaptureFault.mib
BW-FileReposExtdCaptureFault DEFINITIONS ::= BEGIN
  IMPORTS
    NOTIFICATION-TYPE, MODULE-IDENTITY
      FROM SNMPv2-SMI
    common, identifier, timeStamp, alarmName, systemName, severity, alarmState, component, subcomponent, problemText, recommendedActionsText, npProfileServer, npWebAppContextPath
      FROM BroadworksFault;

  systemFaults MODULE-IDENTITY
    LAST-UPDATED  "201305080000Z"
    ORGANIZATION  "Broadsoft, Inc"
    CONTACT-INFO  "Broadsoft, Inc.
9737 Washingtonian Blvd
Suite 350
Gaithersburg , MD 20878
Tel: +1-301-977-9440"
    DESCRIPTION
        "This MIB defines the faults for the BroadWorks FileReposExtdCapture Application."
    REVISION    "201307080000Z"
                DESCRIPTION     "Creation of the Fault MIB."
    ::=  {  common  1  }

  bwFileReposExtdCaptureReplicationFailure  NOTIFICATION-TYPE
    OBJECTS     { identifier, timeStamp, alarmName, systemName, severity, component, subcomponent, problemText, recommendedActionsText, npProfileServer, npWebAppContextPath }
    STATUS      current
    DESCRIPTION
        "A replication failure occurred.
@severity:high
@subcomponent:filerepos"
-- @feature:178321
    ::=  {  systemFaults 12601  }
    
  bwFileReposExtdCaptureReplicationOffline  NOTIFICATION-TYPE
    OBJECTS     { identifier, timeStamp, alarmName, systemName, severity, component, subcomponent, problemText, recommendedActionsText, npWebAppContextPath, npProfileServer }
    STATUS      current
    DESCRIPTION
        "The replication stopped for one of the Profile Server peer. This was caused by exceeding the replication queue capacity.
@severity:high
@subcomponent:filerepos"
-- @feature:178321
    ::=  {  systemFaults 12602  }
    
END

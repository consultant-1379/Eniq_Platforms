ERICSSON-MPE-PROXY-THROUGHPUT-PM-MIB DEFINITIONS ::= BEGIN

IMPORTS
     MODULE-IDENTITY, OBJECT-TYPE, Counter32 , Unsigned32 
          FROM SNMPv2-SMI

     MODULE-COMPLIANCE, OBJECT-GROUP
          FROM SNMPv2-CONF

     mpeModules
          FROM ERICSSON-MPE-REGISTRY-MIB ;

mpeProxyThroughputPmModule MODULE-IDENTITY
   LAST-UPDATED    "201511200053Z"
   ORGANIZATION    "Ericsson AB"
   CONTACT-INFO    "        Ericsson AB

                    Postal: Ericsson AB
                            Kistagangen 26
                            SE - 164 80 Stockholm
                            Sweden

                       Tel: +46 8 7571500
                       Fax:

                    E-Mail: support@ericsson.com"
   DESCRIPTION     "The capacity counters for the interfaces of the proxy 
                    based on protocols. What counter instance that is 
                    used for a specific protocol is configured with the 
                    'Transparent Proxy/Transparent TCP Proxy/Counter instance 
                    number for protocols' parameter"
::= { mpeModules 25 }

proxyThroughputPmObjects  OBJECT IDENTIFIER ::= { mpeProxyThroughputPmModule 1 }

protocol  OBJECT IDENTIFIER ::= { proxyThroughputPmObjects 1 }

proxyThroughputPmConformance  OBJECT IDENTIFIER ::= { mpeProxyThroughputPmModule 3 }

proxyThroughputPmGroups  OBJECT IDENTIFIER ::= { proxyThroughputPmConformance 1 }

proxyThroughputPmCompliances  OBJECT IDENTIFIER ::= { proxyThroughputPmConformance 2 }

protocolTable OBJECT-TYPE
   SYNTAX          SEQUENCE OF ProtocolEntry
   MAX-ACCESS      not-accessible
   STATUS          current
   DESCRIPTION     "One entry is created for each protocol that is 
                    detected in Multiservice Proxy."
::= { protocol 1 } 

protocolEntry OBJECT-TYPE
   SYNTAX          ProtocolEntry
   MAX-ACCESS      not-accessible
   STATUS          current
   DESCRIPTION     "The counters for data throughput for specific 
                    protocols."
   INDEX { protocolIndex }
::= { protocolTable  1 }

ProtocolEntry  ::= SEQUENCE
{
   protocolIndex         Unsigned32,
   protocolDataFromDev   Counter32,
   protocolDataToDev     Counter32,
   protocolDataFromOrig  Counter32,
   protocolDataToOrig    Counter32,
   protocolDataFromCache Counter32
}

protocolIndex  OBJECT-TYPE
   SYNTAX          Unsigned32
   MAX-ACCESS      not-accessible
   STATUS          current
   DESCRIPTION     "An integer used to uniquely identify a protocol table 
                    entry."
::= { protocolEntry 1 }

protocolDataFromDev  OBJECT-TYPE
   SYNTAX          Counter32
   MAX-ACCESS      read-only
   STATUS          current
   DESCRIPTION     "Counter indicating the amount of data in (KB) that 
                    has been received from devices. 
                    The applUptime epoch of the application should be 
                    used as reference point for this counter."
::= { protocolEntry 2 }

protocolDataToDev  OBJECT-TYPE
   SYNTAX          Counter32
   MAX-ACCESS      read-only
   STATUS          current
   DESCRIPTION     "Counter indicating the amount of data in (KB) that 
                    has been sent to devices. 
                    The applUptime epoch of the application should be 
                    used as reference point for this counter."
::= { protocolEntry 3 }

protocolDataFromOrig  OBJECT-TYPE
   SYNTAX          Counter32
   MAX-ACCESS      read-only
   STATUS          current
   DESCRIPTION     "Counter indicating the amount of data in (KB) that 
                    has been received from the origin servers. 
                    The applUptime epoch of the application should be 
                    used as reference point for this counter."
::= { protocolEntry 4 }

protocolDataToOrig  OBJECT-TYPE
   SYNTAX          Counter32
   MAX-ACCESS      read-only
   STATUS          current
   DESCRIPTION     "Counter indicating the amount of data in (KB) that 
                    has been sent to origin servers. 
                    The applUptime epoch of the application should be 
                    used as reference point for this counter."
::= { protocolEntry 5 }

protocolDataFromCache  OBJECT-TYPE
   SYNTAX          Counter32
   MAX-ACCESS      read-only
   STATUS          current
   DESCRIPTION     "Counter indicating the amount of data in (KB) that 
                    has been taken from the cache. 
                    The applUptime epoch of the application should be 
                    used as reference point for this counter."
::= { protocolEntry 6 }

-- Compliance Statements

proxyThroughputCompliance MODULE-COMPLIANCE
   STATUS          current
   DESCRIPTION     "The compliance statement for proxy throughput."
   MODULE          -- this module
   MANDATORY-GROUPS {proxyThroughputConfGroup}
::= { proxyThroughputPmCompliances 1 }

-- Units of Conformance

proxyThroughputConfGroup OBJECT-GROUP
   OBJECTS { protocolDataFromDev,
             protocolDataToDev,
             protocolDataFromOrig,
             protocolDataToOrig,
             protocolDataFromCache}
   STATUS          current
   DESCRIPTION     "A collection of objects providing performance and 
                    fault management information about a proxy throughput."
::= { proxyThroughputPmGroups 1 }
END

--===============================================================
-- File Name : BW-UC-Connect.mib
-- Author    : BroadSoft Inc.
-- Copyright 2000-2009, BroadSoft, Inc. All rights reserved. 
-- Proprietary Property of BroadSoft, Inc. Gaithersburg, MD.
--===============================================================

BW-UC-Connect DEFINITIONS ::= BEGIN
    IMPORTS
      DateAndTime, DisplayString
        FROM SNMPv2-TC
      MODULE-COMPLIANCE, OBJECT-GROUP          
        FROM SNMPv2-CONF
      enterprises, MODULE-IDENTITY, OBJECT-TYPE, Gauge32, Counter32, Integer32, Unsigned32
        FROM SNMPv2-SMI;

  broadsoft MODULE-IDENTITY
    LAST-UPDATED  "200906020000Z"
    ORGANIZATION  "Broadsoft, Inc"
    CONTACT-INFO  "Broadsoft, Inc.
9737 Washingtonian Blvd
Suite 350
Gaithersburg , MD 20878
Tel: +1-301-977-9440"
    DESCRIPTION
      "This is the MIB for the BroadWorks UC-Connect application."
    REVISION    "200906020000Z"
      DESCRIPTION     "Added Session Audit counters."
    REVISION    "200903300000Z"
      DESCRIPTION     "Creation."
    ::= { enterprises 6431 }

  broadworks OBJECT IDENTIFIER
    ::= { broadsoft 1 }

  ucconnect OBJECT IDENTIFIER
    ::= { broadworks 15 }

  protocol OBJECT IDENTIFIER
		::= { ucconnect 1 }

  capModule OBJECT IDENTIFIER
		::= { ucconnect 2 }

  locationApiModule OBJECT IDENTIFIER
    ::= { ucconnect 3 }

  cstaModule OBJECT IDENTIFIER
    ::= { ucconnect 4 }

  sessionAudit  OBJECT IDENTIFIER
    ::= { ucconnect 5 }

  internalModule OBJECT IDENTIFIER
    ::= { ucconnect 6 }

  overloadModule OBJECT IDENTIFIER
    ::= { ucconnect 7 }

  capStats OBJECT IDENTIFIER
    ::= { capModule 1 }
   
  locationApiStats OBJECT IDENTIFIER
    ::= { locationApiModule 1 }

  cstaStats OBJECT IDENTIFIER
    ::= { cstaModule 1 }

  internalStats OBJECT IDENTIFIER
    ::= { internalModule 1 }

  overloadStats OBJECT IDENTIFIER
    ::= { overloadModule 1 }

  bwUCConnectMibConformance OBJECT IDENTIFIER
    ::= { ucconnect 100 }

-- PROTOCOLS  :: SIP ...............................

	sip	OBJECT IDENTIFIER
		::=  {  protocol  1  }

	bwUCConnectSipStatsInviteIns	OBJECT-TYPE
		SYNTAX			Counter32
		MAX-ACCESS		read-write
		STATUS			current
		DESCRIPTION
				"This counter reflects the total number of INVITE requests received by BroadWorks."
		::=  {  sip  1  }

	bwUCConnectSipStatsAckIns	OBJECT-TYPE
		SYNTAX			Counter32
		MAX-ACCESS		read-write
		STATUS			current
		DESCRIPTION
				"This counter reflects the total number of ACK requests received by BroadWorks."
		::=  {  sip  2  }

	bwUCConnectSipStatsInviteResponsesTable	OBJECT-TYPE
		SYNTAX		SEQUENCE  OF  BwUCConnectSipStatsInviteResponsesEntry
		MAX-ACCESS	not-accessible
		STATUS		current
		DESCRIPTION
			"This table contains the counters for all SIP responses to the Invite requests sent by BroadWorks. Each counter is a 32-Bit counter. The response code is used to index into the table. Here are all the response codes:  302, 400, 401, 402, 403, 404, 405, 406, 407, 408, 409, 410, 411, 413, 414, 415, 420, 480, 481, 482, 483, 484, 485, 486, 487"
		::=  { sip  3 }

	bwUCConnectSipStatsCancelIns	OBJECT-TYPE
		SYNTAX			Counter32
		MAX-ACCESS		read-write
		STATUS			current
		DESCRIPTION
				"This counter reflects the total number of CANCEL requests received by BroadWorks."
		::=  {  sip  4  }

	bwUCConnectSipStatsRegisterIns	OBJECT-TYPE
		SYNTAX			Counter32
		MAX-ACCESS		read-write
		STATUS			current
		DESCRIPTION
				"This counter reflects the total number of REGISTER requests received by BroadWorks."
		::=  {  sip  5  }

	bwUCConnectSipStatsNotifyIns	OBJECT-TYPE
		SYNTAX			Counter32
		MAX-ACCESS		read-write
		STATUS			current
		DESCRIPTION
				"This counter reflects the total number of INFO requests received by BroadWorks"
		::=  {  sip  6  }

	bwUCConnectSipStatsSubscribeIns		OBJECT-TYPE
		SYNTAX			Counter32
		MAX-ACCESS		read-write
		STATUS			current
		DESCRIPTION
				"This counter reflects the total number of SUBSCRIBE message that have been received at the AS."
		::=  {  sip  7  }

	bwUCConnectSipStatsMessageIns		OBJECT-TYPE
		SYNTAX			Counter32
		MAX-ACCESS		read-write
		STATUS			current
		DESCRIPTION
				"This counter reflects the total number of MESSAGE message that have been received at the AS."
		::=  {  sip  8  }

	bwUCConnectSipStatsInfoIns	OBJECT-TYPE
		SYNTAX			Counter32
		MAX-ACCESS		read-write
		STATUS			current
		DESCRIPTION
				"This counter reflects the total number of INFO requests received by BroadWorks"
		::=  {  sip  9  }

	bwUCConnectSipStatsOptionsIns	OBJECT-TYPE
		SYNTAX			Counter32
		MAX-ACCESS		read-write
		STATUS			current
		DESCRIPTION
				"This counter reflects the total number of OPTIONS requests received by BroadWorks."
		::=  {  sip  10  }

	bwUCConnectSipStatsOptionsResponsesTable	OBJECT-TYPE
		SYNTAX		SEQUENCE  OF  BwUCConnectSipStatsOptionsResponsesEntry
		MAX-ACCESS	not-accessible
		STATUS		current
		DESCRIPTION
			"This table contains the counters for all SIP responses to the Options requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
		::=  { sip  11 }

	bwUCConnectSipStatsRegisterResponsesTable	OBJECT-TYPE
		SYNTAX		SEQUENCE  OF  BwUCConnectSipStatsRegisterResponsesEntry
		MAX-ACCESS	not-accessible
		STATUS		current
		DESCRIPTION
			"This table contains the counters for all SIP responses to the Register requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
		::=  { sip  12 }

	bwUCConnectSipStatsInfoResponsesTable	OBJECT-TYPE
		SYNTAX		SEQUENCE  OF  BwUCConnectSipStatsInfoResponsesEntry
		MAX-ACCESS	not-accessible
		STATUS		current
		DESCRIPTION
			"This table contains the counters for all SIP responses to the Info requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
		::=  { sip  13 }

	bwUCConnectSipStatsNotifyResponsesTable	OBJECT-TYPE
		SYNTAX		SEQUENCE  OF  BwUCConnectSipStatsNotifyResponsesEntry
		MAX-ACCESS	not-accessible
		STATUS		current
		DESCRIPTION
			"This table contains the counters for all SIP responses to the Notify requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
		::=  { sip  14 }

	bwUCConnectSipStatsSubscribeResponsesTable	OBJECT-TYPE
		SYNTAX		SEQUENCE  OF  BwUCConnectSipStatsSubscribeResponsesEntry
		MAX-ACCESS	not-accessible
		STATUS		current
		DESCRIPTION
			"This table contains the counters for all SIP responses to the Subscribe requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
		::=  { sip  15 }

	bwUCConnectSipStatsMessageResponsesTable	OBJECT-TYPE
		SYNTAX		SEQUENCE  OF  BwUCConnectSipStatsMessageResponsesEntry
		MAX-ACCESS	not-accessible
		STATUS		current
		DESCRIPTION
			"This table contains the counters for all SIP responses to the Message requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
		::=  { sip  16 }

	bwUCConnectSipStatsActiveTcpConnections	OBJECT-TYPE
		SYNTAX			Gauge32
		MAX-ACCESS		read-only
		STATUS			current
		DESCRIPTION
				"This gauge is incremented whenever a SIP TCP connection is established.   It decremented whenever a connection is closed."
		::=  {  sip  18  }

	bwUCConnectSipStatsTcpIns	OBJECT-TYPE
		SYNTAX			Counter32
		MAX-ACCESS		read-write
		STATUS			current
		DESCRIPTION
				"This counter is incremented whenever a SIP message is received via TCP."
		::=  {  sip  19  }

	bwUCConnectSipStatsTcpOuts	OBJECT-TYPE
		SYNTAX			Counter32
		MAX-ACCESS		read-write
		STATUS			current
		DESCRIPTION
				"This counter is incremented whenever a SIP message is sent via TCP."
		::=  {  sip  20  }

	bwUCConnectSipStatsTcpFailures	OBJECT-TYPE
		SYNTAX			Counter32
		MAX-ACCESS		read-write
		STATUS			current
		DESCRIPTION
				"This counter is incremented whenever a SIP message was attempted to be sent via TCP but failed."
		::=  {  sip  21  }

	bwUCConnectSipStatsUdpIns	OBJECT-TYPE
		SYNTAX			Counter32
		MAX-ACCESS		read-write
		STATUS			current
		DESCRIPTION
				"This counter is incremented whenever a SIP message is received via UDP."
		::=  {  sip  22  }

	bwUCConnectSipStatsUdpOuts	OBJECT-TYPE
		SYNTAX			Counter32
		MAX-ACCESS		read-write
		STATUS			current
		DESCRIPTION
				"This counter is incremented whenever a SIP message is sent via UDP."
		::=  {  sip  23  }

  bwUCConnectSipReclaimedStaleTcpConnections OBJECT-TYPE
		SYNTAX			Counter32
		MAX-ACCESS		read-write
		STATUS			current
		DESCRIPTION
				"This counter is incremented every time a SIP TCP connection is reclaimed because it is stale."
		::=  {  sip  24  }


	congestionManagement	OBJECT IDENTIFIER
		::=  { sip  25 }


-- PROTOCOL :: SIP :: INVITE responses ................................................

	bwUCConnectSipStatsInviteResponsesEntry	OBJECT-TYPE
		SYNTAX		BwUCConnectSipStatsInviteResponsesEntry
		MAX-ACCESS	not-accessible
		STATUS		current
		DESCRIPTION
			"This row contains information on a particular SIP status code sent in response to an Invite"
		INDEX		{  bwUCConnectSipStatsInviteResponseCodeValue  }
		::=  { bwUCConnectSipStatsInviteResponsesTable 1 }

	BwUCConnectSipStatsInviteResponsesEntry  ::=  SEQUENCE {
		bwUCConnectSipStatsInviteResponseCodeValue  Integer32,
		bwUCConnectSipStatsInviteResponseOuts  Counter32
		}

	bwUCConnectSipStatsInviteResponseCodeValue	OBJECT-TYPE
		SYNTAX			Integer32  ( 100 .. 999  )
		MAX-ACCESS		not-accessible
		STATUS			current
		DESCRIPTION
				"This integer represents a SIP status code.  The rest of the information in this row is related to this value."
		::=  {  bwUCConnectSipStatsInviteResponsesEntry  1  }

	bwUCConnectSipStatsInviteResponseOuts	OBJECT-TYPE
		SYNTAX			Counter32
		MAX-ACCESS		read-write
		STATUS			current
		DESCRIPTION
				"This counter represents the number of SIP responses sent in response to an Invite"
		::=  {  bwUCConnectSipStatsInviteResponsesEntry  3  }

-- PROTOCOL :: SIP :: OPTION responses ................................................

	bwUCConnectSipStatsOptionsResponsesEntry	OBJECT-TYPE
		SYNTAX		BwUCConnectSipStatsOptionsResponsesEntry
		MAX-ACCESS	not-accessible
		STATUS		current
		DESCRIPTION
			"This row contains information on a particular SIP status code received or sent in response to a Options"
		INDEX		{  bwUCConnectSipStatsOptionsResponseCodeValue  }
		::=  { bwUCConnectSipStatsOptionsResponsesTable 1 }

	BwUCConnectSipStatsOptionsResponsesEntry  ::=  SEQUENCE {
		bwUCConnectSipStatsOptionsResponseCodeValue  Integer32,
		bwUCConnectSipStatsOptionsResponseIns  Counter32,
		bwUCConnectSipStatsOptionsResponseOuts  Counter32
		}


	bwUCConnectSipStatsOptionsResponseCodeValue	OBJECT-TYPE
		SYNTAX			Integer32  ( 100 .. 999  )
		MAX-ACCESS		not-accessible
		STATUS			current
		DESCRIPTION
				"This integer represents a SIP status code.  The rest of the information in this row is related to this value."
		::=  {  bwUCConnectSipStatsOptionsResponsesEntry  1  }


	bwUCConnectSipStatsOptionsResponseIns	OBJECT-TYPE
		SYNTAX			Counter32
		MAX-ACCESS		read-write
		STATUS			current
		DESCRIPTION
				"This counter represents the number of SIP responses received in response to an Options"
		::=  {  bwUCConnectSipStatsOptionsResponsesEntry  2  }


	bwUCConnectSipStatsOptionsResponseOuts	OBJECT-TYPE
		SYNTAX			Counter32
		MAX-ACCESS		read-write
		STATUS			current
		DESCRIPTION
				"This counter represents the number of SIP responses sent in response to an Options"
		::=  {  bwUCConnectSipStatsOptionsResponsesEntry  3  }

-- PROTOCOL :: SIP :: REGISTER responses ................................................

	bwUCConnectSipStatsRegisterResponsesEntry	OBJECT-TYPE
		SYNTAX		BwUCConnectSipStatsRegisterResponsesEntry
		MAX-ACCESS	not-accessible
		STATUS		current
		DESCRIPTION
			"This row contains information on a particular SIP status code received or sent in response to a Register"
		INDEX		{  bwUCConnectSipStatsRegisterResponseCodeValue  }
		::=  { bwUCConnectSipStatsRegisterResponsesTable 1 }

	BwUCConnectSipStatsRegisterResponsesEntry  ::=  SEQUENCE {
		bwUCConnectSipStatsRegisterResponseCodeValue  Integer32,
		bwUCConnectSipStatsRegisterResponseIns  Counter32,
		bwUCConnectSipStatsRegisterResponseOuts  Counter32
		}


	bwUCConnectSipStatsRegisterResponseCodeValue	OBJECT-TYPE
		SYNTAX			Integer32  ( 100 .. 999  )
		MAX-ACCESS		not-accessible
		STATUS			current
		DESCRIPTION
				"This integer represents a SIP status code.  The rest of the information in this row is related to this value."
		::=  {  bwUCConnectSipStatsRegisterResponsesEntry  1  }


	bwUCConnectSipStatsRegisterResponseIns	OBJECT-TYPE
		SYNTAX			Counter32
		MAX-ACCESS		read-write
		STATUS			current
		DESCRIPTION
				"This counter represents the number of SIP responses received in response to a Register"
		::=  {  bwUCConnectSipStatsRegisterResponsesEntry  2  }


	bwUCConnectSipStatsRegisterResponseOuts	OBJECT-TYPE
		SYNTAX			Counter32
		MAX-ACCESS		read-write
		STATUS			current
		DESCRIPTION
				"This counter represents the number of SIP responses sent in response to a Register"
		::=  {  bwUCConnectSipStatsRegisterResponsesEntry  3  }

-- PROTOCOL :: SIP :: INFO responses ................................................

	bwUCConnectSipStatsInfoResponsesEntry	OBJECT-TYPE
		SYNTAX		BwUCConnectSipStatsInfoResponsesEntry
		MAX-ACCESS	not-accessible
		STATUS		current
		DESCRIPTION
			"This row contains information on a particular SIP status code received or sent in response to an Info"
		INDEX		{  bwUCConnectSipStatsInfoResponseCodeValue  }
		::=  { bwUCConnectSipStatsInfoResponsesTable 1 }

	BwUCConnectSipStatsInfoResponsesEntry  ::=  SEQUENCE {
		bwUCConnectSipStatsInfoResponseCodeValue  Integer32,
		bwUCConnectSipStatsInfoResponseIns  Counter32,
		bwUCConnectSipStatsInfoResponseOuts  Counter32
		}


	bwUCConnectSipStatsInfoResponseCodeValue	OBJECT-TYPE
		SYNTAX			Integer32  ( 100 .. 999  )
		MAX-ACCESS		not-accessible
		STATUS			current
		DESCRIPTION
				"This integer represents a SIP status code.  The rest of the information in this row is related to this value."
		::=  {  bwUCConnectSipStatsInfoResponsesEntry  1  }


	bwUCConnectSipStatsInfoResponseIns	OBJECT-TYPE
		SYNTAX			Counter32
		MAX-ACCESS		read-write
		STATUS			current
		DESCRIPTION
				"This counter represents the number of SIP responses received in response to an Info"
		::=  {  bwUCConnectSipStatsInfoResponsesEntry  2  }


	bwUCConnectSipStatsInfoResponseOuts	OBJECT-TYPE
		SYNTAX			Counter32
		MAX-ACCESS		read-write
		STATUS			current
		DESCRIPTION
				"This counter represents the number of SIP responses sent in response to an Info"
		::=  {  bwUCConnectSipStatsInfoResponsesEntry  3  }

-- PROTOCOL :: SIP :: NOTIFY responses ................................................

	bwUCConnectSipStatsNotifyResponsesEntry	OBJECT-TYPE
		SYNTAX		BwUCConnectSipStatsNotifyResponsesEntry
		MAX-ACCESS	not-accessible
		STATUS		current
		DESCRIPTION
			"This row contains information on a particular SIP status code received or sent in response to an Notify"
		INDEX		{  bwUCConnectSipStatsNotifyResponseCodeValue  }
		::=  { bwUCConnectSipStatsNotifyResponsesTable 1 }

	BwUCConnectSipStatsNotifyResponsesEntry  ::=  SEQUENCE {
		bwUCConnectSipStatsNotifyResponseCodeValue  Integer32,
		bwUCConnectSipStatsNotifyResponseIns  Counter32,
		bwUCConnectSipStatsNotifyResponseOuts  Counter32
		}


	bwUCConnectSipStatsNotifyResponseCodeValue	OBJECT-TYPE
		SYNTAX			Integer32  ( 100 .. 999  )
		MAX-ACCESS		not-accessible
		STATUS			current
		DESCRIPTION
				"This integer represents a SIP status code.  The rest of the information in this row is related to this value."
		::=  {  bwUCConnectSipStatsNotifyResponsesEntry  1  }


	bwUCConnectSipStatsNotifyResponseIns	OBJECT-TYPE
		SYNTAX			Counter32
		MAX-ACCESS		read-write
		STATUS			current
		DESCRIPTION
				"This counter represents the number of SIP responses received in response to a Notify"
		::=  {  bwUCConnectSipStatsNotifyResponsesEntry  2  }


	bwUCConnectSipStatsNotifyResponseOuts	OBJECT-TYPE
		SYNTAX			Counter32
		MAX-ACCESS		read-write
		STATUS			current
		DESCRIPTION
				"This counter represents the number of SIP responses sent in response to a Notify"
		::=  {  bwUCConnectSipStatsNotifyResponsesEntry  3  }

-- PROTOCOL :: SIP :: SUBSCRIBE responses ................................................

	bwUCConnectSipStatsSubscribeResponsesEntry	OBJECT-TYPE
		SYNTAX		BwUCConnectSipStatsSubscribeResponsesEntry
		MAX-ACCESS	not-accessible
		STATUS		current
		DESCRIPTION
			"This row contains information on a particular SIP status code received or sent in response to a Subscribe"
		INDEX		{  bwUCConnectSipStatsSubscribeResponseCodeValue  }
		::=  { bwUCConnectSipStatsSubscribeResponsesTable 1 }

	BwUCConnectSipStatsSubscribeResponsesEntry  ::=  SEQUENCE {
		bwUCConnectSipStatsSubscribeResponseCodeValue  Integer32,
		bwUCConnectSipStatsSubscribeResponseIns  Counter32,
		bwUCConnectSipStatsSubscribeResponseOuts  Counter32
		}


	bwUCConnectSipStatsSubscribeResponseCodeValue	OBJECT-TYPE
		SYNTAX			Integer32  ( 100 .. 999  )
		MAX-ACCESS		not-accessible
		STATUS			current
		DESCRIPTION
				"This integer represents a SIP status code.  The rest of the information in this row is related to this value."
		::=  {  bwUCConnectSipStatsSubscribeResponsesEntry  1  }


	bwUCConnectSipStatsSubscribeResponseIns	OBJECT-TYPE
		SYNTAX			Counter32
		MAX-ACCESS		read-write
		STATUS			current
		DESCRIPTION
				"This counter represents the number of SIP responses received in response to a Subscribe"
		::=  {  bwUCConnectSipStatsSubscribeResponsesEntry  2  }


	bwUCConnectSipStatsSubscribeResponseOuts	OBJECT-TYPE
		SYNTAX			Counter32
		MAX-ACCESS		read-write
		STATUS			current
		DESCRIPTION
				"This counter represents the number of SIP responses sent in response to a Subscribe"
		::=  {  bwUCConnectSipStatsSubscribeResponsesEntry  3  }


-- PROTOCOL :: SIP :: MESSAGE responses ................................................

	bwUCConnectSipStatsMessageResponsesEntry	OBJECT-TYPE
		SYNTAX		BwUCConnectSipStatsMessageResponsesEntry
		MAX-ACCESS	not-accessible
		STATUS		current
		DESCRIPTION
			"This row contains information on a particular SIP status code received or sent in response to a Message"
		INDEX		{  bwUCConnectSipStatsMessageResponseCodeValue  }
		::=  { bwUCConnectSipStatsMessageResponsesTable 1 }

	BwUCConnectSipStatsMessageResponsesEntry  ::=  SEQUENCE {
		bwUCConnectSipStatsMessageResponseCodeValue  Integer32,
		bwUCConnectSipStatsMessageResponseIns  Counter32,
		bwUCConnectSipStatsMessageResponseOuts  Counter32
		}


	bwUCConnectSipStatsMessageResponseCodeValue	OBJECT-TYPE
		SYNTAX			Integer32  ( 100 .. 999  )
		MAX-ACCESS		not-accessible
		STATUS			current
		DESCRIPTION
				"This integer represents a SIP status code.  The rest of the information in this row is related to this value."
		::=  {  bwUCConnectSipStatsMessageResponsesEntry  1  }


	bwUCConnectSipStatsMessageResponseIns	OBJECT-TYPE
		SYNTAX			Counter32
		MAX-ACCESS		read-write
		STATUS			current
		DESCRIPTION
				"This counter represents the number of SIP responses received in response to a Message"
		::=  {  bwUCConnectSipStatsMessageResponsesEntry  2  }


	bwUCConnectSipStatsMessageResponseOuts	OBJECT-TYPE
		SYNTAX			Counter32
		MAX-ACCESS		read-write
		STATUS			current
		DESCRIPTION
				"This counter represents the number of SIP responses sent in response to a Message"
		::=  {  bwUCConnectSipStatsMessageResponsesEntry  3  }

-- PROTOCOL :: BCCT Protocol ...............................

	bwUCConnectCommonCommStats OBJECT IDENTIFIER
		::=  { protocol 2 }

	bwUCConnectCommonCommStatsTable	OBJECT-TYPE
		SYNTAX		SEQUENCE  OF  BwUCConnectCommonCommStatsEntry
		MAX-ACCESS	not-accessible
		STATUS		current
		DESCRIPTION
			"This table contains counters for BCCT for the UC-Connect Application."
		::=  { bwUCConnectCommonCommStats 1 }

	bwUCConnectCommonCommStatsEntry	OBJECT-TYPE
		SYNTAX		BwUCConnectCommonCommStatsEntry
		MAX-ACCESS	not-accessible
		STATUS		current
		DESCRIPTION
			"Definition of the entries for bwUCConnectCommonCommStatsTable."
		INDEX		{  bwUCConnectCommonCommStatsIndex  }
		::=  { bwUCConnectCommonCommStatsTable 1 }

	BwUCConnectCommonCommStatsEntry  ::=  SEQUENCE {
		bwUCConnectCommonCommStatsIndex  Unsigned32,
		bwUCConnectCommonCommHost  DisplayString,
		bwUCConnectCommonCommInterface  DisplayString,
		bwUCConnectCommonCommProtocol  DisplayString,
		bwUCConnectCommonCommAcceptedOutboundConnections  Counter32,
		bwUCConnectCommonCommAcceptedInboundConnections  Counter32,
		bwUCConnectCommonCommRejectedOutboundConnections  Counter32,
		bwUCConnectCommonCommRejectedInboundConnections  Counter32,
		bwUCConnectCommonCommOutputMessagesProcessed  Counter32,
		bwUCConnectCommonCommInputMessagesProcessed  Counter32,
		bwUCConnectCommonCommOutputCommunicationErrors  Counter32,
		bwUCConnectCommonCommInputCommunicationErrors  Counter32
		}

	bwUCConnectCommonCommStatsIndex	OBJECT-TYPE
		SYNTAX			Unsigned32
		MAX-ACCESS		read-only
		STATUS			current
		DESCRIPTION
				"This integer represents an index in table bwUCConnectCommonCommStatsTable. The index represents a connection for a specific Host-Interfacece-Protocol combination."
		::=  {  bwUCConnectCommonCommStatsEntry  1  }

	bwUCConnectCommonCommHost	OBJECT-TYPE
		SYNTAX			DisplayString
		MAX-ACCESS		read-only
		STATUS			current
		DESCRIPTION
				"The address of a host connected to the BroadWorks Common Communication Protocol."
		::=  {  bwUCConnectCommonCommStatsEntry  2  }


	bwUCConnectCommonCommInterface	OBJECT-TYPE
		SYNTAX			DisplayString
		MAX-ACCESS		read-only
		STATUS			current
		DESCRIPTION
				"The IP address of a local interface that a protocol is bound to."
		::=  {  bwUCConnectCommonCommStatsEntry  3  }

	bwUCConnectCommonCommProtocol	OBJECT-TYPE
		SYNTAX			DisplayString
		MAX-ACCESS		read-only
		STATUS			current
		DESCRIPTION
				"The name of a BroadWorks Common Communication Protocol client protocol, e.g. OCI or SyncApi."
		::=  {  bwUCConnectCommonCommStatsEntry  4  }

	bwUCConnectCommonCommAcceptedOutboundConnections	OBJECT-TYPE
		SYNTAX			Counter32
		MAX-ACCESS		read-write
		STATUS			current
		DESCRIPTION
				"This counter is incremented whenever a client in this process connects to the framework to a remote host, using the interface and protocol."
		::=  {  bwUCConnectCommonCommStatsEntry  5  }

	bwUCConnectCommonCommAcceptedInboundConnections	OBJECT-TYPE
		SYNTAX			Counter32
		MAX-ACCESS		read-write
		STATUS			current
		DESCRIPTION
				"This counter is incremented whenever a client in this process connects to the framework from a remote host, using the interface and protocol."
		::=  {  bwUCConnectCommonCommStatsEntry  6  }

	bwUCConnectCommonCommRejectedOutboundConnections	OBJECT-TYPE
		SYNTAX			Counter32
		MAX-ACCESS		read-write
		STATUS			current
		DESCRIPTION
				"This counter is incremented whenever a client connection request going from this process to a remote host and going through this interface has been rejected for a particular protocol."
		::=  {  bwUCConnectCommonCommStatsEntry  7  }

	bwUCConnectCommonCommRejectedInboundConnections	OBJECT-TYPE
		SYNTAX			Counter32
		MAX-ACCESS		read-write
		STATUS			current
		DESCRIPTION
				"This counter is incremented whenever a client connection request coming to this host and going through this interface has been rejected by the framework for a particular protocol."
		::=  {  bwUCConnectCommonCommStatsEntry  8  }

	bwUCConnectCommonCommOutputMessagesProcessed	OBJECT-TYPE
		SYNTAX			Counter32
		MAX-ACCESS		read-write
		STATUS			current
		DESCRIPTION
				"This counter is incremented whenever a message has been sent and processed for this host, interface and protocol."
		::=  {  bwUCConnectCommonCommStatsEntry  9  }

	bwUCConnectCommonCommInputMessagesProcessed	OBJECT-TYPE
		SYNTAX			Counter32
		MAX-ACCESS		read-write
		STATUS			current
		DESCRIPTION
				"This counter is incremented whenever a message has been received and processed for this host, interface and protocol."
		::=  {  bwUCConnectCommonCommStatsEntry  10  }

	bwUCConnectCommonCommOutputCommunicationErrors	OBJECT-TYPE
		SYNTAX			Counter32
		MAX-ACCESS		read-write
		STATUS			current
		DESCRIPTION
				"This counter is incremented whenever a message could not be read because the TCP stack returned an error."
		::=  {  bwUCConnectCommonCommStatsEntry  11  }

	bwUCConnectCommonCommInputCommunicationErrors	OBJECT-TYPE
		SYNTAX			Counter32
		MAX-ACCESS		read-write
		STATUS			current
		DESCRIPTION
				"This counter is incremented whenever a message has been sent and processed for this host, interface and protocol."
		::=  {  bwUCConnectCommonCommStatsEntry  12  }

-- MODULE - CAP Client
  bwUCConnectCapConnectionTable OBJECT-TYPE
    SYNTAX    SEQUENCE  OF  BwUCConnectCapConnectionEntry
    MAX-ACCESS  not-accessible
    STATUS    current
    DESCRIPTION
      "This table contains CAP Connection statistics."
    ::=  { capStats 1 }

  bwUCConnectCapConnectionEntry  OBJECT-TYPE
    SYNTAX    BwUCConnectCapConnectionEntry
    MAX-ACCESS  not-accessible
    STATUS    current
    DESCRIPTION
      "This row contains information on a particular CAP connection."
    INDEX { bwUCConnectCapClientConnectionIndex }
    ::= { bwUCConnectCapConnectionTable 1 }

  BwUCConnectCapConnectionEntry  ::=  SEQUENCE {
    bwUCConnectCapClientConnectionIndex Unsigned32,
    bwUCConnectCapClientConnectionState INTEGER,
    bwUCConnectCapClientSessionCountPerConnection Gauge32,
    bwUCConnectCapClientIncomingMessageCountPerConnection Gauge32, 
    bwUCConnectCapClientOutgoingMessageCountPerConnection Gauge32
  }

  bwUCConnectCapClientConnectionIndex OBJECT-TYPE 
    SYNTAX Unsigned32
    MAX-ACCESS read-only
    STATUS current
    DESCRIPTION   
      "This column is the index for the table."
    ::= { bwUCConnectCapConnectionEntry 1 }

  bwUCConnectCapClientConnectionState OBJECT-TYPE
    SYNTAX INTEGER { opening(0), opened(1), closed(2), inactive(3) }
    MAX-ACCESS read-only
    STATUS current
    DESCRIPTION   
      "The state of the CAP connection specified by the index."
    ::= { bwUCConnectCapConnectionEntry 2 }

  bwUCConnectCapClientSessionCountPerConnection OBJECT-TYPE
    SYNTAX Gauge32
    MAX-ACCESS read-only
    STATUS current
    DESCRIPTION   
      "The number of active CAP session over the connection specified by the index."
    ::= { bwUCConnectCapConnectionEntry 3 }

  bwUCConnectCapClientIncomingMessageCountPerConnection OBJECT-TYPE
    SYNTAX Gauge32
    MAX-ACCESS read-only
    STATUS current
    DESCRIPTION   
      "The number of CAP messages received over a specific CAP connection identified by the index."
    ::= { bwUCConnectCapConnectionEntry 4 }

  bwUCConnectCapClientOutgoingMessageCountPerConnection OBJECT-TYPE
    SYNTAX Gauge32
    MAX-ACCESS read-only
    STATUS current
    DESCRIPTION   
      "The number of CAP messages sent over a specific CAP connection identified by the index."
    ::= { bwUCConnectCapConnectionEntry 5 }

  bwUCConnectCapClientConnectionCount OBJECT-TYPE
    SYNTAX Gauge32
    MAX-ACCESS read-only
    STATUS current
    DESCRIPTION   
      "The number of active CAP connections (i.e. in the Opening, Opened or Closed state)."
    ::= { capStats 2 }

  bwUCConnectCapClientSessionCountTotal OBJECT-TYPE
    SYNTAX Gauge32
    MAX-ACCESS read-only
    STATUS current
    DESCRIPTION   
      "The number of active CAP sessions over all connections."
      ::= { capStats 3 }

  bwUCConnectCapClientIncomingMessageCountTotal OBJECT-TYPE
    SYNTAX Gauge32
    MAX-ACCESS read-only
    STATUS current
    DESCRIPTION   
      "The number of CAP messages received over all CAP connections."
    ::= { capStats 4 }

  bwUCConnectCapClientOutgoingMessageCountTotal OBJECT-TYPE
    SYNTAX Gauge32
    MAX-ACCESS read-only
    STATUS current
    DESCRIPTION   
      "The number of CAP messages sent over all CAP connections."
    ::= { capStats 5 }

-- MODULE - Location API Client
  bwUCConnectLocationApiClientConnectionTable OBJECT-TYPE
    SYNTAX SEQUENCE OF BwUCConnectLocationApiClientConnectionEntry
    MAX-ACCESS  not-accessible
    STATUS    current
    DESCRIPTION
      "This table contains DNS statistics."
    ::=  { locationApiStats 1 }

  bwUCConnectLocationApiClientConnectionEntry  OBJECT-TYPE
    SYNTAX    BwUCConnectLocationApiClientConnectionEntry
    MAX-ACCESS  not-accessible
    STATUS    current
    DESCRIPTION
      "This row contains information on a particular Location API client connection."
    INDEX { bwUCConnectLocationApiClientConnectionIndex }
    ::= { bwUCConnectLocationApiClientConnectionTable 1 }

  BwUCConnectLocationApiClientConnectionEntry ::=  SEQUENCE {
    bwUCConnectLocationApiClientConnectionIndex Unsigned32,
    bwUCConnectLocationApiClientConnectionName DisplayString,
    bwUCConnectLocationApiClientAttemptPerConnection Counter32,
    bwUCConnectLocationApiClientSuccessPerConnection Counter32
  }

  bwUCConnectLocationApiClientConnectionIndex OBJECT-TYPE
    SYNTAX Unsigned32
    MAX-ACCESS read-only
    STATUS current
    DESCRIPTION   
      "This column is the index for the table."
    ::= { bwUCConnectLocationApiClientConnectionEntry 1 }

  bwUCConnectLocationApiClientConnectionName OBJECT-TYPE
    SYNTAX DisplayString
    MAX-ACCESS read-only
    STATUS current
    DESCRIPTION   
      "This is the name of the Network Server or Location Server."
    ::= { bwUCConnectLocationApiClientConnectionEntry 2 }

  bwUCConnectLocationApiClientAttemptPerConnection OBJECT-TYPE
    SYNTAX Counter32
    MAX-ACCESS read-write
    STATUS current
    DESCRIPTION   
      "The number of Location API queries attempted with the specific server identified by the index."
    ::= { bwUCConnectLocationApiClientConnectionEntry 3 }

  bwUCConnectLocationApiClientSuccessPerConnection OBJECT-TYPE
    SYNTAX Counter32
    MAX-ACCESS read-write
    STATUS current
    DESCRIPTION   
      "The number of Location API queries successfully answered by the specific server identified by the index."
    ::= { bwUCConnectLocationApiClientConnectionEntry 4 }

  bwUCConnectLocationApiClientAttemptTotal OBJECT-TYPE
    SYNTAX Counter32
    MAX-ACCESS read-write
    STATUS current
    DESCRIPTION   
      "The total number of Location API queries attempted."
    ::= { locationApiStats 2 }

  bwUCConnectLocationApiClientSuccessTotal OBJECT-TYPE
    SYNTAX Counter32
    MAX-ACCESS read-write
    STATUS current
    DESCRIPTION   
      "The total number of Location API queries successfully answered by any server."
    ::= { locationApiStats 3 }

-- MODULE - CSTA Statistics
  bwCstaActiveSessions OBJECT-TYPE
    SYNTAX Gauge32
    MAX-ACCESS read-only
    STATUS current
    DESCRIPTION   
      "Number of current active sessions."
    ::= { cstaStats 1 }

  bwCstaActiveCalls OBJECT-TYPE
    SYNTAX Gauge32
    MAX-ACCESS read-only
    STATUS current
    DESCRIPTION   
      "Number of current active Calls among all CSTA sessions."
    ::= { cstaStats 2 }

  bwCstaActiveConferences OBJECT-TYPE
    SYNTAX Gauge32
    MAX-ACCESS read-only
    STATUS current
    DESCRIPTION   
      "Number of current active Conferences among all CSTA sessions."
    ::= { cstaStats 3 }

  bwCstaSuccessfulRegistrationsTotal OBJECT-TYPE
    SYNTAX Counter32
    MAX-ACCESS read-only
    STATUS current
    DESCRIPTION   
      "Total number of successful registrations."
    ::= { cstaStats 4 }

  bwCstaFailedRegistrationsTotal OBJECT-TYPE
    SYNTAX Counter32
    MAX-ACCESS read-only
    STATUS current
    DESCRIPTION   
      "Total number of failed registrations."
    ::= { cstaStats 5 }

  bwCstaCompletedSessionsTotal OBJECT-TYPE
    SYNTAX Counter32
    MAX-ACCESS read-only
    STATUS current
    DESCRIPTION   
      "Total number of completed sessions."
    ::= { cstaStats 6 }

  bwCstaIncomingMessagesTotal OBJECT-TYPE
    SYNTAX Counter32
    MAX-ACCESS read-only
    STATUS current
    DESCRIPTION   
      "Total number of incoming CSTA messages."
    ::= { cstaStats 7 }

  bwCstaOutgoingMessagesTotal OBJECT-TYPE
    SYNTAX Counter32
    MAX-ACCESS read-only
    STATUS current
    DESCRIPTION   
      "Total number of outgoing CSTA messages."
    ::= { cstaStats 8 }

  bwCstaMalformedCSTAMessagesTotal OBJECT-TYPE
    SYNTAX Counter32
    MAX-ACCESS read-only
    STATUS current
    DESCRIPTION   
      "Total number of  malformed CSTA messages received."
    ::= { cstaStats 9 }

  bwCstaMalformedCAPMessagesTotal OBJECT-TYPE
    SYNTAX Counter32
    MAX-ACCESS read-only
    STATUS current
    DESCRIPTION   
      "Total number of  malformed CAP messages received."
    ::= { cstaStats 10 }

  bwCstaCallsMadeTotal OBJECT-TYPE
    SYNTAX Counter32
    MAX-ACCESS read-only
    STATUS current
    DESCRIPTION   
      "Total number calls originated from CSTA."
    ::= { cstaStats 11 }

  bwCstaCallsAnsweredTotal OBJECT-TYPE
    SYNTAX Counter32
    MAX-ACCESS read-only
    STATUS current
    DESCRIPTION   
      "Total number of calls answered from CSTA."
    ::= { cstaStats 12 }

  bwCstaCallsHeldTotal OBJECT-TYPE
    SYNTAX Counter32
    MAX-ACCESS read-only
    STATUS current
    DESCRIPTION   
      "Total number of calls held from CSTA."
    ::= { cstaStats 13 }

  bwCstaCallsResumedTotal OBJECT-TYPE
    SYNTAX Counter32
    MAX-ACCESS read-only
    STATUS current
    DESCRIPTION   
      "Total number of calls resumed from CSTA."
    ::= { cstaStats 14 }

  bwCstaCallsReleasedTotal OBJECT-TYPE
    SYNTAX Counter32
    MAX-ACCESS read-only
    STATUS current
    DESCRIPTION   
      "Total number of calls released from CSTA."
    ::= { cstaStats 15 }

  bwCstaCallsRedirectedTotal OBJECT-TYPE
    SYNTAX Counter32
    MAX-ACCESS read-only
    STATUS current
    DESCRIPTION   
      "Total number of calls redirected from CSTA."
    ::= { cstaStats 16 }

  bwCstaCallsTransferredTotal OBJECT-TYPE
    SYNTAX Counter32
    MAX-ACCESS read-only
    STATUS current
    DESCRIPTION   
      "Total number of calls transferred from CSTA."
    ::= { cstaStats 17 }

  bwCstaConferencesTotal OBJECT-TYPE
    SYNTAX Counter32
    MAX-ACCESS read-only
    STATUS current
    DESCRIPTION   
      "Total number of conferences originated from CSTA."
    ::= { cstaStats 18 }

-- MODULE - Session Audit
  bwSessionAuditNumEndpointsAudited OBJECT-TYPE
    SYNTAX Counter32
    MAX-ACCESS read-write
    STATUS current
    DESCRIPTION "This is the number of times UC-Connect audits a SIP endpoint."
      ::= { sessionAudit 1 }

  bwSessionAuditNumEndpointsFailedAudit OBJECT-TYPE
    SYNTAX Counter32
    MAX-ACCESS read-write
    STATUS current
    DESCRIPTION "This is the number of times UC-Connect audits failed."
      ::= { sessionAudit 2 }

-- MODULE - Internal Stats
  bwUCConnectInternalQueueResets OBJECT-TYPE
    SYNTAX Counter32
    MAX-ACCESS read-write
    STATUS current
    DESCRIPTION "When set to a value other then 0, all the internal queue statistic stored under bwUCConnectInternalQueueTable are reset to 0."
      ::= { internalStats 1 }

  bwUCConnectInternalQueueTable OBJECT-TYPE
    SYNTAX SEQUENCE OF BwUCConnectInternalQueueEntry
    MAX-ACCESS not-accessible
    STATUS current
    DESCRIPTION
      "This table contains statistics about the BroadWorks internal queues."
    ::= { internalStats 2 }

  bwUCConnectInternalQueueEntry OBJECT-TYPE
    SYNTAX BwUCConnectInternalQueueEntry
    MAX-ACCESS not-accessible
    STATUS current
    DESCRIPTION
      "This row contains the statistics for a given internal queue in the system"
    INDEX { bwUCConnectInternalQueueIndex }
    ::= { bwUCConnectInternalQueueTable 1 }

    BwUCConnectInternalQueueEntry ::= SEQUENCE 
    {
      bwUCConnectInternalQueueIndex Unsigned32,
      bwUCConnectInternalQueueName DisplayString,
      bwUCConnectInternalQueueSize Counter32,
      bwUCConnectInternalQueueTimeAvg Gauge32,
      bwUCConnectInternalQueueTimeMin Gauge32,
      bwUCConnectInternalQueueTimeMax Gauge32,
      bwUCConnectInternalQueueLengthCurrent Gauge32,
      bwUCConnectInternalQueueLengthAvg Gauge32,
      bwUCConnectInternalQueueLengthMax Gauge32,
      bwUCConnectInternalQueueTimeMaxTimestampMSB Gauge32,
      bwUCConnectInternalQueueLengthMaxTimestampMSB Gauge32,
      bwUCConnectInternalQueueLengthMaxTimestampLSB Gauge32,
      bwUCConnectInternalQueueTimeMaxTimestampLSB Gauge32
    }

  bwUCConnectInternalQueueIndex OBJECT-TYPE
    SYNTAX Unsigned32
    MAX-ACCESS read-only
    STATUS current
    DESCRIPTION
      "This integer represents an index to an internal queue in the application."
    ::= { bwUCConnectInternalQueueEntry 1 }

  bwUCConnectInternalQueueName OBJECT-TYPE
    SYNTAX DisplayString
    MAX-ACCESS read-only
    STATUS current
    DESCRIPTION
      "This string represents the name of an internal queue."
    ::= { bwUCConnectInternalQueueEntry 2 }

  bwUCConnectInternalQueueSize OBJECT-TYPE
    SYNTAX Counter32
    MAX-ACCESS read-only
    STATUS current
    DESCRIPTION
      "The number of sample elements that the average, minimum and maximum holding time were calculated from."
    ::= { bwUCConnectInternalQueueEntry 3 }

  bwUCConnectInternalQueueTimeAvg OBJECT-TYPE
    SYNTAX Gauge32
    MAX-ACCESS read-only
    STATUS current
    DESCRIPTION
      "The average queue holding time. Note that this value is in 1/1000 of millisec, i.e. divide by 1000 to get the value in milliseconds."
    ::= { bwUCConnectInternalQueueEntry 4 }

  bwUCConnectInternalQueueTimeMin OBJECT-TYPE
    SYNTAX Gauge32
    MAX-ACCESS read-only
    STATUS current
    DESCRIPTION
      "The smallest queue sample holding time."
    ::= { bwUCConnectInternalQueueEntry 5 }

  bwUCConnectInternalQueueTimeMax OBJECT-TYPE
    SYNTAX Gauge32
    MAX-ACCESS read-only
    STATUS current
    DESCRIPTION
      "The biggest queue sample holding time."
    ::= { bwUCConnectInternalQueueEntry 6 }

  bwUCConnectInternalQueueLengthCurrent OBJECT-TYPE
    SYNTAX Gauge32
    MAX-ACCESS read-only
    STATUS current
    DESCRIPTION
      "The number of elements currently hold in the queue."
    ::= { bwUCConnectInternalQueueEntry 7 }

  bwUCConnectInternalQueueLengthAvg OBJECT-TYPE
    SYNTAX Gauge32
    MAX-ACCESS read-only
    STATUS current
    DESCRIPTION
      "The average number of elements simultaneously held in the queue multiple by 1000. Divide by 1000 to get the value in units."
    ::= { bwUCConnectInternalQueueEntry 8 }

  bwUCConnectInternalQueueLengthMax OBJECT-TYPE
    SYNTAX Gauge32
    MAX-ACCESS read-only
    STATUS current
    DESCRIPTION
      "The maximum number of elements simultaneously held in the queue multiple by 1000. Divide by 1000 to get the value in units."
    ::= { bwUCConnectInternalQueueEntry 9 }

  bwUCConnectInternalQueueTimeMaxTimestampMSB OBJECT-TYPE
    SYNTAX Gauge32
    MAX-ACCESS read-only
    STATUS current
    DESCRIPTION
      "The most significant part of the timestamp (4 most significant bytes) of when bwUCConnectInternalQueueTimeMax was obtained."
    ::= { bwUCConnectInternalQueueEntry 10 }

  bwUCConnectInternalQueueLengthMaxTimestampMSB  OBJECT-TYPE
    SYNTAX      Gauge32
    MAX-ACCESS    read-only
    STATUS      current
                DESCRIPTION
                                "The most significant part of the timestamp (4 most significant bytes) of when bwUCConnectInternalQueueLengthMax was obtained."
                ::=  {  bwUCConnectInternalQueueEntry  11 }
                
  bwUCConnectInternalQueueLengthMaxTimestampLSB  OBJECT-TYPE
    SYNTAX      Gauge32
    MAX-ACCESS    read-only
    STATUS      current
                DESCRIPTION
                                "The least significant part of the timestamp (4 least significant bytes) of when bwUCConnectInternalQueueLengthMax was obtained."
    ::=  {  bwUCConnectInternalQueueEntry  12 }    
                
  bwUCConnectInternalQueueTimeMaxTimestampLSB  OBJECT-TYPE
    SYNTAX      Gauge32
    MAX-ACCESS    read-only
    STATUS      current
                DESCRIPTION
                                "The least significant part of the timestamp (4 least significant bytes) of when bwUCConnectInternalQueueTimeMax was obtained."
                ::=  {  bwUCConnectInternalQueueEntry  13 }

-- MODULE - Call Overload Stats
  bwUCConnectCurrentCallOverloadZone OBJECT-TYPE
    SYNTAX DisplayString
    MAX-ACCESS read-only
    STATUS current
    DESCRIPTION "The current call related overload zone. Value is a string indicating Green, Yellow, or Red."
      ::= { overloadStats 1 }

  bwUCConnectNumCallYellowZoneOverloadTrans OBJECT-TYPE
    SYNTAX Counter32
    MAX-ACCESS read-write
    STATUS current
    DESCRIPTION "The number of times that the UC-Connect application has transitioned to the call related yellow overload zone."
      ::= { overloadStats 2 }

  bwUCConnectNumCallRedZoneOverloadTrans OBJECT-TYPE
    SYNTAX Counter32
    MAX-ACCESS read-write
    STATUS current
    DESCRIPTION "The number of times that the UC-Connect application has transitioned to the call related red overload zone."
      ::= { overloadStats 3 }

  bwUCConnectNumDiscardedMessage OBJECT-TYPE
    SYNTAX Counter32
    MAX-ACCESS read-write
    STATUS current
    DESCRIPTION "The number of messages that were dropped from the SIP or MGCP decoder queues."
      ::= { overloadStats 4 }

  bwUCConnectTimeLastDiscardedMessage OBJECT-TYPE
    SYNTAX DisplayString
    MAX-ACCESS read-write
    STATUS current
    DESCRIPTION "The last time a message was dropped from the SIP or MGCP decoded queues."
      ::= { overloadStats 5 }

-- BroadWorks Common managed object MIB Conformance Definition  ...........................................

bwUCConnectMibGroups OBJECT IDENTIFIER ::= { bwUCConnectMibConformance 1 }
bwUCConnectMibCompliancy OBJECT IDENTIFIER ::= { bwUCConnectMibConformance 2 }

bwUCConnectSipStatsGroup OBJECT-GROUP
    OBJECTS { bwUCConnectSipStatsInviteIns, bwUCConnectSipStatsAckIns, bwUCConnectSipStatsCancelIns, bwUCConnectSipStatsRegisterIns, bwUCConnectSipStatsNotifyIns, bwUCConnectSipStatsSubscribeIns, bwUCConnectSipStatsMessageIns, bwUCConnectSipStatsInfoIns, bwUCConnectSipStatsOptionsIns, bwUCConnectSipStatsActiveTcpConnections, bwUCConnectSipStatsTcpIns, bwUCConnectSipStatsTcpOuts, bwUCConnectSipStatsTcpFailures, bwUCConnectSipStatsUdpIns, bwUCConnectSipStatsUdpOuts, bwUCConnectSipReclaimedStaleTcpConnections, bwUCConnectSipStatsInviteResponseOuts, bwUCConnectSipStatsOptionsResponseIns, bwUCConnectSipStatsOptionsResponseOuts, bwUCConnectSipStatsRegisterResponseIns, bwUCConnectSipStatsRegisterResponseOuts, bwUCConnectSipStatsInfoResponseIns, bwUCConnectSipStatsInfoResponseOuts, bwUCConnectSipStatsNotifyResponseIns, bwUCConnectSipStatsNotifyResponseOuts, bwUCConnectSipStatsSubscribeResponseIns, bwUCConnectSipStatsSubscribeResponseOuts, bwUCConnectSipStatsMessageResponseIns, bwUCConnectSipStatsMessageResponseOuts }
  STATUS  current
  DESCRIPTION
     "This group defines statistics for the SIP protocol."
  ::= { bwUCConnectMibGroups 1 }

bwUCConnectBcctGroup OBJECT-GROUP
    OBJECTS { bwUCConnectCommonCommStatsIndex, bwUCConnectCommonCommHost, bwUCConnectCommonCommInterface, bwUCConnectCommonCommProtocol, bwUCConnectCommonCommAcceptedOutboundConnections, bwUCConnectCommonCommAcceptedInboundConnections, bwUCConnectCommonCommRejectedOutboundConnections, bwUCConnectCommonCommRejectedInboundConnections, bwUCConnectCommonCommOutputMessagesProcessed, bwUCConnectCommonCommInputMessagesProcessed, bwUCConnectCommonCommOutputCommunicationErrors, bwUCConnectCommonCommInputCommunicationErrors }
  STATUS  current
  DESCRIPTION
     "This group defines the statistics for the BCCT protocol for the UC-Connect Application."
  ::= { bwUCConnectMibGroups 2 }

bwUCConnectCapClientGroup OBJECT-GROUP
  OBJECTS { bwUCConnectCapClientConnectionIndex, bwUCConnectCapClientConnectionState, bwUCConnectCapClientSessionCountPerConnection, bwUCConnectCapClientIncomingMessageCountPerConnection, bwUCConnectCapClientOutgoingMessageCountPerConnection, bwUCConnectCapClientConnectionCount, bwUCConnectCapClientSessionCountTotal, bwUCConnectCapClientIncomingMessageCountTotal, bwUCConnectCapClientOutgoingMessageCountTotal }
  STATUS  current
  DESCRIPTION
     "This group defines the CAP Client statistics for the UC-Connect Application."
  ::= { bwUCConnectMibGroups 3 }

bwUCConnectLocationApiClientGroup OBJECT-GROUP
  OBJECTS { bwUCConnectLocationApiClientConnectionIndex, bwUCConnectLocationApiClientConnectionName, bwUCConnectLocationApiClientAttemptPerConnection, bwUCConnectLocationApiClientSuccessPerConnection, bwUCConnectLocationApiClientAttemptTotal, bwUCConnectLocationApiClientSuccessTotal }
  STATUS  current
  DESCRIPTION
     "This group defines the CAP Client statistics for the UC-Connect Application."
  ::= { bwUCConnectMibGroups 4 }

bwUCConnectCSTAGroup OBJECT-GROUP
  OBJECTS { bwCstaActiveSessions, bwCstaActiveCalls, bwCstaActiveConferences, bwCstaSuccessfulRegistrationsTotal, bwCstaFailedRegistrationsTotal, bwCstaCompletedSessionsTotal, bwCstaIncomingMessagesTotal, bwCstaOutgoingMessagesTotal, bwCstaMalformedCSTAMessagesTotal, bwCstaMalformedCAPMessagesTotal, bwCstaCallsMadeTotal, bwCstaCallsAnsweredTotal, bwCstaCallsHeldTotal, bwCstaCallsResumedTotal, bwCstaCallsReleasedTotal, bwCstaCallsRedirectedTotal, bwCstaCallsTransferredTotal, bwCstaConferencesTotal }
  STATUS current
  DESCRIPTION
    "This group defines the CSTA statistics for the UC-Connect Application."
  ::= { bwUCConnectMibGroups 5 }

bwUCConnectSessionAuditGroup OBJECT-GROUP
  OBJECTS { bwSessionAuditNumEndpointsAudited, bwSessionAuditNumEndpointsFailedAudit }
  STATUS current
  DESCRIPTION
    "This group defines the Session Audit statistics for the UC-Connect Application."
  ::= { bwUCConnectMibGroups 6 }

bwUCConnectInternalGroup OBJECT-GROUP
  OBJECTS { bwUCConnectInternalQueueResets, bwUCConnectInternalQueueIndex, bwUCConnectInternalQueueName, bwUCConnectInternalQueueSize, bwUCConnectInternalQueueTimeAvg, bwUCConnectInternalQueueTimeMin, bwUCConnectInternalQueueTimeMax, bwUCConnectInternalQueueLengthCurrent, bwUCConnectInternalQueueLengthAvg, bwUCConnectInternalQueueLengthMax, bwUCConnectInternalQueueTimeMaxTimestampMSB, bwUCConnectInternalQueueLengthMaxTimestampMSB, bwUCConnectInternalQueueLengthMaxTimestampLSB, bwUCConnectInternalQueueTimeMaxTimestampLSB }
  STATUS current
  DESCRIPTION
    "This group defines the Internal statistics for the UC-Connect Application."
  ::= { bwUCConnectMibGroups 7 }

bwUCConnectOverloadGroup OBJECT-GROUP
  OBJECTS { bwUCConnectCurrentCallOverloadZone, bwUCConnectNumCallYellowZoneOverloadTrans, bwUCConnectNumCallRedZoneOverloadTrans, bwUCConnectNumDiscardedMessage, bwUCConnectTimeLastDiscardedMessage }
  STATUS current
  DESCRIPTION
    "This group defines the Overload statistics for the UC-Connect Application."
  ::= { bwUCConnectMibGroups 8 }

END

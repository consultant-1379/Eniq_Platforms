-- File Name : BW-CAPStackFault.mib

BW-CAPStackFault DEFINITIONS ::= BEGIN
  IMPORTS
    enterprises, MODULE-IDENTITY, NOTIFICATION-TYPE
      FROM SNMPv2-SMI
common, faultFields, identifier, timeStamp, alarmName, systemName, severity, alarmState, component, subcomponent, problemText, recommendedActionsText, correlationParameter, sccpObjId, sccpState, sccpAffectedSsn, sccpAffectedSsnSp, sccpAffectedSsnSsn, sccpConnectionId, sccpResetReason,  sccpOriginator, sccpModuleId,sccpSubModuleId, sccpMtpSap, sccpErrorCode, sccpBitMask, sccpDroppedApiId,  sccpErrorLevel, sccpErrorFlag, sccpPointCode, m3uaAsId, m3uaLocalSpId, m3uaRemSpId, m3uaState, m3uaNwSpId, m3uaAspId, m3uaOptIndParams, m3uaOptIndParamsBitmap, m3uaOptIndParamsDownCause, m3uaSgId, m3uaAssocId, m3uaNumInStreams, m3uaNumOutStreams, m3uaErrSrc, m3uaEcode, m3uaInfoLength, m3uaPInfoStr, m3uaRegStatus, m3uaDeregStatus, m3uaNewAs, m3uaDelAs, ss7pInstanceId, ss7pStackType, ss7pEcode, ss7pEntityStatus, ss7pFailureEcode, ss7pTierId, ss7pPc, ss7pPcType, ss7pSpId, ss7pNi, ss7pVariant, ss7pSapId, ss7pSsn, ss7pSsId, ss7pNumBitsInstanceId, ss7pFlag, ss7pEmStatus, ss7pEmInfoAddr, ss7pEmInfoServerPort, ss7pEmInfoMinClientPort, ss7pEmInfoMaxClientPort, ss7pInstanceType, ss7pIp, ss7pPort, ss7pIpStr, mapInstId, mapTierLevel, mapErrorCode, mapInfoLen, mapInfoStr, mapStatus, mapInstanceType, mapVariant, mapIp, mapPort, mapEmStatus, mapEmInfoAddr, mapEmInfoServerPort, mapEmInfoMinClientPort, mapEmInfoMaxClientPort, npSS7SubsystemNumber
      FROM BroadworksFault;

  broadsoft MODULE-IDENTITY
    LAST-UPDATED  "201103240000Z"
    ORGANIZATION  "Broadsoft, Inc"
    CONTACT-INFO  "Broadsoft, Inc.
220 Perry Parkway
Gaithersburg, MD  20877
301-977-9440"
    DESCRIPTION
        "This MIB defines management information that is common to all elements in a Broadworks system."
    REVISION    "201103240000Z"
                DESCRIPTION     "Creating the mib."
    ::=  {  enterprises  6431  }

  broadworks  OBJECT IDENTIFIER
    ::=  {  broadsoft  1  }

  common  OBJECT IDENTIFIER
    ::=  {  broadworks  1  }

  systemFaults  OBJECT IDENTIFIER
    ::=  {  common  1  }

  bwPMemSS7CAPLaunched  NOTIFICATION-TYPE
    OBJECTS     { identifier, timeStamp, alarmName, systemName, severity, component, subcomponent, problemText, recommendedActionsText }
    STATUS      current
    DESCRIPTION
        "This notification indicates that the emSS7CAP process has been started.
@severity:informational
@subcomponent:processmonitor
@correlationrules:bwPMemSS7CAPLaunched, bwPMemSS7CAPShutDown, bwPMemSS7CAPStarted, and bwPMemSS7CAPDeath can be correlated into a single notification.  These events have to be considered as a transition of the state machine for the management of the emSS7CAP process running on some of the BroadWorks servers."
-- @feature:158606
    ::=  {  systemFaults 10509  }

  bwPMemSS7CAPShutDown  NOTIFICATION-TYPE
    OBJECTS     { identifier, timeStamp, alarmName, systemName, severity, component, subcomponent, problemText, recommendedActionsText }
    STATUS      current
    DESCRIPTION
        "This notification indicates that the emSS7CAP process has been manually shut down.
@severity:informational
@subcomponent:processmonitor
@correlationrules:bwPMemSS7CAPLaunched, bwPMemSS7CAPShutDown, bwPMemSS7CAPStarted, and bwPMemSS7CAPDeath can be correlated into a single notification.  These events have to be considered as a transition of the state machine for the management of the emSS7CAP process running on some of the BroadWorks servers."
-- @feature:158606
    ::=  {  systemFaults 10510  }

  bwPMemSS7CAPRestarted  NOTIFICATION-TYPE
    OBJECTS     { identifier, timeStamp, alarmName, systemName, severity, component, subcomponent, problemText, recommendedActionsText }
    STATUS      current
    DESCRIPTION
        "This notification provides the date and time of the emSS7CAP process restart.
@severity:informational
@subcomponent:processmonitor
@correlationrules:bwPMemSS7CAPLaunched, bwPMemSS7CAPShutDown, bwPMemSS7CAPStarted, and bwPMemSS7CAPDeath can be correlated into a single notification.  These events have to be considered as a transition of the state machine for the management of the emSS7CAP process running on some of the BroadWorks servers."
-- @feature:158606
    ::=  {  systemFaults 10511  }

  bwPMemSS7CAPDeath  NOTIFICATION-TYPE
    OBJECTS     { identifier, timeStamp, alarmName, systemName, severity, component, subcomponent, problemText, recommendedActionsText }
    STATUS      current
    DESCRIPTION
        "This notification provides the date and time of the emSS7CAP process death.
@severity:critical
@subcomponent:processmonitor
@correlationrules:bwPMemSS7CAPLaunched, bwPMemSS7CAPShutDown, bwPMemSS7CAPStarted, and bwPMemSS7CAPDeath can be correlated into a single notification.  These events have to be considered as a transition of the state machine for the management of the emSS7CAP process running on some of the BroadWorks servers."
-- @feature:158606
    ::=  {  systemFaults 10512  }

  bwPMss7CAPLaunched  NOTIFICATION-TYPE
    OBJECTS     { identifier, timeStamp, alarmName, systemName, severity, component, subcomponent, problemText, recommendedActionsText }
    STATUS      current
    DESCRIPTION
        "This notification indicates that the ss7CAP process has been started.
@severity:informational
@subcomponent:processmonitor
@correlationrules:bwPMss7CAPLaunched, bwPMss7CAPShutDown, bwPMss7CAPStarted, and bwPMss7CAPDeath can be correlated into a single notification.  These events have to be considered as a transition of the state machine for the management of the ss7CAP process running on some of the BroadWorks servers."
-- @feature:158606
    ::=  {  systemFaults 10513  }

  bwPMss7CAPShutDown  NOTIFICATION-TYPE
    OBJECTS     { identifier, timeStamp, alarmName, systemName, severity, component, subcomponent, problemText, recommendedActionsText }
    STATUS      current
    DESCRIPTION
        "This notification indicates that the ss7CAP process has been manually shut down.
@severity:informational
@subcomponent:processmonitor
@correlationrules:bwPMss7CAPLaunched, bwPMss7CAPShutDown, bwPMss7CAPStarted, and bwPMss7CAPDeath can be correlated into a single notification.  These events have to be considered as a transition of the state machine for the management of the ss7CAP process running on some of the BroadWorks servers."
-- @feature:158606
    ::=  {  systemFaults 10514  }

  bwPMss7CAPRestarted  NOTIFICATION-TYPE
    OBJECTS     { identifier, timeStamp, alarmName, systemName, severity, component, subcomponent, problemText, recommendedActionsText }
    STATUS      current
    DESCRIPTION
        "This notification provides the date and time of the ss7CAP process restart.
@severity:informational
@subcomponent:processmonitor
@correlationrules:bwPMss7CAPLaunched, bwPMss7CAPShutDown, bwPMss7CAPStarted, and bwPMss7CAPDeath can be correlated into a single notification.  These events have to be considered as a transition of the state machine for the management of the ss7CAP process running on some of the BroadWorks servers."
-- @feature:158606
    ::=  {  systemFaults 10515  }

  bwPMss7CAPDeath  NOTIFICATION-TYPE
    OBJECTS     { identifier, timeStamp, alarmName, systemName, severity, component, subcomponent, problemText, recommendedActionsText }
    STATUS      current
    DESCRIPTION
        "This notification provides the date and time of the ss7CAP process death.
@severity:critical
@subcomponent:processmonitor
@correlationrules:bwPMss7CAPLaunched, bwPMss7CAPShutDown, bwPMss7CAPStarted, and bwPMss7CAPDeath can be correlated into a single notification.  These events have to be considered as a transition of the state machine for the management of the ss7CAP process running on some of the BroadWorks servers."
-- @feature:158606
    ::=  {  systemFaults 10516  }

  bwPMss7CAPBridgeLaunched  NOTIFICATION-TYPE
    OBJECTS     { identifier, timeStamp, alarmName, systemName, severity, component, subcomponent, problemText, recommendedActionsText }
    STATUS      current
    DESCRIPTION
        "This notification indicates that the ss7CAPBridge process has been started.
@severity:informational
@subcomponent:processmonitor
@correlationrules:bwPMss7CAPBridgeLaunched, bwPMss7CAPBridgeShutDown, bwPMss7CAPBridgeStarted, and bwPMss7CAPBridgeDeath can be correlated into a single notification.  These events have to be considered as a transition of the state machine for the management of the ss7CAPBridge process running on some of the BroadWorks servers."
-- @feature:158606
    ::=  {  systemFaults 10525  }

  bwPMss7CAPBridgeShutDown  NOTIFICATION-TYPE
    OBJECTS     { identifier, timeStamp, alarmName, systemName, severity, component, subcomponent, problemText, recommendedActionsText }
    STATUS      current
    DESCRIPTION
        "This notification indicates that the ss7CAPBridge process has been manually shut down.
@severity:informational
@subcomponent:processmonitor
@correlationrules:bwPMss7CAPBridgeLaunched, bwPMss7CAPBridgeShutDown, bwPMss7CAPBridgeStarted, and bwPMss7CAPBridgeDeath can be correlated into a single notification.  These events have to be considered as a transition of the state machine for the management of the ss7CAPBridge process running on some of the BroadWorks servers."
-- @feature:158606
    ::=  {  systemFaults 10526  }

  bwPMss7CAPBridgeRestarted  NOTIFICATION-TYPE
    OBJECTS     { identifier, timeStamp, alarmName, systemName, severity, component, subcomponent, problemText, recommendedActionsText }
    STATUS      current
    DESCRIPTION
        "This notification provides the date and time of the ss7CAPBridge process restart.
@severity:informational
@subcomponent:processmonitor
@correlationrules:bwPMss7CAPBridgeLaunched, bwPMss7CAPBridgeShutDown, bwPMss7CAPBridgeStarted, and bwPMss7CAPBridgeDeath can be correlated into a single notification.  These events have to be considered as a transition of the state machine for the management of the ss7CAPBridge process running on some of the BroadWorks servers."
-- @feature:158606
    ::=  {  systemFaults 10527  }

  bwPMss7CAPBridgeDeath  NOTIFICATION-TYPE
    OBJECTS     { identifier, timeStamp, alarmName, systemName, severity, component, subcomponent, problemText, recommendedActionsText }
    STATUS      current
    DESCRIPTION
        "This notification provides the date and time of the ss7CAPBridge process death.
@severity:critical
@subcomponent:processmonitor
@correlationrules:bwPMss7CAPBridgeLaunched, bwPMss7CAPBridgeShutDown, bwPMss7CAPBridgeStarted, and bwPMss7CAPBridgeDeath can be correlated into a single notification.  These events have to be considered as a transition of the state machine for the management of the ss7CAPBridge process running on some of the BroadWorks servers."
-- @feature:158606
    ::=  {  systemFaults 10528  }

  bwSS7CapSubsystemDown  NOTIFICATION-TYPE
    OBJECTS     { identifier, timeStamp, alarmName, systemName, severity, alarmState, component, subcomponent, problemText, recommendedActionsText, correlationParameter, npSS7SubsystemNumber }
    STATUS      current
    DESCRIPTION
        "A required CAP subsystem is not available for use.
@severity:high
@subcomponent:ss7Cap"
-- @feature:158606
    ::=  {  systemFaults 10558  }
       
  bwPMss7CAPOAMBridgeLaunched  NOTIFICATION-TYPE
    OBJECTS     { identifier, timeStamp, alarmName, systemName, severity, component, subcomponent, problemText, recommendedActionsText }
    STATUS      current
    DESCRIPTION
        "This notification indicates that the ss7CAPOAMBridge process has been started.
@severity:informational
@subcomponent:processmonitor
@correlationrules:bwPMss7CAPOAMBridgeLaunched, bwPMss7CAPOAMBridgeShutDown, bwPMss7CAPOAMBridgeStarted, and bwPMss7CAPOAMBridgeDeath can be correlated into a single notification.  These events have to be considered as a transition of the state machine for the management of the ss7CAPOAMBridge process running on some of the BroadWorks servers."
-- @feature:177228
    ::=  {  systemFaults 12301  }

  bwPMss7CAPOAMBridgeShutDown  NOTIFICATION-TYPE
    OBJECTS     { identifier, timeStamp, alarmName, systemName, severity, component, subcomponent, problemText, recommendedActionsText }
    STATUS      current
    DESCRIPTION
        "This notification indicates that the ss7CAPOAMBridge process has been manually shut down.
@severity:informational
@subcomponent:processmonitor
@correlationrules:bwPMss7CAPOAMBridgeLaunched, bwPMss7CAPOAMBridgeShutDown, bwPMss7CAPOAMBridgeStarted, and bwPMss7CAPOAMBridgeDeath can be correlated into a single notification.  These events have to be considered as a transition of the state machine for the management of the ss7CAPOAMBridge process running on some of the BroadWorks servers."
-- @feature:177228
    ::=  {  systemFaults 12302  }

  bwPMss7CAPOAMBridgeRestarted  NOTIFICATION-TYPE
    OBJECTS     { identifier, timeStamp, alarmName, systemName, severity, component, subcomponent, problemText, recommendedActionsText }
    STATUS      current
    DESCRIPTION
        "This notification provides the date and time of the ss7CAPOAMBridge process restart.
@severity:informational
@subcomponent:processmonitor
@correlationrules:bwPMss7CAPOAMBridgeLaunched, bwPMss7CAPOAMBridgeShutDown, bwPMss7CAPOAMBridgeStarted, and bwPMss7CAPOAMBridgeDeath can be correlated into a single notification.  These events have to be considered as a transition of the state machine for the management of the ss7CAPOAMBridge process running on some of the BroadWorks servers."
-- @feature:177228
    ::=  {  systemFaults 12303  }

  bwPMss7CAPOAMBridgeDeath  NOTIFICATION-TYPE
    OBJECTS     { identifier, timeStamp, alarmName, systemName, severity, component, subcomponent, problemText, recommendedActionsText }
    STATUS      current
    DESCRIPTION
        "This notification provides the date and time of the ss7CAPOAMBridge process death.
@severity:critical
@subcomponent:processmonitor
@correlationrules:bwPMss7CAPOAMBridgeLaunched, bwPMss7CAPOAMBridgeShutDown, bwPMss7CAPOAMBridgeStarted, and bwPMss7CAPOAMBridgeDeath can be correlated into a single notification.  These events have to be considered as a transition of the state machine for the management of the ss7CAPOAMBridge process running on some of the BroadWorks servers."
-- @feature:177228
    ::=  {  systemFaults 12304  }
    
END

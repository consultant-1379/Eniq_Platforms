-- extracted from rfc1407.txt
-- at Mon Nov 15 17:11:56 1999

               RFC1407-MIB DEFINITIONS ::= BEGIN

               IMPORTS
                       Gauge
                               FROM RFC1155-SMI
                       DisplayString, transmission
                               FROM RFC1213-MIB
                       OBJECT-TYPE
                               FROM RFC-1212;

               -- This MIB module uses the extended OBJECT-TYPE macro
               -- as defined in RFC 1212.

                       ds3  OBJECT IDENTIFIER ::= { transmission 30 }


               -- The DS3/E3 Near End Group

               -- Implementation of this group is mandatory for all
               -- systems that attach to a DS3/E3 Interface.

               -- The DS3/E3 Near End Group consists of four tables:
               --    DS3/E3 Configuration
               --    DS3/E3 Current
               --    DS3/E3 Interval
               --    DS3/E3 Total

               -- the DS3/E3 Configuration

               dsx3ConfigTable OBJECT-TYPE
                   SYNTAX  SEQUENCE OF Dsx3ConfigEntry
                   ACCESS  not-accessible
                   STATUS  mandatory
                   DESCRIPTION
                           "The DS3/E3 Configuration table."
                  ::= { ds3 5 }

              dsx3ConfigEntry OBJECT-TYPE
                  SYNTAX  Dsx3ConfigEntry
                  ACCESS  not-accessible
                  STATUS  mandatory
                  DESCRIPTION
                          "An entry in the DS3/E3 Configuration table."
                 INDEX   { dsx3LineIndex }
                 ::= { dsx3ConfigTable 1 }

             Dsx3ConfigEntry ::=
                 SEQUENCE {
                     dsx3LineIndex
                         INTEGER,
                     dsx3IfIndex
                         INTEGER,
                     dsx3TimeElapsed
                         INTEGER,
                     dsx3ValidIntervals
                         INTEGER,
                     dsx3LineType
                         INTEGER,
                     dsx3LineCoding
                         INTEGER,
                     dsx3SendCode
                         INTEGER,
                     dsx3CircuitIdentifier
                         DisplayString,
                     dsx3LoopbackConfig
                         INTEGER,
                     dsx3LineStatus
                         INTEGER,
                     dsx3TransmitClockSource
                         INTEGER
             }

             dsx3LineIndex OBJECT-TYPE
                 SYNTAX  INTEGER (1..65535)
                 ACCESS  read-only
                 STATUS  mandatory
                 DESCRIPTION
                         "This object is the identifier of a DS3/E3
                         Interface on a managed device.  If there is an
                         ifEntry that is directly associated with this
                         and only this DS3/E3 interface, it should have
                         the same value as ifIndex.  Otherwise, number
                         the dsx3LineIndices with an unique identifier
                         following the rules of choosing a number that
                         is greater than ifNumber and numbering the
                         inside interfaces (e.g., equipment side) with
                         even numbers and outside interfaces (e.g,
                         network side) with odd numbers."
                ::= { dsx3ConfigEntry 1 }

            dsx3IfIndex OBJECT-TYPE
                SYNTAX  INTEGER (1..65535)
                ACCESS  read-only
                STATUS  mandatory
                DESCRIPTION
                        "This value for this object is equal to the
                        value of ifIndex from the Interfaces table of
                        MIB II (RFC 1213)."
               ::= { dsx3ConfigEntry 2 }

           dsx3TimeElapsed OBJECT-TYPE
               SYNTAX  INTEGER (0..899)
               ACCESS  read-only
               STATUS  mandatory
               DESCRIPTION
                       "The number of seconds that have elapsed since
                       the beginning of the near end current error-
                       measurement period."
              ::= { dsx3ConfigEntry 3 }

          dsx3ValidIntervals OBJECT-TYPE
              SYNTAX  INTEGER (0..96)
              ACCESS  read-only
              STATUS  mandatory
              DESCRIPTION
                      "The number of previous near end intervals for
                      which valid data was collected.  The value will be
                      96 unless the interface was brought online within
                      the last 24 hours, in which case the value will be
                      the number of complete 15 minute near end
                      intervals since the interface has been online."
              ::= { dsx3ConfigEntry 4 }

          dsx3LineType OBJECT-TYPE
              SYNTAX  INTEGER {
                          dsx3other(1),
                          dsx3M23(2),
                          dsx3SYNTRAN(3),
                          dsx3CbitParity(4),
                          dsx3ClearChannel(5),
                          e3other(6),
                          e3Framed(7),
                          e3Plcp(8)
                      }
              ACCESS  read-write
              STATUS  mandatory
              DESCRIPTION
                      "This variable indicates the variety of DS3 C-bit
                      or E3 application
                      implementing this interface.  The type of
                      interface affects the interpretation of the
                      usage and error statistics.
                      The rate of DS3 is 44.736 Mbps and E3 is
                      34.368 Mbps.
                      The dsx3ClearChannel value means that the C-bits
                      are not used except for sending/receiving
                      AIS.

                      The values, in sequence, describe:

                      TITLE:            SPECIFICATION:
                      dsx3M23            ANSI T1.107-1988
                      dsx3SYNTRAN        ANSI T1.107-1988
                      dsx3CbitParity     ANSI T1.107a-1989
                      dsx3ClearChannel   ANSI T1.102-1987
                      e3Framed           CCITT G.751
                      e3Plcp             ETSI T/NA(91)18."
              ::= { dsx3ConfigEntry 5 }

          dsx3LineCoding OBJECT-TYPE
              SYNTAX  INTEGER {
                          dsx3Other(1),
                          dsx3B3ZS(2),
                          e3HDB3(3)
                      }
              ACCESS  read-write
              STATUS  mandatory
              DESCRIPTION
                      "This variable describes the variety of Zero Code
                      Suppression used on this interface, which in turn
                      affects a number of its characteristics.

                      dsx3B3ZS and e3HDB3 refer to the use of specified
                      patterns of normal bits and bipolar violations
                      which are used to replace sequences of zero bits
                      of a specified length."
              ::= { dsx3ConfigEntry 6 }

          dsx3SendCode OBJECT-TYPE
                 SYNTAX  INTEGER {
                         dsx3SendNoCode(1),
                         dsx3SendLineCode(2),
                         dsx3SendPayloadCode(3),
                         dsx3SendResetCode(4),
                         dsx3SendDS1LoopCode(5),
                         dsx3SendTestPattern(6)
                         }
                 ACCESS  read-write
                 STATUS  mandatory
                 DESCRIPTION
                      "This variable indicates what type of code is
                      being sent across the DS3/E3 interface by the
                      device.  (These are optional for E3 interfaces.)
                      The values mean:

                         dsx3SendNoCode
                             sending looped or normal data

                         dsx3SendLineCode
                             sending a request for a line loopback

                         dsx3SendPayloadCode
                             sending a request for a payload loopback
                             (i.e., all DS1/E1s in a DS3/E3 frame)

                         dsx3SendResetCode
                             sending a loopback deactivation request

                         dsx3SendDS1LoopCode
                             requesting to loopback a particular DS1/E1
                             within a DS3/E3 frame

                         dsx3SendTestPattern
                             sending a test pattern."
                 ::= { dsx3ConfigEntry 7 }

          dsx3CircuitIdentifier OBJECT-TYPE
              SYNTAX  DisplayString (SIZE (0..255))
              ACCESS  read-write
              STATUS  mandatory
              DESCRIPTION
                      "This variable contains the transmission vendor's
                      circuit identifier, for the purpose of
                      facilitating troubleshooting."
              ::= { dsx3ConfigEntry 8 }

          dsx3LoopbackConfig OBJECT-TYPE
                 SYNTAX  INTEGER {
                           dsx3NoLoop(1),
                           dsx3PayloadLoop(2),
                           dsx3LineLoop(3),
                           dsx3OtherLoop(4)
                         }
                 ACCESS  read-write
                 STATUS  mandatory
                 DESCRIPTION
                    "This variable represents the loopback configuration
                    of the DS3/E3 interface.
                    The values mean:

                    dsx3NoLoop
                      Not in the loopback state.  A device that is
                      not capable of performing a loopback on
                      the interface shall always return this as
                      it's value.

                    dsx3PayloadLoop
                      The received signal at this interface is looped
                      through the device.
                      Typically the received signal
                      is looped back for retransmission after it has
                      passed through the device's framing function.

                    dsx3LineLoop
                      The received signal at this interface does not
                      go through the device (minimum penetration) but
                      is looped back out.

                    dsx3OtherLoop
                      Loopbacks that are not defined here."
                 ::= { dsx3ConfigEntry 9 }

          dsx3LineStatus OBJECT-TYPE
              SYNTAX  INTEGER (1..1023)
              ACCESS  read-only
              STATUS  mandatory
              DESCRIPTION
                 "This variable indicates the
                 Line Status of the interface.
                 It contains loopback state information
                 and failure state information.
                 The dsx3LineStatus is a bit map represented
                 as a sum, therefore,
                 it can represent multiple failures
                 and a loopback (see dsx3LoopbackConfig object
                 for the type of loopback)
                 simultaneously.
                 The dsx3NoAlarm should be set if and only if
                 no other flag is set.

                 The various bit positions are:
                    1     dsx3NoAlarm       No alarm present
                    2     dsx3RcvRAIFailure Receiving Yellow/Remote
                          Alarm Indication
                    4     dsx3XmitRAIAlarm Transmitting Yellow/Remote
                          Alarm Indication

                    8     dsx3RcvAIS        Receiving AIS failure state
                   16     dsx3XmitAIS       Transmitting AIS
                   32     dsx3LOF           Receiving LOF failure state
                   64     dsx3LOS           Receiving LOS failure state
                  128     dsx3LoopbackState Looping the received signal
                  256     dsx3RcvTestCode   Receiving a Test Pattern
                  512     dsx3OtherFailure any line status not defined
                          here"
              ::= { dsx3ConfigEntry 10 }

          dsx3TransmitClockSource OBJECT-TYPE
              SYNTAX  INTEGER {
                          loopTiming(1),
                          localTiming(2),
                          throughTiming(3)
                      }
              ACCESS  read-write
              STATUS  mandatory
              DESCRIPTION
                 "The source of Transmit Clock.
                 is derived from the recovered receive clock of
                 another DS3 interface."
              ::= { dsx3ConfigEntry 11 }


          -- the DS3/E3 Current

          -- The DS3/E3 current table contains various statistics being
          -- collected for the current 15 minute interval.

          dsx3CurrentTable OBJECT-TYPE
              SYNTAX  SEQUENCE OF Dsx3CurrentEntry
              ACCESS  not-accessible
              STATUS  mandatory
              DESCRIPTION
                      "The DS3/E3 Current table."
              ::= { ds3 6 }

          dsx3CurrentEntry OBJECT-TYPE
              SYNTAX  Dsx3CurrentEntry
              ACCESS  not-accessible
              STATUS  mandatory
              DESCRIPTION
                      "An entry in the DS3/E3 Current table."
              INDEX   { dsx3CurrentIndex }
              ::= { dsx3CurrentTable 1 }

          Dsx3CurrentEntry ::=
              SEQUENCE {
                  dsx3CurrentIndex
                      INTEGER,
                  dsx3CurrentPESs
                      Gauge,
                  dsx3CurrentPSESs
                      Gauge,
                  dsx3CurrentSEFSs
                      Gauge,
                  dsx3CurrentUASs
                      Gauge,
                  dsx3CurrentLCVs
                      Gauge,
                  dsx3CurrentPCVs
                      Gauge,
                  dsx3CurrentLESs
                      Gauge,
                  dsx3CurrentCCVs
                      Gauge,
                  dsx3CurrentCESs
                      Gauge,
                  dsx3CurrentCSESs
                      Gauge
              }

          dsx3CurrentIndex OBJECT-TYPE
              SYNTAX  INTEGER (1..65535)
              ACCESS  read-only
              STATUS  mandatory
              DESCRIPTION
                      "The index value which uniquely identifies the
                      DS3/E3 interface to which this entry is
                      applicable.  The interface identified by a
                      particular value of this index is the same
                      interface as identified by the same value an
                      dsx3LineIndex object instance."
              ::= { dsx3CurrentEntry 1 }

          dsx3CurrentPESs OBJECT-TYPE
              SYNTAX  Gauge
              ACCESS  read-only
              STATUS  mandatory
              DESCRIPTION
                      "The counter associated with the number of P-bit
                      Errored Seconds, encountered by a DS3 interface in
                      the current 15 minute interval."
              ::= { dsx3CurrentEntry 2 }

          dsx3CurrentPSESs OBJECT-TYPE
              SYNTAX  Gauge
              ACCESS  read-only
              STATUS  mandatory
              DESCRIPTION
                      "The counter associated with the number of P-bit
                      Severely Errored Seconds, encountered by a DS3
                      interface in the current 15 minute interval."
              ::= { dsx3CurrentEntry 3 }

          dsx3CurrentSEFSs OBJECT-TYPE
              SYNTAX  Gauge
              ACCESS  read-only
              STATUS  mandatory
              DESCRIPTION
                      "The counter associated with the number of
                      Severely Errored Framing Seconds, encountered by a
                      DS3/E3 interface in the current 15 minute
                      interval."
              ::= { dsx3CurrentEntry 4 }

          dsx3CurrentUASs OBJECT-TYPE
              SYNTAX  Gauge
              ACCESS  read-only
              STATUS  mandatory
              DESCRIPTION
                      "The counter associated with the number of
                      Unavailable Seconds, encountered by a DS3
                      interface in the current 15 minute interval."
              ::= { dsx3CurrentEntry 5 }

          dsx3CurrentLCVs OBJECT-TYPE
              SYNTAX  Gauge
              ACCESS  read-only
              STATUS  mandatory
              DESCRIPTION
                      "The counter associated with the number of Line
                      Coding Violations encountered by a DS3/E3
                      interface in the current 15 minute interval."
              ::= { dsx3CurrentEntry 6 }

          dsx3CurrentPCVs OBJECT-TYPE
              SYNTAX  Gauge
              ACCESS  read-only
              STATUS  mandatory
              DESCRIPTION
                      "The counter associated with the number of P-bit
                      Coding Violations, encountered by a DS3 interface
                      in the current 15 minute interval."
              ::= { dsx3CurrentEntry 7 }

          dsx3CurrentLESs OBJECT-TYPE
              SYNTAX  Gauge
              ACCESS  read-only
              STATUS  mandatory
              DESCRIPTION
                      "The number of Line Errored Seconds encountered by
                      a DS3/E3 interface in the current 15 minute
                      interval."
              ::= { dsx3CurrentEntry 8 }

          dsx3CurrentCCVs OBJECT-TYPE
              SYNTAX  Gauge
              ACCESS  read-only
              STATUS  mandatory
              DESCRIPTION
                      "The number of C-bit Coding Violations encountered
                      by a DS3 interface in the current 15 minute
                      interval."
              ::= { dsx3CurrentEntry 9 }

          dsx3CurrentCESs OBJECT-TYPE
              SYNTAX  Gauge
              ACCESS  read-only
              STATUS  mandatory
              DESCRIPTION
                      "The number of C-bit Errored Seconds encountered
                      by a DS3 interface in the current 15 minute
                      interval."
              ::= { dsx3CurrentEntry 10 }

          dsx3CurrentCSESs OBJECT-TYPE
              SYNTAX  Gauge
              ACCESS  read-only
              STATUS  mandatory
              DESCRIPTION
                      "The number of C-bit Severely Errored Seconds
                      encountered by a DS3 interface in the current 15
                      minute interval."
              ::= { dsx3CurrentEntry 11 }


          -- the DS3/E3 Interval

          -- The DS3/E3 Interval Table contains various statistics
          -- collected by each DS3/E3 Interface over the previous 24
          -- hours of operation.  The past 24 hours are broken into 96
          -- completed 15 minute intervals.

          dsx3IntervalTable OBJECT-TYPE
              SYNTAX  SEQUENCE OF Dsx3IntervalEntry
              ACCESS  not-accessible
              STATUS  mandatory
              DESCRIPTION
                      "The DS3/E3 Interval table."
              ::= { ds3 7 }

          dsx3IntervalEntry OBJECT-TYPE
              SYNTAX  Dsx3IntervalEntry
              ACCESS  not-accessible
              STATUS  mandatory
              DESCRIPTION
                      "An entry in the DS3/E3 Interval table."
              INDEX   { dsx3IntervalIndex, dsx3IntervalNumber }
              ::= { dsx3IntervalTable 1 }

          Dsx3IntervalEntry ::=
              SEQUENCE {
                  dsx3IntervalIndex
                      INTEGER,
                  dsx3IntervalNumber
                      INTEGER,
                  dsx3IntervalPESs
                      Gauge,
                  dsx3IntervalPSESs
                      Gauge,
                  dsx3IntervalSEFSs
                      Gauge,
                  dsx3IntervalUASs
                      Gauge,
                  dsx3IntervalLCVs
                      Gauge,
                  dsx3IntervalPCVs
                      Gauge,
                  dsx3IntervalLESs
                      Gauge,
                  dsx3IntervalCCVs
                      Gauge,
                  dsx3IntervalCESs
                      Gauge,
                  dsx3IntervalCSESs
                      Gauge
              }

          dsx3IntervalIndex OBJECT-TYPE
              SYNTAX  INTEGER (1..65535)
              ACCESS  read-only
              STATUS  mandatory
              DESCRIPTION
                      "The index value which uniquely identifies the
                      DS3/E3 interface to which this entry is
                      applicable.  The interface identified by a
                      particular value of this index is the same
                      interface as identified by the same value an
                      dsx3LineIndex object instance."
              ::= { dsx3IntervalEntry 1 }

          dsx3IntervalNumber OBJECT-TYPE
              SYNTAX  INTEGER (1..96)
              ACCESS  read-only
              STATUS  mandatory
              DESCRIPTION
                      "A number between 1 and 96, where 1 is the most
                      recently completed 15 minute interval and 96 is
                      the least recently completed 15 minutes interval
                      (assuming that all 96 intervals are valid)."
              ::= { dsx3IntervalEntry 2 }

          dsx3IntervalPESs OBJECT-TYPE
              SYNTAX  Gauge
              ACCESS  read-only
              STATUS  mandatory
              DESCRIPTION
                      "The counter associated with the number of P-bit
                      Errored Seconds, encountered by a DS3 interface in
                      one of the previous 96, individual 15 minute,
                      intervals."
              ::= { dsx3IntervalEntry 3 }

          dsx3IntervalPSESs OBJECT-TYPE
              SYNTAX  Gauge
              ACCESS  read-only
              STATUS  mandatory
              DESCRIPTION
                      "The counter associated with the number of P-bit
                      Severely Errored Seconds, encountered by a DS3
                      interface in one of the previous 96, individual 15
                      minute, intervals."
              ::= { dsx3IntervalEntry 4 }

          dsx3IntervalSEFSs OBJECT-TYPE
              SYNTAX  Gauge
              ACCESS  read-only
              STATUS  mandatory
              DESCRIPTION
                      "The counter associated with the number of
                      Severely Errored Framing Seconds, encountered by a
                      DS3/E3 interface in one of the previous 96,
                      individual 15 minute, intervals."
              ::= { dsx3IntervalEntry 5 }

          dsx3IntervalUASs OBJECT-TYPE
              SYNTAX  Gauge
              ACCESS  read-only
              STATUS  mandatory
              DESCRIPTION
                      "The counter associated with the number of
                      Unavailable Seconds, encountered by a DS3
                      interface in one of the previous 96, individual 15
                      minute, intervals."
              ::= { dsx3IntervalEntry 6 }

          dsx3IntervalLCVs OBJECT-TYPE
              SYNTAX  Gauge
              ACCESS  read-only
              STATUS  mandatory
              DESCRIPTION
                      "The counter associated with the number of Line
                      Coding Violations encountered by a DS3/E3
                      interface in one of the previous 96, individual 15
                      minute, intervals."
              ::= { dsx3IntervalEntry 7 }

          dsx3IntervalPCVs OBJECT-TYPE
              SYNTAX  Gauge
              ACCESS  read-only
              STATUS  mandatory
              DESCRIPTION
                      "The counter associated with the number of P-bit
                      Coding Violations, encountered by a DS3 interface
                      in one of the previous 96, individual 15 minute,
                      intervals."
              ::= { dsx3IntervalEntry 8 }

          dsx3IntervalLESs OBJECT-TYPE
              SYNTAX  Gauge
              ACCESS  read-only
              STATUS  mandatory
              DESCRIPTION
                   "The number of Line Errored  Seconds  (BPVs  or
                   illegal  zero  sequences) encountered by a DS3/E3
                   interface in one of the previous 96, individual
                   15 minute, intervals."
              ::= { dsx3IntervalEntry 9 }

          dsx3IntervalCCVs OBJECT-TYPE
              SYNTAX  Gauge
              ACCESS  read-only
              STATUS  mandatory
              DESCRIPTION
                      "The number of C-bit Coding Violations encountered
                      by a DS3 interface in one of the previous 96,
                      individual 15 minute, intervals."
              ::= { dsx3IntervalEntry 10 }

          dsx3IntervalCESs OBJECT-TYPE
              SYNTAX  Gauge
              ACCESS  read-only
              STATUS  mandatory
              DESCRIPTION
                      "The number of C-bit Errored Seconds encountered
                      by a DS3 interface in one of the previous 96,
                      individual 15 minute, intervals."
              ::= { dsx3IntervalEntry 11 }

          dsx3IntervalCSESs OBJECT-TYPE
              SYNTAX  Gauge
              ACCESS  read-only
              STATUS  mandatory
              DESCRIPTION
                      "The number of C-bit Severely Errored Seconds
                      encountered by a DS3 interface in one of the
                      previous 96, individual 15 minute, intervals."
              ::= { dsx3IntervalEntry 12 }


          -- the DS3/E3 Total

          -- The DS3/E3 Total Table contains the cumulative sum of the
          -- various statistics for the 24 hour period preceding the
          -- current interval.

          dsx3TotalTable OBJECT-TYPE
              SYNTAX  SEQUENCE OF Dsx3TotalEntry
              ACCESS  not-accessible
              STATUS  mandatory
              DESCRIPTION
                      "The DS3/E3 Total table.  24 hour interval."
              ::= { ds3 8 }

          dsx3TotalEntry OBJECT-TYPE
              SYNTAX  Dsx3TotalEntry
              ACCESS  not-accessible
              STATUS  mandatory
              DESCRIPTION
                      "An entry in the DS3/E3 Total table."
              INDEX   { dsx3TotalIndex }
              ::= { dsx3TotalTable 1 }

          Dsx3TotalEntry ::=
              SEQUENCE {
                  dsx3TotalIndex
                      INTEGER,
                  dsx3TotalPESs
                      Gauge,
                  dsx3TotalPSESs
                      Gauge,
                  dsx3TotalSEFSs
                      Gauge,
                  dsx3TotalUASs
                      Gauge,
                  dsx3TotalLCVs
                      Gauge,
                  dsx3TotalPCVs
                      Gauge,
                  dsx3TotalLESs
                      Gauge,
                  dsx3TotalCCVs
                      Gauge,
                  dsx3TotalCESs
                      Gauge,
                  dsx3TotalCSESs
                      Gauge
              }

          dsx3TotalIndex OBJECT-TYPE
              SYNTAX  INTEGER (1..65535)
              ACCESS  read-only
              STATUS  mandatory
              DESCRIPTION
                      "The index value which uniquely identifies the
                      DS3/E3 interface to which this entry is
                      applicable.  The interface identified by a
                      particular value of this index is the same
                      interface as identified by the same value an
                      dsx3LineIndex object instance."
              ::= { dsx3TotalEntry 1 }

          dsx3TotalPESs OBJECT-TYPE
              SYNTAX  Gauge
              ACCESS  read-only
              STATUS  mandatory
              DESCRIPTION
                      "The counter associated with the number of P-bit
                      Errored Seconds, encountered by a DS3 interface in
                      the previous 24 hour interval"
              ::= { dsx3TotalEntry 2 }

          dsx3TotalPSESs OBJECT-TYPE
              SYNTAX  Gauge
              ACCESS  read-only
              STATUS  mandatory
              DESCRIPTION
                      "The counter associated with the number of P-bit
                      Severely Errored Seconds, encountered by a DS3
                      interface in the previous 24 hour interval."
              ::= { dsx3TotalEntry 3 }

          dsx3TotalSEFSs OBJECT-TYPE
              SYNTAX  Gauge
              ACCESS  read-only
              STATUS  mandatory
              DESCRIPTION
                      "The counter associated with the number of
                      Severely Errored Framing Seconds, encountered by a
                      DS3/E3 interface in the previous 24 hour
                      interval."
              ::= { dsx3TotalEntry 4 }

          dsx3TotalUASs OBJECT-TYPE
              SYNTAX  Gauge
              ACCESS  read-only
              STATUS  mandatory
              DESCRIPTION
                      "The counter associated with the number of
                      Unavailable Seconds, encountered by a DS3
                      interface in the previous 24 hour interval."
              ::= { dsx3TotalEntry 5 }

          dsx3TotalLCVs OBJECT-TYPE
              SYNTAX  Gauge
              ACCESS  read-only
              STATUS  mandatory
              DESCRIPTION
                      "The counter associated with the number of Line
                      Coding Violations encountered by a DS3/E3
                      interface in the previous 24 hour interval."
              ::= { dsx3TotalEntry 6 }

          dsx3TotalPCVs OBJECT-TYPE
              SYNTAX  Gauge
              ACCESS  read-only
              STATUS  mandatory
              DESCRIPTION
                      "The counter associated with the number of P-bit
                      Coding Violations, encountered by a DS3 interface
                      in the previous 24 hour interval."
              ::= { dsx3TotalEntry 7 }

          dsx3TotalLESs OBJECT-TYPE
              SYNTAX  Gauge
              ACCESS  read-only
              STATUS  mandatory
              DESCRIPTION
                   "The number of Line Errored  Seconds  (BPVs  or
                   illegal  zero  sequences) encountered by a DS3/E3
                   interface in the previous 24 hour interval."
              ::= { dsx3TotalEntry 8 }

          dsx3TotalCCVs OBJECT-TYPE
              SYNTAX  Gauge
              ACCESS  read-only
              STATUS  mandatory
              DESCRIPTION
                      "The number of C-bit Coding Violations encountered
                      by a DS3 interface in the previous 24 hour
                      interval."
              ::= { dsx3TotalEntry 9 }

          dsx3TotalCESs OBJECT-TYPE
              SYNTAX  Gauge
              ACCESS  read-only
              STATUS  mandatory
              DESCRIPTION
                      "The number of C-bit Errored Seconds encountered
                      by a DS3 interface in the previous 24 hour
                      interval."
              ::= { dsx3TotalEntry 10 }

          dsx3TotalCSESs OBJECT-TYPE
              SYNTAX  Gauge
              ACCESS  read-only
              STATUS  mandatory
              DESCRIPTION
                      "The number of C-bit Severely Errored Seconds
                      encountered by a DS3 interface in the previous 24
                      hour interval."
              ::= { dsx3TotalEntry 11 }


          -- The DS3 Far End Group

          -- Implementation of this group is optional for all systems
          -- that attach to a DS3 Interface.
          -- However, only C-bit Parity and SYNTRAN DS3 applications
          -- have the capability (option) of providing this information.

          -- The DS3 Far End Group consists of four tables:
          --   DS3 Far End Configuration
          --   DS3 Far End Current
          --   DS3 Far End Interval
          --   DS3 Far End Total


          -- The DS3 Far End Configuration Table contains
          -- configuration information
          -- reported in the C-bits from the remote end.

          dsx3FarEndConfigTable OBJECT-TYPE
              SYNTAX  SEQUENCE OF Dsx3FarEndConfigEntry
              ACCESS  not-accessible
              STATUS  mandatory
              DESCRIPTION
                 "The DS3 Far End Configuration table."
              ::= { ds3 9 }

          dsx3FarEndConfigEntry OBJECT-TYPE
              SYNTAX  Dsx3FarEndConfigEntry
              ACCESS  not-accessible
              STATUS  mandatory
              DESCRIPTION
                   "An entry in the DS3 Far End Configuration table."
              INDEX   { dsx3FarEndLineIndex }
              ::= { dsx3FarEndConfigTable 1 }

          Dsx3FarEndConfigEntry ::=
              SEQUENCE {
                  dsx3FarEndLineIndex
                      INTEGER,
                  dsx3FarEndEquipCode
                      DisplayString,
                  dsx3FarEndLocationIDCode
                      DisplayString,
                  dsx3FarEndFrameIDCode
                      DisplayString,
                  dsx3FarEndUnitCode
                      DisplayString,
                  dsx3FarEndFacilityIDCode
                      DisplayString
               }

          dsx3FarEndLineIndex OBJECT-TYPE
              SYNTAX  INTEGER (1..65535)
              ACCESS  read-only
              STATUS  mandatory
              DESCRIPTION
                   "The index value which uniquely identifies the
                   DS3 interface
                   to which this entry is applicable.  The
                   interface identified by a particular value of
                   this index is the same interface as identified
                   by the same value an dsx3LineIndex object
                   instance."
             ::= { dsx3FarEndConfigEntry 1 }

          dsx3FarEndEquipCode OBJECT-TYPE
              SYNTAX  DisplayString (SIZE (0..10))
              ACCESS  read-write
              STATUS  mandatory
              DESCRIPTION
                    "This is the Far End Equipment Identification code
                    that describes the specific piece of equipment.
                    It is sent within the Path
                    Identification Message."
              ::= { dsx3FarEndConfigEntry 2 }

          dsx3FarEndLocationIDCode OBJECT-TYPE
              SYNTAX  DisplayString (SIZE (0..11))
              ACCESS  read-write
              STATUS  mandatory
              DESCRIPTION
                    "This is the Far End Location Identification code
                    that describes the specific location of the
                    equipment.
                    It is sent within the Path
                    Identification Message."
              ::= { dsx3FarEndConfigEntry 3 }

          dsx3FarEndFrameIDCode OBJECT-TYPE
              SYNTAX  DisplayString (SIZE (0..10))
              ACCESS  read-write
              STATUS  mandatory
              DESCRIPTION
                    "This is the Far End Frame Identification code
                    that identifies where the equipment is located
                    within a building at a given location.
                    It is sent within the Path
                    Identification Message."
              ::= { dsx3FarEndConfigEntry 4 }

          dsx3FarEndUnitCode OBJECT-TYPE
              SYNTAX  DisplayString (SIZE (0..6))
              ACCESS  read-write
              STATUS  mandatory
              DESCRIPTION
                    "This is the Far End code
                    that identifies the equipment location within a bay.
                    It is sent within the Path
                    Identification Message."
              ::= { dsx3FarEndConfigEntry 5 }

          dsx3FarEndFacilityIDCode OBJECT-TYPE
              SYNTAX  DisplayString (SIZE (0..38))
              ACCESS  read-write
              STATUS  mandatory
              DESCRIPTION
                    "This code identifies a specific Far End DS3 path.
                    It is sent within the Path
                    Identification Message."
              ::= { dsx3FarEndConfigEntry 6 }


          -- The DS3 Far End Current

          -- The DS3 Far End Current table contains various statistics
          -- being collected for the current 15 minute interval.
          -- The statistics are collected from the far end block error
          -- code within the C-bits.

          dsx3FarEndCurrentTable OBJECT-TYPE
              SYNTAX  SEQUENCE OF Dsx3FarEndCurrentEntry
              ACCESS  not-accessible
              STATUS  mandatory
              DESCRIPTION
                      "The DS3 Far End Current table."
              ::= { ds3 10 }

          dsx3FarEndCurrentEntry OBJECT-TYPE
              SYNTAX  Dsx3FarEndCurrentEntry
              ACCESS  not-accessible
              STATUS  mandatory
              DESCRIPTION
                      "An entry in the DS3 Far End Current table."
              INDEX   { dsx3FarEndCurrentIndex }
              ::= { dsx3FarEndCurrentTable 1 }

          Dsx3FarEndCurrentEntry ::=
              SEQUENCE {
                  dsx3FarEndCurrentIndex
                      INTEGER,
                  dsx3FarEndTimeElapsed
                      INTEGER,
                  dsx3FarEndValidIntervals
                      INTEGER,
                  dsx3FarEndCurrentCESs
                      Gauge,
                  dsx3FarEndCurrentCSESs
                      Gauge,
                  dsx3FarEndCurrentCCVs
                      Gauge,
                  dsx3FarEndCurrentUASs
                      Gauge
              }

           dsx3FarEndCurrentIndex OBJECT-TYPE
              SYNTAX  INTEGER (1..65535)
              ACCESS  read-only
              STATUS  mandatory
              DESCRIPTION
                      "The index value which uniquely identifies the
                      DS3 interface
                      to which this entry is applicable.  The interface
                      identified by a particular value of this index is
                      the same interface as identified by the same value
                      an dsx3LineIndex object instance."
              ::= { dsx3FarEndCurrentEntry 1 }

          dsx3FarEndTimeElapsed OBJECT-TYPE
              SYNTAX  INTEGER (0..899)
              ACCESS  read-only
              STATUS  mandatory
              DESCRIPTION
                      "The number of seconds that have elapsed since the
                      beginning of the far end current error-measurement
                      period."
              ::= { dsx3FarEndCurrentEntry 2 }

          dsx3FarEndValidIntervals OBJECT-TYPE
              SYNTAX  INTEGER (0..96)
              ACCESS  read-only
              STATUS  mandatory
              DESCRIPTION
                      "The number of previous far end intervals for
                      which valid data was collected.  The value will be
                      96 unless the interface was brought online within
                      the last 24 hours, in which case the value will be
                      the number of complete 15 minute far end intervals
                      since the interface has been online."
              ::= { dsx3FarEndCurrentEntry 3 }

          dsx3FarEndCurrentCESs OBJECT-TYPE
              SYNTAX  Gauge
              ACCESS  read-only
              STATUS  mandatory
              DESCRIPTION
                      "The counter associated with the number of Far
                      Far End C-bit Errored Seconds encountered by a DS3
                      interface in the current 15 minute interval."
              ::= { dsx3FarEndCurrentEntry 4 }

          dsx3FarEndCurrentCSESs OBJECT-TYPE
              SYNTAX  Gauge
              ACCESS  read-only
              STATUS  mandatory
              DESCRIPTION
                      "The counter associated with the number of
                      Far End C-bit Severely Errored Seconds
                      encountered by a DS3 interface in the current 15
                      minute interval."
              ::= { dsx3FarEndCurrentEntry 5 }

          dsx3FarEndCurrentCCVs OBJECT-TYPE
              SYNTAX  Gauge
              ACCESS  read-only
              STATUS  mandatory
              DESCRIPTION
                      "The counter associated with the number of
                      Far End C-bit Coding Violations reported via
                      the far end block error count
                      encountered by a
                      DS3 interface in the current 15 minute interval."
              ::= { dsx3FarEndCurrentEntry 6 }

          dsx3FarEndCurrentUASs OBJECT-TYPE
              SYNTAX  Gauge
              ACCESS  read-only
              STATUS  mandatory
              DESCRIPTION
                      "The counter associated with the number of
                      Far End unavailable seconds
                      encountered by a
                      DS3 interface in the current 15 minute interval."
              ::= { dsx3FarEndCurrentEntry 7 }


          -- The DS3 Far End Interval

          -- The DS3 Far End Interval Table contains various statistics
          -- collected by each DS3 interface over the previous 24
          -- hours of operation.  The past 24 hours are broken into 96
          -- completed 15 minute intervals.

          dsx3FarEndIntervalTable OBJECT-TYPE
              SYNTAX  SEQUENCE OF Dsx3FarEndIntervalEntry
              ACCESS  not-accessible
              STATUS  mandatory
              DESCRIPTION
                     "The DS3 Far End Interval table."
              ::= { ds3 11 }

          dsx3FarEndIntervalEntry OBJECT-TYPE
              SYNTAX  Dsx3FarEndIntervalEntry
              ACCESS  not-accessible
              STATUS  mandatory
              DESCRIPTION
                    "An entry in the DS3 Far
                    End Interval table."
              INDEX   { dsx3FarEndIntervalIndex,
                        dsx3FarEndIntervalNumber }
              ::= { dsx3FarEndIntervalTable 1 }

          Dsx3FarEndIntervalEntry ::=
              SEQUENCE {
                   dsx3FarEndIntervalIndex
                        INTEGER,
                   dsx3FarEndIntervalNumber
                        INTEGER,
                   dsx3FarEndIntervalCESs
                        Gauge,
                   dsx3FarEndIntervalCSESs
                        Gauge,

                   dsx3FarEndIntervalCCVs
                        Gauge,
                   dsx3FarEndIntervalUASs
                        Gauge
              }

          dsx3FarEndIntervalIndex OBJECT-TYPE
              SYNTAX  INTEGER (1..65535)
              ACCESS  read-only
              STATUS  mandatory
              DESCRIPTION
                      "The index value which uniquely identifies the
                      DS3 interface
                      to which this entry is applicable.  The
                      interface identified by a particular value of
                      this index is the same interface as identified
                      by the same value an dsx3LineIndex object
                      instance."
              ::= { dsx3FarEndIntervalEntry 1 }

          dsx3FarEndIntervalNumber OBJECT-TYPE
             SYNTAX  INTEGER (1..96)
             ACCESS  read-only
             STATUS  mandatory
             DESCRIPTION
                    "A number between 1 and 96, where 1 is the most
                    recently completed 15 minute interval and 96 is
                    the least recently completed 15 minutes
                    interval (assuming that all 96 intervals are
                    valid)."
             ::= { dsx3FarEndIntervalEntry 2 }

          dsx3FarEndIntervalCESs OBJECT-TYPE
             SYNTAX  Gauge
             ACCESS  read-only
             STATUS  mandatory
             DESCRIPTION
                     "The counter associated with the number of
                      Far End C-bit Errored Seconds encountered
                      by a DS3 interface in one of the previous 96,
                      individual 15 minute, intervals."
            ::= { dsx3FarEndIntervalEntry 3 }

          dsx3FarEndIntervalCSESs OBJECT-TYPE
             SYNTAX  Gauge
             ACCESS  read-only
             STATUS  mandatory
             DESCRIPTION
                     "The counter associated with the number of
                     Far End C-bit Severely Errored Seconds
                     encountered by a DS3 interface in one of the
                     previous 96, individual 15 minute, intervals."
            ::= { dsx3FarEndIntervalEntry 4 }

          dsx3FarEndIntervalCCVs OBJECT-TYPE
              SYNTAX  Gauge
              ACCESS  read-only
              STATUS  mandatory
              DESCRIPTION
                      "The counter associated with the number of
                      Far End C-bit Coding Violations reported via
                      the far end block error count
                      encountered by a
                      DS3 interface in one of the previous 96,
                      individual 15 minute, intervals."
              ::= { dsx3FarEndIntervalEntry 5 }

          dsx3FarEndIntervalUASs OBJECT-TYPE
              SYNTAX  Gauge
              ACCESS  read-only
              STATUS  mandatory
              DESCRIPTION
                      "The counter associated with the number of
                      Far End unavailable seconds
                      encountered by a
                      DS3 interface in one of the previous 96,
                      individual 15 minute, intervals."
              ::= { dsx3FarEndIntervalEntry 6 }


          -- The DS3 Far End Total

          -- The DS3 Far End Total Table contains the cumulative sum
          -- of the various statistics for the 24 hour period preceding
          -- the current interval.

          dsx3FarEndTotalTable OBJECT-TYPE
              SYNTAX  SEQUENCE OF Dsx3FarEndTotalEntry
              ACCESS  not-accessible
              STATUS  mandatory
              DESCRIPTION
                      "The DS3 Far End Total table.  24 hour interval."
              ::= { ds3 12 }

          dsx3FarEndTotalEntry OBJECT-TYPE
              SYNTAX  Dsx3FarEndTotalEntry
              ACCESS  not-accessible
              STATUS  mandatory
              DESCRIPTION
                      "An entry in the DS3 Far End Total table."
              INDEX   { dsx3FarEndTotalIndex }
              ::= { dsx3FarEndTotalTable 1 }

          Dsx3FarEndTotalEntry ::=
              SEQUENCE {
                  dsx3FarEndTotalIndex
                      INTEGER,
                  dsx3FarEndTotalCESs
                      Gauge,
                  dsx3FarEndTotalCSESs
                      Gauge,
                  dsx3FarEndTotalCCVs
                      Gauge,
                  dsx3FarEndTotalUASs
                      Gauge
              }

          dsx3FarEndTotalIndex OBJECT-TYPE
              SYNTAX  INTEGER (1..65535)
              ACCESS  read-only
              STATUS  mandatory
              DESCRIPTION
                      "The index value which uniquely identifies the
                      DS3 interface
                      to which this entry is applicable.  The interface
                      identified by a particular value of this index is
                      the same interface as identified by the same value
                      an dsx3LineIndex object instance."
              ::= { dsx3FarEndTotalEntry 1 }

          dsx3FarEndTotalCESs OBJECT-TYPE
             SYNTAX  Gauge
             ACCESS  read-only
             STATUS  mandatory
             DESCRIPTION
                     "The counter associated with the number of Far
                     End C-bit Errored Seconds encountered by a DS3
                     interface in the previous 24 hour interval."
             ::= { dsx3FarEndTotalEntry 2 }

          dsx3FarEndTotalCSESs OBJECT-TYPE
             SYNTAX  Gauge
             ACCESS  read-only
             STATUS  mandatory
             DESCRIPTION
                     "The counter associated with the number of
                     Far End C-bit Severely Errored Seconds
                     encountered by a DS3 interface in the previous 24
                     hour interval."
             ::= { dsx3FarEndTotalEntry 3 }

          dsx3FarEndTotalCCVs OBJECT-TYPE
             SYNTAX  Gauge
             ACCESS  read-only
             STATUS  mandatory
             DESCRIPTION
                     "The counter associated with the number of
                     Far End C-bit Coding Violations reported via the
                     far end block error count
                     encountered by a
                     DS3 interface in the previous 24 hour interval."
             ::= { dsx3FarEndTotalEntry 4 }

          dsx3FarEndTotalUASs OBJECT-TYPE
             SYNTAX  Gauge
             ACCESS  read-only
             STATUS  mandatory
             DESCRIPTION
                     "The counter associated with the number of
                     Far End unavailable seconds
                     encountered by a
                     DS3 interface in the previous 24 hour interval."
             ::= { dsx3FarEndTotalEntry 5 }


          -- the DS3/E3 Fractional Group

          -- Implementation of this group is optional.  It is designed
          -- for those systems dividing a DS3/E3 into channels
          -- containing different data streams that are of local
          -- interest.

          -- The DS3/E3 fractional table identifies which DS3/E3
          -- channels associated with a CSU are being used to
          -- support a logical interface, i.e., an entry in the
          -- interfaces table from the Internet-standard MIB.

          -- For example, consider a DS3 device with 4 high speed links
          -- carrying router traffic, a feed for voice, a feed for
          -- video, and a synchronous channel for a non-routed
          -- protocol.
          -- We might describe the allocation of channels, in the
          -- dsx3FracTable, as follows:

          -- dsx3FracIfIndex.2. 1 = 3    dsx3FracIfIndex.2.15 = 4
          -- dsx3FracIfIndex.2. 2 = 3    dsx3FracIfIndex.2.16 = 6
          -- dsx3FracIfIndex.2. 3 = 3    dsx3FracIfIndex.2.17 = 6
          -- dsx3FracIfIndex.2. 4 = 3    dsx3FracIfIndex.2.18 = 6
          -- dsx3FracIfIndex.2. 5 = 3    dsx3FracIfIndex.2.19 = 6
          -- dsx3FracIfIndex.2. 6 = 3    dsx3FracIfIndex.2.20 = 6
          -- dsx3FracIfIndex.2. 7 = 4    dsx3FracIfIndex.2.21 = 6
          -- dsx3FracIfIndex.2. 8 = 4    dsx3FracIfIndex.2.22 = 6
          -- dsx3FracIfIndex.2. 9 = 4    dsx3FracIfIndex.2.23 = 6
          -- dsx3FracIfIndex.2.10 = 4    dsx3FracIfIndex.2.24 = 6
          -- dsx3FracIfIndex.2.11 = 4    dsx3FracIfIndex.2.25 = 6
          -- dsx3FracIfIndex.2.12 = 5    dsx3FracIfIndex.2.26 = 6
          -- dsx3FracIfIndex.2.13 = 5    dsx3FracIfIndex.2.27 = 6
          -- dsx3FracIfIndex.2.14 = 5    dsx3FracIfIndex.2.28 = 6

          -- For dsx3M23, dsx3SYNTRAN, dsx3CbitParity, and
          -- dsx3ClearChannel there are 28 legal channels, numbered 1
          -- through 28.

          -- For e3Framed there are 16 legal channels,
          -- numbered 1 through 16.  The channels (1..16) correspond
          -- directly to the equivalently numbered time-slots.

          dsx3FracTable OBJECT-TYPE
              SYNTAX  SEQUENCE OF Dsx3FracEntry
              ACCESS  not-accessible
              STATUS  mandatory
              DESCRIPTION
                 "The DS3 Fractional table."
              ::= { ds3 13 }

          dsx3FracEntry OBJECT-TYPE
               SYNTAX  Dsx3FracEntry
               ACCESS  not-accessible
               STATUS  mandatory
               DESCRIPTION
                  "An entry in the DS3 Fractional table."
              INDEX   { dsx3FracIndex, dsx3FracNumber }
              ::= { dsx3FracTable 1 }

          Dsx3FracEntry ::=
              SEQUENCE {
                  dsx3FracIndex
                      INTEGER,
                  dsx3FracNumber
                      INTEGER,

                  dsx3FracIfIndex
                      INTEGER
              }


          dsx3FracIndex OBJECT-TYPE
              SYNTAX  INTEGER (1..'7fffffff'h)
              ACCESS  read-only
              STATUS  mandatory
              DESCRIPTION
                 "The index value which uniquely identifies  the
                 DS3  interface  to which this entry is applicable
                 The interface identified by a  particular
                 value  of  this  index is the same interface as
                 identified by the same value  an  dsx3LineIndex
                 object instance."
             ::= { dsx3FracEntry 1 }

          dsx3FracNumber OBJECT-TYPE
              SYNTAX  INTEGER (1..31)
              ACCESS  read-only
              STATUS  mandatory
              DESCRIPTION
                 "The channel number for this entry."
             ::= { dsx3FracEntry 2 }

          dsx3FracIfIndex OBJECT-TYPE
              SYNTAX  INTEGER (1..'7fffffff'h)
              ACCESS  read-write
              STATUS  mandatory
              DESCRIPTION
                 "An index value that uniquely identifies an
                 interface.  The interface identified by a particular
                 value of this index is the same  interface
                 as  identified by the same value an ifIndex
                 object instance. If no interface is currently using
                 a channel, the value should be zero.  If a
                 single interface occupies more  than  one  time
                 slot,  that ifIndex value will be found in multiple
                 time slots."
             ::= { dsx3FracEntry 3 }



          END

--===============================================================
-- File Name : BW-DeviceManagement-TFTP.mib
-- Author    : BroadSoft Inc.
-- Copyright 2000-2009, BroadSoft, Inc. All rights reserved. 
-- Proprietary Property of BroadSoft, Inc. Gaithersburg, MD.
--===============================================================

BW-DeviceManagement-TFTP DEFINITIONS ::= BEGIN
  IMPORTS
    enterprises, MODULE-IDENTITY, OBJECT-TYPE, Gauge32, Counter32
      FROM SNMPv2-SMI;
  
  broadsoft MODULE-IDENTITY
    LAST-UPDATED  "200905120000Z"
    ORGANIZATION  "Broadsoft, Inc"
    CONTACT-INFO  "Broadsoft, Inc
220 Perry Parkway
Gaithersburg, MD  20877
301-977-9440"
    DESCRIPTION
      "This is the MIB for the BroadWorks DeviceManagement-TFTP application."
      
    REVISION    "200905120000Z"
      DESCRIPTION     "Creation."
    ::= { enterprises 6431 }

  broadworks OBJECT IDENTIFIER
    ::= { broadsoft 1 }

  devicemanagementtftp OBJECT IDENTIFIER
    ::= { broadworks 16 }  
    
  protocol OBJECT IDENTIFIER
	::= { devicemanagementtftp 1 }
	
  tftp OBJECT IDENTIFIER
    ::= { protocol 1 }
    
  bwDeviceManagementTftpRrqIns				OBJECT-TYPE
  	SYNTAX		Counter32
  	MAX-ACCESS 	read-write
  	STATUS		current
  	DESCRIPTION
  			"This counter reflects the total number of TFTP RRQ received by BroadWorks."
  	::= { tftp 1 }
  	
  bwDeviceManagementTftpWrqIns				OBJECT-TYPE
  	SYNTAX		Counter32
  	MAX-ACCESS	read-write
  	STATUS		current
  	DESCRIPTION
  			"This counter reflects the total number of TFTP WRQ received by BroadWorks."
  	::= { tftp 2 }
  	
  bwDeviceManagementTftpDataIns				OBJECT-TYPE
  	SYNTAX		Counter32
  	MAX-ACCESS	read-write
  	STATUS		current
  	DESCRIPTION
  			"This counter reflects the total number of TFTP DATA received by BroadWorks."
  	::= { tftp 3 }	
  	
  bwDeviceManagementTftpDataOuts			OBJECT-TYPE
  	SYNTAX		Counter32
  	MAX-ACCESS	read-write
  	STATUS		current
  	DESCRIPTION
  			"This counter reflects the total number of TFTP DATA sent by BroadWorks."
  	::= { tftp 4 }	
  	
  bwDeviceManagementTftpAckIns				OBJECT-TYPE
  	SYNTAX		Counter32
  	MAX-ACCESS	read-write
  	STATUS		current
  	DESCRIPTION
  			"This counter reflects the total number of TFTP ACK received by BroadWorks."
  	::= { tftp 5 }	
  	
  bwDeviceManagementTftpAckOuts				OBJECT-TYPE
  	SYNTAX		Counter32
  	MAX-ACCESS	read-write
  	STATUS		current
  	DESCRIPTION
  			"This counter reflects the total number of TFTP ACK sent by BroadWorks."
  	::= { tftp 6 }	

  bwDeviceManagementTftpErrorIns			OBJECT-TYPE
  	SYNTAX		Counter32
  	MAX-ACCESS	read-write
  	STATUS		current
  	DESCRIPTION
  			"This counter reflects the total number of TFTP ERROR received by BroadWorks."
  	::= { tftp 7 }	
  	
  bwDeviceManagementTftpErrorOuts			OBJECT-TYPE
  	SYNTAX		Counter32
  	MAX-ACCESS	read-write
  	STATUS		current
  	DESCRIPTION
  			"This counter reflects the total number of TFTP ERROR sent by BroadWorks."
  	::= { tftp 8 }	
  	
  bwDeviceManagementNbOfActiveTftpTransfer	OBJECT-TYPE
  	SYNTAX		Gauge32
  	MAX-ACCESS	read-only
  	STATUS		current
  	DESCRIPTION
  			"Counts the total number of currently active TFTP transfer."
  	::= {tftp 9 }
  	
END

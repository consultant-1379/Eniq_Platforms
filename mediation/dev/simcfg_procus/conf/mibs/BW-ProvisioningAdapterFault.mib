-- File Name : BW-ProvisioningAdapterFault.mib
BW-ProvisioningAdapterFault DEFINITIONS ::= BEGIN
  IMPORTS
    NOTIFICATION-TYPE, MODULE-IDENTITY
      FROM SNMPv2-SMI
    common, identifier, timeStamp, alarmName, systemName, severity, alarmState, component, subcomponent, problemText, recommendedActionsText
      FROM BroadworksFault;

  systemFaults MODULE-IDENTITY
    LAST-UPDATED  "201407290000Z"
    ORGANIZATION  "Broadsoft, Inc"
    CONTACT-INFO  "Broadsoft, Inc.
9737 Washingtonian Blvd
Suite 350
Gaithersburg , MD 20878
Tel: +1-301-977-9440"
    DESCRIPTION
        "This MIB defines the faults for the BroadWorks ProvisioningAdapter Application."
    REVISION    "201407290000Z"
                DESCRIPTION     "Creation of the Fault MIB."
    ::=  {  common  1  }
    
bwProvisioningAdapterLicensedUserLimitReached  NOTIFICATION-TYPE
     OBJECTS     { identifier, timeStamp, alarmName, systemName, severity, component, subcomponent, problemText, recommendedActionsText }
     STATUS      current
     DESCRIPTION
         "The licensed user account limit has been reached.
 @severity:high
 @subcomponent:ProvisioningAdapter"
-- @feature:165352
    ::=  {  systemFaults 15301  }    

END

ERICSSON-MPE-MMS-PROXY-PM-MIB DEFINITIONS ::= BEGIN

IMPORTS
     MODULE-IDENTITY, OBJECT-TYPE, Gauge32 , Counter32 
          FROM SNMPv2-SMI

     MODULE-COMPLIANCE, OBJECT-GROUP
          FROM SNMPv2-CONF

     applIndex
          FROM NETWORK-SERVICES-MIB

     ItuPerceivedSeverity
          FROM ITU-ALARM-TC

     mpeModules
          FROM ERICSSON-MPE-REGISTRY-MIB ;

mpeMmsProxyPmModule MODULE-IDENTITY
   LAST-UPDATED    "201312111700Z"
   ORGANIZATION    "Ericsson AB"
   CONTACT-INFO    "        Ericsson AB

                    Postal: Ericsson AB
                            Kistagangen 26
                            SE - 164 80 Stockholm
                            Sweden

                       Tel: +46 8 7571500
                       Fax:

                    E-Mail: support@ericsson.com"
   DESCRIPTION     "Counters and states used by the MMS Caching Proxy 
                    functionality."
::= { mpeModules 9 }

mmsProxyPmObjects  OBJECT IDENTIFIER ::= { mpeMmsProxyPmModule 1 }

cachingProxy  OBJECT IDENTIFIER ::= { mmsProxyPmObjects 1 }

proxyLogic  OBJECT IDENTIFIER ::= { mmsProxyPmObjects 2 }

cachingLogic  OBJECT IDENTIFIER ::= { mmsProxyPmObjects 3 }

mmsProxyPmConformance  OBJECT IDENTIFIER ::= { mpeMmsProxyPmModule 3 }

mmsProxyPmGroups  OBJECT IDENTIFIER ::= { mmsProxyPmConformance 1 }

mmsProxyPmCompliances  OBJECT IDENTIFIER ::= { mmsProxyPmConformance 2 }

cachingProxyTable OBJECT-TYPE
   SYNTAX          SEQUENCE OF CachingProxyEntry
   MAX-ACCESS      not-accessible
   STATUS          current
   DESCRIPTION     "One entry is created for each application that 
                    contains the MMS Caching Proxy (9=MMS Caching Proxy, 22=MMS 
                    Common Cache)."
::= { cachingProxy 1 } 

cachingProxyEntry OBJECT-TYPE
   SYNTAX          CachingProxyEntry
   MAX-ACCESS      not-accessible
   STATUS          current
   DESCRIPTION     "The common MMS Caching Proxy counters and events."
   INDEX { applIndex }
::= { cachingProxyTable  1 }

CachingProxyEntry  ::= SEQUENCE
{
   cachingProxyConfigDataErr ItuPerceivedSeverity
}

cachingProxyConfigDataErr  OBJECT-TYPE
   SYNTAX          ItuPerceivedSeverity
   MAX-ACCESS      read-only
   STATUS          current
   DESCRIPTION     "A configuration data error has occurred in the MMS 
                    Caching Proxy. The cause of the error is given in the 
                    dynamic text."
::= { cachingProxyEntry 1 }

proxyLogicTable OBJECT-TYPE
   SYNTAX          SEQUENCE OF ProxyLogicEntry
   MAX-ACCESS      not-accessible
   STATUS          current
   DESCRIPTION     "One entry is created for each application that 
                    contains the MMS Proxy Logic (9=MMS Caching Proxy, 22=MMS 
                    Common Cache)."
::= { proxyLogic 1 } 

proxyLogicEntry OBJECT-TYPE
   SYNTAX          ProxyLogicEntry
   MAX-ACCESS      not-accessible
   STATUS          current
   DESCRIPTION     "The counters and events of the MMS Proxy Logic."
   INDEX { applIndex }
::= { proxyLogicTable  1 }

ProxyLogicEntry  ::= SEQUENCE
{
   proxyLogicContentTypeErr         Counter32,
   proxyLogicFaultyMMS              Counter32,
   proxyLogicMsisdnMissing          Counter32,
   proxyLogicHttpMethodNotSupported Counter32,
   proxyLogicMSISDNDecodeError      Counter32,
   proxyLogicMSISDNDecryptError     Counter32,
   proxyLogicMSISDNEOwnerError      Counter32,
   proxyLogicTransIdFormatError     Counter32,
   proxyLogicMsgFileNotFound        Counter32
}

proxyLogicContentTypeErr  OBJECT-TYPE
   SYNTAX          Counter32
   MAX-ACCESS      read-only
   STATUS          current
   DESCRIPTION     "Shows the number of requests/responses that have a 
                    Content-Type different from the configured Content Type 
                    parameter in MMSPush Engine. The request with wrong 
                    Content-Type will not be accepted! A high value of this 
                    counter indicates that the node is not configured 
                    properly..
                    The applUptime epoch of the application instance 
                    should be used as reference point for this counter."
::= { proxyLogicEntry 1 }

proxyLogicFaultyMMS  OBJECT-TYPE
   SYNTAX          Counter32
   MAX-ACCESS      read-only
   STATUS          current
   DESCRIPTION     "Shows the number of requests/responses that have a 
                    faulty MMS content. A high level on this counter 
                    indicates problems and the MMSs sent must be investigated in 
                    more detail.
                    The applUptime epoch of the application instance 
                    should be used as reference point for this counter."
::= { proxyLogicEntry 2 }

proxyLogicMsisdnMissing  OBJECT-TYPE
   SYNTAX          Counter32
   MAX-ACCESS      read-only
   STATUS          current
   DESCRIPTION     "Shows the number of requests that are missing the 
                    MSISDN information in the configured header. Requests not 
                    having the configured header with the MSISDN will be 
                    rejected. A high level on this counter indicates error 
                    in the node configuration.
                    The applUptime epoch of the application instance 
                    should be used as reference point for this counter."
::= { proxyLogicEntry 3 }

proxyLogicHttpMethodNotSupported  OBJECT-TYPE
   SYNTAX          Counter32
   MAX-ACCESS      read-only
   STATUS          current
   DESCRIPTION     "Shows the number of requests that issues a not 
                    supported HTTP method in the MMS Caching Proxy. The only 
                    supported methods are GET and POST. A high value of this 
                    counter indicates faulty usage of the MMS Caching 
                    Proxy.
                    The applUptime epoch of the application instance 
                    should be used as reference point for this counter."
::= { proxyLogicEntry 4 }

proxyLogicMSISDNDecodeError  OBJECT-TYPE
   SYNTAX          Counter32
   MAX-ACCESS      read-only
   STATUS          current
   DESCRIPTION     "Shows the number of times the decoding of the MSISDN 
                    fails.
                    The applUptime epoch of the application instance 
                    should be used as reference point for this counter."
::= { proxyLogicEntry 5 }

proxyLogicMSISDNDecryptError  OBJECT-TYPE
   SYNTAX          Counter32
   MAX-ACCESS      read-only
   STATUS          current
   DESCRIPTION     "Shows the number of times the decrypting of the 
                    MSISDN fails.
                    The applUptime epoch of the application instance 
                    should be used as reference point for this counter."
::= { proxyLogicEntry 6 }

proxyLogicMSISDNEOwnerError  OBJECT-TYPE
   SYNTAX          Counter32
   MAX-ACCESS      read-only
   STATUS          current
   DESCRIPTION     "Shows the number of times a try is made to fetch an 
                    MMS by an MSISDN that is not the owner of MMS.
                    The applUptime epoch of the application instance 
                    should be used as reference point for this counter."
::= { proxyLogicEntry 7 }

proxyLogicTransIdFormatError  OBJECT-TYPE
   SYNTAX          Counter32
   MAX-ACCESS      read-only
   STATUS          current
   DESCRIPTION     "Shows the number of times transaction-ID in the POST 
                    messages from the terminals are not according to the 
                    expected format. A high value of this this counter 
                    indicates that the MMS Caching Proxy is getting the POSTs 
                    not amid for this node!
                    The applUptime epoch of the application instance 
                    should be used as reference point for this counter."
::= { proxyLogicEntry 9 }

proxyLogicMsgFileNotFound  OBJECT-TYPE
   SYNTAX          Counter32
   MAX-ACCESS      read-only
   STATUS          current
   DESCRIPTION     "Shows the number of times the MMS Caching Proxy gets 
                    in requests to access deleted (not found) files. The 
                    files are probably deleted because of the expiry time 
                    have elapsed. 
                    The applUptime epoch of the application instance 
                    should be used as reference point for this counter."
::= { proxyLogicEntry 10 }

cachingLogicTable OBJECT-TYPE
   SYNTAX          SEQUENCE OF CachingLogicEntry
   MAX-ACCESS      not-accessible
   STATUS          current
   DESCRIPTION     "One entry is created for each application that 
                    contains the MMS Proxy Logic (9=MMS Caching Proxy, 22=MMS 
                    Common Cache)."
::= { cachingLogic 1 } 

cachingLogicEntry OBJECT-TYPE
   SYNTAX          CachingLogicEntry
   MAX-ACCESS      not-accessible
   STATUS          current
   DESCRIPTION     "The cache related paramters in the MMS Caching Proxy."
   INDEX { applIndex }
::= { cachingLogicTable  1 }

CachingLogicEntry  ::= SEQUENCE
{
   cachingLogicNumOfBInCache   Gauge32,
   cachingLogicNumOfEntInCache Gauge32,
   cachingLogicCacheMiss       Counter32,
   cachingLogicNumOfReq        Counter32
}

cachingLogicNumOfBInCache  OBJECT-TYPE
   SYNTAX          Gauge32
   MAX-ACCESS      read-only
   STATUS          current
   DESCRIPTION     "Shows the number of bytes in the Cache."
::= { cachingLogicEntry 1 }

cachingLogicNumOfEntInCache  OBJECT-TYPE
   SYNTAX          Gauge32
   MAX-ACCESS      read-only
   STATUS          current
   DESCRIPTION     "Shows the number of entries in the Cache."
::= { cachingLogicEntry 2 }

cachingLogicCacheMiss  OBJECT-TYPE
   SYNTAX          Counter32
   MAX-ACCESS      read-only
   STATUS          current
   DESCRIPTION     "Shows the number of cache misses in the MMS Caching 
                    Proxy. 
                    The applUptime epoch of the application instance 
                    should be used as reference point for this counter."
::= { cachingLogicEntry 3 }

cachingLogicNumOfReq  OBJECT-TYPE
   SYNTAX          Counter32
   MAX-ACCESS      read-only
   STATUS          current
   DESCRIPTION     "Shows the number of requests in the MMS Caching 
                    Proxy. 
                    The applUptime epoch of the application instance 
                    should be used as reference point for this counter."
::= { cachingLogicEntry 4 }

-- Compliance Statements

mmsProxyCompliance MODULE-COMPLIANCE
   STATUS          current
   DESCRIPTION     "The compliance statement for mms caching proxy."
   MODULE          -- this module
   MANDATORY-GROUPS {mmsProxyConfGroup}
::= { mmsProxyPmCompliances 1 }

-- Units of Conformance

mmsProxyConfGroup OBJECT-GROUP
   OBJECTS { cachingProxyConfigDataErr,
             proxyLogicContentTypeErr,
             proxyLogicFaultyMMS,
             proxyLogicMsisdnMissing,
             proxyLogicHttpMethodNotSupported,
             proxyLogicMSISDNDecodeError,
             proxyLogicMSISDNDecryptError,
             proxyLogicMSISDNEOwnerError,
             proxyLogicTransIdFormatError,
             proxyLogicMsgFileNotFound,
             cachingLogicNumOfBInCache,
             cachingLogicNumOfEntInCache,
             cachingLogicCacheMiss,
             cachingLogicNumOfReq}
   STATUS          current
   DESCRIPTION     "A collection of objects providing performance and 
                    fault management information about a mms caching proxy."
::= { mmsProxyPmGroups 1 }
END

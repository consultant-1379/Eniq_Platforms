-- File Name : BW-LicenseControllerFault.mib
BW-LicenseControllerFault DEFINITIONS ::= BEGIN
  IMPORTS
    NOTIFICATION-TYPE, MODULE-IDENTITY
      FROM SNMPv2-SMI
    common, identifier, timeStamp, alarmName, systemName, severity, alarmState, component, subcomponent, problemText, recommendedActionsText, npName, npValidLicenseId, npInvalidLicenseId, npNFMName, npNodeName, npLicenseIdInstance, npExecutorType
      FROM BroadworksFault;

  systemFaults MODULE-IDENTITY
    LAST-UPDATED  "201409100000Z"
    ORGANIZATION  "Broadsoft, Inc"
    CONTACT-INFO  "Broadsoft, Inc.
9737 Washingtonian Blvd
Suite 350
Gaithersburg , MD 20878
Tel: +1-301-977-9440"
    DESCRIPTION
        "This MIB defines the faults for the BroadWorks license controller Application."
    REVISION    "201409100000Z"
                DESCRIPTION     "Creation of the Fault MIB."
    ::=  {  common  1  }

  bwPMLicenseControllerLaunched  NOTIFICATION-TYPE
    OBJECTS     { identifier, timeStamp, alarmName, systemName, severity, component, subcomponent, problemText, recommendedActionsText }
    STATUS      current
    DESCRIPTION
        "This notification indicates that the license controller has been started.
@severity:informational
@subcomponent:processmonitor
@correlationrules:bwPMLicenseControllerLaunched, bwPMLicenseControllerShutDown, bwPMLicenseControllerRestarted, bwPMLicenseControllerDeath, and bwPMLicenseControllerOutOfMemory can be correlated into a single alarm.  These events have to be considered as a transition of the state machine for the management of the license controller process"
-- @feature:217550
    ::=  {  systemFaults 15401  }

  bwPMLicenseControllerShutDown  NOTIFICATION-TYPE
    OBJECTS     { identifier, timeStamp, alarmName, systemName, severity, component, subcomponent, problemText, recommendedActionsText }
    STATUS      current
    DESCRIPTION
        "This notification indicates that the license controller has been manually shut down.
@severity:informational
@subcomponent:processmonitor
@correlationrules:bwPMLicenseControllerLaunched, bwPMLicenseControllerShutDown, bwPMLicenseControllerRestarted, bwPMLicenseControllerDeath, and bwPMLicenseControllerOutOfMemory can be correlated into a single alarm.  These events have to be considered as a transition of the state machine for the management of the license controller process"
-- @feature:217550
    ::=  {  systemFaults 15402  }

  bwPMLicenseControllerRestarted  NOTIFICATION-TYPE
    OBJECTS     { identifier, timeStamp, alarmName, systemName, severity, component, subcomponent, problemText, recommendedActionsText }
    STATUS      current
    DESCRIPTION
        "This notification provides the date and time of the license controller restart.
@severity:informational
@subcomponent:processmonitor
@correlationrules:bwPMLicenseControllerLaunched, bwPMLicenseControllerShutDown, bwPMLicenseControllerRestarted, bwPMLicenseControllerDeath, and bwPMLicenseControllerOutOfMemory can be correlated into a single alarm.  These events have to be considered as a transition of the state machine for the management of the license controller process"
-- @feature:217550
    ::=  {  systemFaults 15403  }

  bwPMLicenseControllerDeath  NOTIFICATION-TYPE
    OBJECTS     { identifier, timeStamp, alarmName, systemName, severity, component, subcomponent, problemText, recommendedActionsText }
    STATUS      current
    DESCRIPTION
        "This notification provides the date and time of the license controller death.
@severity:critical
@subcomponent:processmonitor
@correlationrules:bwPMLicenseControllerLaunched, bwPMLicenseControllerShutDown, bwPMLicenseControllerRestarted, bwPMLicenseControllerDeath, and bwPMLicenseControllerOutOfMemory can be correlated into a single alarm.  These events have to be considered as a transition of the state machine for the management of the license controller process"
-- @feature:217550
    ::=  {  systemFaults 15404  }
    
bwPMLicenseControllerOutOfMemory  NOTIFICATION-TYPE
     OBJECTS     { identifier, timeStamp, alarmName, systemName, severity, component, subcomponent, problemText, recommendedActionsText }
     STATUS      current
     DESCRIPTION
         "This notification provides the date and time when the license controller application ran out of memory.
 @severity:high
 @subcomponent:processmonitor
 @correlationrules:bwPMLicenseControllerLaunched, bwPMLicenseControllerShutDown, bwPMLicenseControllerRestarted, bwPMLicenseControllerDeath, and bwPMLicenseControllerOutOfMemory can be correlated into a single alarm.  These events have to be considered as a transition of the state machine for the management of the license controller process."
-- @feature:217550
    ::=  {  systemFaults 15405  }

  bwLicenseControllerNodeUsingUnauthorizedLicense  NOTIFICATION-TYPE
    OBJECTS     { identifier, timeStamp, alarmName, systemName, severity, component, subcomponent, problemText, recommendedActionsText, npName, npValidLicenseId, npInvalidLicenseId }
    STATUS      current
    DESCRIPTION
        "This notification indicates that the specified node is requesting grant for a license different than the one that has been assigned to the node.
@severity:high
@subcomponent:licenseController"
-- @feature:217550
    ::=  {  systemFaults 15406  }
    
  bwLicenseControllerNodeLicenseUpdateFailure  NOTIFICATION-TYPE
    OBJECTS     { identifier, timeStamp, alarmName, systemName, severity, component, subcomponent, problemText, recommendedActionsText, npNFMName, npNodeName }
    STATUS      current
    DESCRIPTION
        "This notification indicates that the Network Function Manager failed to send a license update notification to the specified node. 
@severity:high
@subcomponent:licenseController"
-- @feature:217550
    ::=  {  systemFaults 15407  }
    
  bwLicenseControllerNodeUsingUndeployedLicenseInstance  NOTIFICATION-TYPE
    OBJECTS     { identifier, timeStamp, alarmName, systemName, severity, component, subcomponent, problemText, recommendedActionsText, npNodeName, npLicenseIdInstance }
    STATUS      current
    DESCRIPTION
        "This notification indicates that the specified node is not using the deployed license instance. 
@severity:high
@subcomponent:licenseController"
-- @feature:217550
    ::=  {  systemFaults 15408  }
    
  bwLicenseControllerExecutorQueueUsageExceeded  NOTIFICATION-TYPE
    OBJECTS     { identifier, timeStamp, alarmName, systemName, severity, alarmState, component, subcomponent, problemText, recommendedActionsText, npExecutorType }
    STATUS      current
    DESCRIPTION
        "This alarm indicates the usage ratio of the executor queue exceeded the threshold level.
@severity:high
@subcomponent:licenseController"
-- @feature:217550
    ::=  {  systemFaults 15409  }
    
  bwLicenseControllerExecutorQueueLatencyExceeded  NOTIFICATION-TYPE
    OBJECTS     { identifier, timeStamp, alarmName, systemName, severity, alarmState, component, subcomponent, problemText, recommendedActionsText, npExecutorType }
    STATUS      current
    DESCRIPTION
        "This alarm indicates that the executor queue latency exceeded the threshold level.
@severity:high
@subcomponent:licenseController"
-- @feature:217550
    ::=  {  systemFaults 15410  }
    
  bwLicenseControllerExecutorThreadPoolProcessingTimeExceeded  NOTIFICATION-TYPE
    OBJECTS     { identifier, timeStamp, alarmName, systemName, severity, alarmState, component, subcomponent, problemText, recommendedActionsText, npExecutorType }
    STATUS      current
    DESCRIPTION
        "The alarm indicates that the executor thread pool processing time exceeded the threshold level.
@severity:high
@subcomponent:licenseController"
-- @feature:217550
    ::=  {  systemFaults 15411  }
    
  bwLicenseControllerExecutorThreadPoolBusyExceeded  NOTIFICATION-TYPE
    OBJECTS     { identifier, timeStamp, alarmName, systemName, severity, alarmState, component, subcomponent, problemText, recommendedActionsText }
    STATUS      current
    DESCRIPTION
        "The alarm indicates that the executor thread pool busy ratio exceeded the threshold level.
@severity:high
@subcomponent:licenseController"
-- @feature:217550
    ::=  {  systemFaults 15412  }
    
END

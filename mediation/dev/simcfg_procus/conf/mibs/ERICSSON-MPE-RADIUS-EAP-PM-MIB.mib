ERICSSON-MPE-RADIUS-EAP-PM-MIB DEFINITIONS ::= BEGIN

IMPORTS
     MODULE-IDENTITY, OBJECT-TYPE, Gauge32 , Counter32 
          FROM SNMPv2-SMI

     MODULE-COMPLIANCE, OBJECT-GROUP
          FROM SNMPv2-CONF

     applIndex
          FROM NETWORK-SERVICES-MIB

     ItuPerceivedSeverity
          FROM ITU-ALARM-TC

     mpeModules
          FROM ERICSSON-MPE-REGISTRY-MIB ;

mpeRadiusEapPmModule MODULE-IDENTITY
   LAST-UPDATED    "201603231116Z"
   ORGANIZATION    "Ericsson AB"
   CONTACT-INFO    "        Ericsson AB

                    Postal: Ericsson AB
                            Kistagangen 26
                            SE - 164 80 Stockholm
                            Sweden

                       Tel: +46 8 7571500
                       Fax:

                    E-Mail: support@ericsson.com"
   DESCRIPTION     "Radius Eap events and counters."
::= { mpeModules 33 }

radiusEapPmObjects  OBJECT IDENTIFIER ::= { mpeRadiusEapPmModule 1 }

radEapQueryCnt  OBJECT IDENTIFIER ::= { radiusEapPmObjects 2 }

radEapQueryError  OBJECT IDENTIFIER ::= { radiusEapPmObjects 3 }

radiusEapPmConformance  OBJECT IDENTIFIER ::= { mpeRadiusEapPmModule 3 }

radiusEapPmGroups  OBJECT IDENTIFIER ::= { radiusEapPmConformance 1 }

radiusEapPmCompliances  OBJECT IDENTIFIER ::= { radiusEapPmConformance 2 }

radEapQueryCntTable OBJECT-TYPE
   SYNTAX          SEQUENCE OF RadEapQueryCntEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { radEapQueryCnt 1 } 

radEapQueryCntEntry OBJECT-TYPE
   SYNTAX          RadEapQueryCntEntry
   MAX-ACCESS      not-accessible
   STATUS          current
   DESCRIPTION     "Counters for RADIUS Eap Query. Only valid if the 
                    RADIUS Eap Query functionality is used."
   INDEX { applIndex }
::= { radEapQueryCntTable  1 }

RadEapQueryCntEntry  ::= SEQUENCE
{
   radEapQueryCntPrimReq         Counter32,
   radEapQueryCntPrimAcc         Counter32,
   radEapQueryCntPrimChal        Counter32,
   radEapQueryCntPrimRej         Counter32,
   radEapQueryCntPrimFail        Counter32,
   radEapQueryCntPrimAvgRespTime Gauge32,
   radEapQueryCntSecReq          Counter32,
   radEapQueryCntSecAcc          Counter32,
   radEapQueryCntSecChal         Counter32,
   radEapQueryCntSecRej          Counter32,
   radEapQueryCntSecFail         Counter32,
   radEapQueryCntSecAvgRespTime  Gauge32
}

radEapQueryCntPrimReq  OBJECT-TYPE
   SYNTAX          Counter32
   MAX-ACCESS      read-only
   STATUS          current
   DESCRIPTION     "Counter holding the number of RADIUS Eap access 
                    requests sent to the primary AAA server.
                    The applUptime epoch of the application instance 
                    should be used as reference point for this counter."
::= { radEapQueryCntEntry 2 }

radEapQueryCntPrimAcc  OBJECT-TYPE
   SYNTAX          Counter32
   MAX-ACCESS      read-only
   STATUS          current
   DESCRIPTION     "Counter holding the number of RADIUS Eap access 
                    accepted received from the primary AAA server.
                    The applUptime epoch of the application instance 
                    should be used as reference point for this counter."
::= { radEapQueryCntEntry 3 }

radEapQueryCntPrimChal  OBJECT-TYPE
   SYNTAX          Counter32
   MAX-ACCESS      read-only
   STATUS          current
   DESCRIPTION     "Counter holding the number of RADIUS Eap Access 
                    Challange received from primary AAA server.
                    The applUptime epoch of the application instance 
                    should be used as reference point for this counter."
::= { radEapQueryCntEntry 4 }

radEapQueryCntPrimRej  OBJECT-TYPE
   SYNTAX          Counter32
   MAX-ACCESS      read-only
   STATUS          current
   DESCRIPTION     "Counter holding the number of RADIUS Eap access 
                    rejected received from the primary AAA server.
                    The applUptime epoch of the application instance 
                    should be used as reference point for this counter."
::= { radEapQueryCntEntry 5 }

radEapQueryCntPrimFail  OBJECT-TYPE
   SYNTAX          Counter32
   MAX-ACCESS      read-only
   STATUS          current
   DESCRIPTION     "Counter holding the number of failed (time-out) 
                    RADIUS Eap access requests to the primary AAA server.
                    The applUptime epoch of the application instance 
                    should be used as reference point for this counter."
::= { radEapQueryCntEntry 6 }

radEapQueryCntPrimAvgRespTime  OBJECT-TYPE
   SYNTAX          Gauge32
   MAX-ACCESS      read-only
   STATUS          current
   DESCRIPTION     "Shows the average response time in milliseconds to 
                    get a response from the primary RADIUS Eap AAA server."
::= { radEapQueryCntEntry 7 }

radEapQueryCntSecReq  OBJECT-TYPE
   SYNTAX          Counter32
   MAX-ACCESS      read-only
   STATUS          current
   DESCRIPTION     "Counter holding the number of RADIUS Eap access 
                    requests sent to the secondary AAA server.
                    The applUptime epoch of the application instance 
                    should be used as reference point for this counter."
::= { radEapQueryCntEntry 8 }

radEapQueryCntSecAcc  OBJECT-TYPE
   SYNTAX          Counter32
   MAX-ACCESS      read-only
   STATUS          current
   DESCRIPTION     "Counter holding the number of RADIUS Eap access 
                    accepted received from the secondary AAA server.
                    The applUptime epoch of the application instance 
                    should be used as reference point for this counter."
::= { radEapQueryCntEntry 9 }

radEapQueryCntSecChal  OBJECT-TYPE
   SYNTAX          Counter32
   MAX-ACCESS      read-only
   STATUS          current
   DESCRIPTION     "Counter holding the number of RADIUS Eap access 
                    challenge received from the secondary AAA server.
                    The applUptime epoch of the application instance 
                    should be used as reference point for this counter."
::= { radEapQueryCntEntry 10 }

radEapQueryCntSecRej  OBJECT-TYPE
   SYNTAX          Counter32
   MAX-ACCESS      read-only
   STATUS          current
   DESCRIPTION     "Counter holding the number of RADIUS Eap access 
                    rejected received from the secondary AAA server.
                    The applUptime epoch of the application instance 
                    should be used as reference point for this counter."
::= { radEapQueryCntEntry 11 }

radEapQueryCntSecFail  OBJECT-TYPE
   SYNTAX          Counter32
   MAX-ACCESS      read-only
   STATUS          current
   DESCRIPTION     "Counter holding the number of failed (time-out) 
                    RADIUS Eap access requests to the secondary AAA server.
                    The applUptime epoch of the application instance 
                    should be used as reference point for this counter."
::= { radEapQueryCntEntry 12 }

radEapQueryCntSecAvgRespTime  OBJECT-TYPE
   SYNTAX          Gauge32
   MAX-ACCESS      read-only
   STATUS          current
   DESCRIPTION     "Shows the average response time in milliseconds to 
                    get a response from the secondary RADIUS AAA server."
::= { radEapQueryCntEntry 13 }

radEapQueryErrorTable OBJECT-TYPE
   SYNTAX          SEQUENCE OF RadEapQueryErrorEntry
   MAX-ACCESS      not-accessible
   STATUS          current
   DESCRIPTION     "One entry is created for each application that 
                    contains the pull proxy module 
                    (1=Secure Connection Oriented, 2=Secure 
                    Connectionless, 3=Connection-Oriented, 4=Connectionless, 5=W-HTTP)."
::= { radEapQueryError 1 } 

radEapQueryErrorEntry OBJECT-TYPE
   SYNTAX          RadEapQueryErrorEntry
   MAX-ACCESS      not-accessible
   STATUS          current
   DESCRIPTION     "Alarms for RADIUS Eap Query. Only valid if the RADIUS 
                    Eap Query functionality is used."
   INDEX { applIndex }
::= { radEapQueryErrorTable  1 }

RadEapQueryErrorEntry  ::= SEQUENCE
{
   radEapQueryErrorToPrim   ItuPerceivedSeverity,
   radEapQueryErrorToSecond ItuPerceivedSeverity
}

radEapQueryErrorToPrim  OBJECT-TYPE
   SYNTAX          ItuPerceivedSeverity
   MAX-ACCESS      read-only
   STATUS          current
   DESCRIPTION     "."
::= { radEapQueryErrorEntry 2 }

radEapQueryErrorToSecond  OBJECT-TYPE
   SYNTAX          ItuPerceivedSeverity
   MAX-ACCESS      read-only
   STATUS          current
   DESCRIPTION     "."
::= { radEapQueryErrorEntry 3 }

-- Compliance Statements

radiusEapCompliance MODULE-COMPLIANCE
   STATUS          current
   DESCRIPTION     "The compliance statement for radius eap."
   MODULE          -- this module
   MANDATORY-GROUPS {radiusEapConfGroup}
::= { radiusEapPmCompliances 1 }

-- Units of Conformance

radiusEapConfGroup OBJECT-GROUP
   OBJECTS { radEapQueryCntPrimReq,
             radEapQueryCntPrimAcc,
             radEapQueryCntPrimChal,
             radEapQueryCntPrimRej,
             radEapQueryCntPrimFail,
             radEapQueryCntPrimAvgRespTime,
             radEapQueryCntSecReq,
             radEapQueryCntSecAcc,
             radEapQueryCntSecChal,
             radEapQueryCntSecRej,
             radEapQueryCntSecFail,
             radEapQueryCntSecAvgRespTime,
             radEapQueryErrorToPrim,
             radEapQueryErrorToSecond}
   STATUS          current
   DESCRIPTION     "A collection of objects providing performance and 
                    fault management information about a radius eap."
::= { radiusEapPmGroups 1 }
END

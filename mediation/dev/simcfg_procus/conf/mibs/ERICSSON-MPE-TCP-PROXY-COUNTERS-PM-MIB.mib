ERICSSON-MPE-TCP-PROXY-COUNTERS-PM-MIB DEFINITIONS ::= BEGIN

IMPORTS
     MODULE-IDENTITY, OBJECT-TYPE, Gauge32 , Counter32 
          FROM SNMPv2-SMI

     MODULE-COMPLIANCE, OBJECT-GROUP
          FROM SNMPv2-CONF

     applIndex
          FROM NETWORK-SERVICES-MIB

     mpeModules
          FROM ERICSSON-MPE-REGISTRY-MIB ;

mpeTcpProxyCountersPmModule MODULE-IDENTITY
   LAST-UPDATED    "201511200053Z"
   ORGANIZATION    "Ericsson AB"
   CONTACT-INFO    "        Ericsson AB

                    Postal: Ericsson AB
                            Kistagangen 26
                            SE - 164 80 Stockholm
                            Sweden

                       Tel: +46 8 7571500
                       Fax:

                    E-Mail: support@ericsson.com"
   DESCRIPTION     "The capacity counters for the interfaces of the proxy 
                    based on protocols. What counter instance that is 
                    used for a specific protocol is configured with the 
                    'Transparent Proxy/Transparent TCP Proxy/Counter instance 
                    number for protocols' parameter"
::= { mpeModules 36 }

tcpProxyCountersPmObjects  OBJECT IDENTIFIER ::= { mpeTcpProxyCountersPmModule 1 }

tcpServer  OBJECT IDENTIFIER ::= { tcpProxyCountersPmObjects 1 }

tcpProxyCountersPmConformance  OBJECT IDENTIFIER ::= { mpeTcpProxyCountersPmModule 3 }

tcpProxyCountersPmGroups  OBJECT IDENTIFIER ::= { tcpProxyCountersPmConformance 1 }

tcpProxyCountersPmCompliances  OBJECT IDENTIFIER ::= { tcpProxyCountersPmConformance 2 }

tcpServerTable OBJECT-TYPE
   SYNTAX          SEQUENCE OF TcpServerEntry
   MAX-ACCESS      not-accessible
   STATUS          current
   DESCRIPTION     "One entry is created for each protocol that is 
                    detected in Multiservice Proxy."
::= { tcpServer 1 } 

tcpServerEntry OBJECT-TYPE
   SYNTAX          TcpServerEntry
   MAX-ACCESS      not-accessible
   STATUS          current
   DESCRIPTION     "The counters for traffic visibility at tcp level."
   INDEX { applIndex }
::= { tcpServerTable  1 }

TcpServerEntry  ::= SEQUENCE
{
   tcpServerTotalConnectAttempts Counter32,
   tcpServerReceivedBytes        Counter32,
   tcpServerSentBytes            Counter32,
   tcpServerConnections          Gauge32,
   tcpServerAverageRtt           Gauge32,
   tcpServerMaxRtt               Gauge32,
   tcpServerRetransmits          Counter32,
   tcpServerLostPackets          Counter32,
   tcpServerJobs                 Counter32,
   tcpServerMaxExec              Gauge32,
   tcpServerMinExec              Gauge32,
   tcpServerAvgExec              Gauge32,
   tcpServerStdevExec            Gauge32,
   tcpServerMaxIdle              Gauge32,
   tcpServerMinIdle              Gauge32,
   tcpServerAvgIdle              Gauge32,
   tcpServerStdevIdle            Gauge32,
   tcpServerMaxQueue             Gauge32,
   tcpServerMinQueue             Gauge32,
   tcpServerAvgQueue             Gauge32,
   tcpServerStdevQueue           Gauge32,
   tcpServerRejConnectAttempts   Counter32
}

tcpServerTotalConnectAttempts  OBJECT-TYPE
   SYNTAX          Counter32
   MAX-ACCESS      read-only
   STATUS          current
   DESCRIPTION     "Counter indicating the total number of connection 
                    attempts over Tcp Proxy. 
                    The applUptime epoch of the application instance 
                    should be used as reference point for this counter."
::= { tcpServerEntry 2 }

tcpServerReceivedBytes  OBJECT-TYPE
   SYNTAX          Counter32
   MAX-ACCESS      read-only
   STATUS          current
   DESCRIPTION     "Counter holding the total number of bytes received by 
                    the Tcp Server from client terminals. 
                    The applUptime epoch of the application instance 
                    should be used as reference point for this counter."
::= { tcpServerEntry 3 }

tcpServerSentBytes  OBJECT-TYPE
   SYNTAX          Counter32
   MAX-ACCESS      read-only
   STATUS          current
   DESCRIPTION     "Counter holding the total number of bytes sent by the 
                    Tcp Server to client terminals. 
                    The applUptime epoch of the application instance 
                    should be used as reference point for this counter."
::= { tcpServerEntry 4 }

tcpServerConnections  OBJECT-TYPE
   SYNTAX          Gauge32
   MAX-ACCESS      read-only
   STATUS          current
   DESCRIPTION     "Counter holding the number of active Tcp Server 
                    connections at a given time."
::= { tcpServerEntry 5 }

tcpServerAverageRtt  OBJECT-TYPE
   SYNTAX          Gauge32
   MAX-ACCESS      read-only
   STATUS          current
   DESCRIPTION     "Counter holding smoothed average TCP RTT on the 
                    server side of MSP."
::= { tcpServerEntry 6 }

tcpServerMaxRtt  OBJECT-TYPE
   SYNTAX          Gauge32
   MAX-ACCESS      read-only
   STATUS          current
   DESCRIPTION     "Counter holding max TCP RTT value on the server side 
                    of MSP."
::= { tcpServerEntry 7 }

tcpServerRetransmits  OBJECT-TYPE
   SYNTAX          Counter32
   MAX-ACCESS      read-only
   STATUS          current
   DESCRIPTION     "Counter holding the total number of retransmits form 
                    the Tcp Server to client terminals. 
                    The applUptime epoch of the application instance 
                    should be used as reference point for this counter."
::= { tcpServerEntry 8 }

tcpServerLostPackets  OBJECT-TYPE
   SYNTAX          Counter32
   MAX-ACCESS      read-only
   STATUS          current
   DESCRIPTION     "Counter holding the total number of lost packets sent 
                    by the Tcp Server to client terminals. 
                    The applUptime epoch of the application instance 
                    should be used as reference point for this counter."
::= { tcpServerEntry 9 }

tcpServerJobs  OBJECT-TYPE
   SYNTAX          Counter32
   MAX-ACCESS      read-only
   STATUS          current
   DESCRIPTION     "Counter holding the number of jobs executed. 
                    The applUptime epoch of the application instance 
                    should be used as reference point for this counter."
::= { tcpServerEntry 10 }

tcpServerMaxExec  OBJECT-TYPE
   SYNTAX          Gauge32
   MAX-ACCESS      read-only
   STATUS          current
   DESCRIPTION     "Counter holding the execution time of the longest job 
                    that was executed in measurement interval (measured 
                    in micro seconds)."
::= { tcpServerEntry 11 }

tcpServerMinExec  OBJECT-TYPE
   SYNTAX          Gauge32
   MAX-ACCESS      read-only
   STATUS          current
   DESCRIPTION     "Counter holding the execution time of shortest job 
                    that was executed in measurement interval (measured in 
                    micro seconds)."
::= { tcpServerEntry 12 }

tcpServerAvgExec  OBJECT-TYPE
   SYNTAX          Gauge32
   MAX-ACCESS      read-only
   STATUS          current
   DESCRIPTION     "Counter holding the average execution time of jobs 
                    that were executed in measurement interval (measured in 
                    micro seconds)."
::= { tcpServerEntry 13 }

tcpServerStdevExec  OBJECT-TYPE
   SYNTAX          Gauge32
   MAX-ACCESS      read-only
   STATUS          current
   DESCRIPTION     "Counter holding the standard deviation of the 
                    execution time of jobs that were executed in measurement 
                    interval (measured in micro seconds)."
::= { tcpServerEntry 14 }

tcpServerMaxIdle  OBJECT-TYPE
   SYNTAX          Gauge32
   MAX-ACCESS      read-only
   STATUS          current
   DESCRIPTION     "Counter holding idle time of the worker thread that 
                    was most idle in measurement interval (measured in %)."
::= { tcpServerEntry 15 }

tcpServerMinIdle  OBJECT-TYPE
   SYNTAX          Gauge32
   MAX-ACCESS      read-only
   STATUS          current
   DESCRIPTION     "Counter holding idle time of the worker thread that 
                    was least idle in measurement interval (measured in %)."
::= { tcpServerEntry 16 }

tcpServerAvgIdle  OBJECT-TYPE
   SYNTAX          Gauge32
   MAX-ACCESS      read-only
   STATUS          current
   DESCRIPTION     "Counter holding the average idle time of the worker 
                    threads in measurement interval (measured in %)."
::= { tcpServerEntry 17 }

tcpServerStdevIdle  OBJECT-TYPE
   SYNTAX          Gauge32
   MAX-ACCESS      read-only
   STATUS          current
   DESCRIPTION     "Counter holding the standard deviation of the idle 
                    time of the worker threads in measurement interval 
                    (measured in %)."
::= { tcpServerEntry 18 }

tcpServerMaxQueue  OBJECT-TYPE
   SYNTAX          Gauge32
   MAX-ACCESS      read-only
   STATUS          current
   DESCRIPTION     "Counter holding the maximum queuing time for 
                    connection attemps in measurement interval (measured in micro 
                    seconds)."
::= { tcpServerEntry 19 }

tcpServerMinQueue  OBJECT-TYPE
   SYNTAX          Gauge32
   MAX-ACCESS      read-only
   STATUS          current
   DESCRIPTION     "Counter holding the minimum queuing time for 
                    connections attempts in measurement interval (measured in 
                    micro seconds)."
::= { tcpServerEntry 20 }

tcpServerAvgQueue  OBJECT-TYPE
   SYNTAX          Gauge32
   MAX-ACCESS      read-only
   STATUS          current
   DESCRIPTION     "Counter holding the average queuing time for 
                    connections attempts in measurement interval (measured in 
                    micro seconds)."
::= { tcpServerEntry 21 }

tcpServerStdevQueue  OBJECT-TYPE
   SYNTAX          Gauge32
   MAX-ACCESS      read-only
   STATUS          current
   DESCRIPTION     "Counter holding the standard deviation of the queuing 
                    time for connection attempts in measurement interval 
                    (measured in micro seconds)."
::= { tcpServerEntry 22 }

tcpServerRejConnectAttempts  OBJECT-TYPE
   SYNTAX          Counter32
   MAX-ACCESS      read-only
   STATUS          current
   DESCRIPTION     "Counter indicating the total number of connection 
                    attempts over Tcp Proxy that were rejected because of 
                    overload. 
                    The applUptime epoch of the application instance 
                    should be used as reference point for this counter."
::= { tcpServerEntry 23 }

-- Compliance Statements

tcpProxyCountersCompliance MODULE-COMPLIANCE
   STATUS          current
   DESCRIPTION     "The compliance statement for tcp level counters."
   MODULE          -- this module
   MANDATORY-GROUPS {tcpProxyCountersConfGroup}
::= { tcpProxyCountersPmCompliances 1 }

-- Units of Conformance

tcpProxyCountersConfGroup OBJECT-GROUP
   OBJECTS { tcpServerTotalConnectAttempts,
             tcpServerReceivedBytes,
             tcpServerSentBytes,
             tcpServerConnections,
             tcpServerAverageRtt,
             tcpServerMaxRtt,
             tcpServerRetransmits,
             tcpServerLostPackets,
             tcpServerJobs,
             tcpServerMaxExec,
             tcpServerMinExec,
             tcpServerAvgExec,
             tcpServerStdevExec,
             tcpServerMaxIdle,
             tcpServerMinIdle,
             tcpServerAvgIdle,
             tcpServerStdevIdle,
             tcpServerMaxQueue,
             tcpServerMinQueue,
             tcpServerAvgQueue,
             tcpServerStdevQueue,
             tcpServerRejConnectAttempts}
   STATUS          current
   DESCRIPTION     "A collection of objects providing performance and 
                    fault management information about a tcp level counters."
::= { tcpProxyCountersPmGroups 1 }
END

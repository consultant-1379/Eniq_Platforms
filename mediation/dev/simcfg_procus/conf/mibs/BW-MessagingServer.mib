--===============================================================
-- File Name : BW-MessagingServer.mib 
-- Date      : Dec 14 2013
-- Author    : BroadSoft Inc.
--===============================================================

BW-MessagingServer DEFINITIONS ::= BEGIN
	IMPORTS
		enterprises, MODULE-IDENTITY, NOTIFICATION-TYPE, OBJECT-TYPE, Counter32, Gauge32, Counter64, Integer32
			FROM SNMPv2-SMI
		MODULE-COMPLIANCE, OBJECT-GROUP          
			FROM SNMPv2-CONF
		DateAndTime, DisplayString
			FROM SNMPv2-TC;

	broadsoft	MODULE-IDENTITY
		LAST-UPDATED  "201312140000Z"
		ORGANIZATION	"Broadsoft, Inc"
    CONTACT-INFO  "Broadsoft, Inc.
9737 Washingtonian Blvd
Suite 350
Gaithersburg , MD 20878
Tel: +1-301-977-9440"
		DESCRIPTION
				"This is the System Management Information structure for the
				Broadsoft enterprise."
		REVISION    "201312140000Z"
                DESCRIPTION     "Messaging Server MIB creation"
		::=  {  enterprises  6431  }
		
  broadworks	OBJECT IDENTIFIER
		::=  {  broadsoft  1  }		
	
  ums           OBJECT IDENTIFIER
		::=  {  broadworks  38  }
	
  bwUMSMibConformance OBJECT IDENTIFIER
		::=  {  ums  1000  }

-- ################### ...............................
--                     ...............................
-- ################### ...............................

	
-- BroadWorks UMS Server MIB Conformance Definition  ...........................................

bwUMSMibGroups		OBJECT IDENTIFIER ::= { bwUMSMibConformance 1 }
bwUMSMibCompliancy	OBJECT IDENTIFIER ::= { bwUMSMibConformance 2 }

-- units of conformance

bwUMSBasicCompliance MODULE-COMPLIANCE
	STATUS current
     	DESCRIPTION
		"BroadWorks UMS Server MIB compliance"
	MODULE -- this module
	::= { bwUMSMibCompliancy 1 }		
	    
-- End of MIB file - Do not put anything behind this line ...........................................

END

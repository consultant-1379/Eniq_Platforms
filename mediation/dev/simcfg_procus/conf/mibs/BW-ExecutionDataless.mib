-- File Name : BW-ExecutionDataless.mib

BW-ExecutionDataless DEFINITIONS ::= BEGIN
  IMPORTS
    DateAndTime, DisplayString 
      FROM SNMPv2-TC
    MODULE-COMPLIANCE, OBJECT-GROUP 
      FROM SNMPv2-CONF
    enterprises, MODULE-IDENTITY, OBJECT-TYPE, Gauge32, Counter32, Integer32, Unsigned32 
      FROM SNMPv2-SMI;

  broadsoft MODULE-IDENTITY
    LAST-UPDATED "201006230000Z"
    ORGANIZATION "Broadsoft, Inc"
    CONTACT-INFO  "Broadsoft, Inc.
9737 Washingtonian Blvd
Suite 350
Gaithersburg , MD 20878
Tel: +1-301-977-9440"
    DESCRIPTION
      "This is the System Management Information structure for the BroadSoft Dataless Execution."

    REVISION "201006230000Z"
      DESCRIPTION "Creation of the Dataless Execution MIB."
    ::= { enterprises 6431 }

  broadworks OBJECT IDENTIFIER
    ::= { broadsoft 1 }

  executionDataless OBJECT IDENTIFIER
    ::= { broadworks 22 }

-- Execution Server modules  ...........................................

  imsModule OBJECT IDENTIFIER
    ::= { executionDataless 4 }

  callpModule OBJECT IDENTIFIER
    ::= { executionDataless 7 }

  smtpModule OBJECT IDENTIFIER
    ::= { executionDataless 8 }

  sipModule OBJECT IDENTIFIER
    ::= { executionDataless 9 }

  services OBJECT IDENTIFIER
    ::= { executionDataless 11 }

  mssModule OBJECT IDENTIFIER
    ::= { executionDataless 12 }

  nrsModule OBJECT IDENTIFIER
    ::= { executionDataless 13 }

  pmtModule OBJECT IDENTIFIER
    ::= { executionDataless 15 }

  systemModule OBJECT IDENTIFIER
    ::= { executionDataless 16 }

  management OBJECT IDENTIFIER
    ::= { executionDataless 17 }

  capModule OBJECT IDENTIFIER
    ::= { executionDataless 19 }

  smdiModule OBJECT IDENTIFIER
    ::= { executionDataless 20 }

  mediaModule OBJECT IDENTIFIER
    ::= { executionDataless 21 }

  wspModule OBJECT IDENTIFIER
    ::= { executionDataless 22 }

  realtimeAccountingModule OBJECT IDENTIFIER
    ::= { executionDataless 23 }

  externalCallLogsModule OBJECT IDENTIFIER
    ::= { executionDataless 24 }

  commonCommModule OBJECT IDENTIFIER
    ::= { executionDataless 25 }

  tcpModule OBJECT IDENTIFIER
    ::= { executionDataless 26 }

  concurrentModule OBJECT IDENTIFIER
    ::= { executionDataless 27 }

  soapModule OBJECT IDENTIFIER
    ::= { executionDataless 28 }

  smppModule OBJECT IDENTIFIER
    ::= { executionDataless 29 }

  dnsModule OBJECT IDENTIFIER
    ::= { executionDataless 30 }

  offlineChargingModule OBJECT IDENTIFIER
    ::= { executionDataless 31 }

  ocicModule OBJECT IDENTIFIER
    ::= { executionDataless 32 }

  onlineChargingModule OBJECT IDENTIFIER
    ::= { executionDataless 33 }

  diameterModule OBJECT IDENTIFIER
    ::= { executionDataless 34 }

  shRelayInterfaceModule OBJECT IDENTIFIER
    ::= { executionDataless 35 }

  shModule OBJECT IDENTIFIER
    ::= { executionDataless 36 }

  bwDXSExecutionMibConformance OBJECT IDENTIFIER
    ::= { executionDataless 1000 }

-- Stats and other modules.

  imsStats OBJECT IDENTIFIER
    ::= { imsModule 1 }

  callpStats OBJECT IDENTIFIER
    ::= { callpModule 1 }

  profileLoading OBJECT IDENTIFIER
    ::= { callpModule 2 }

  smtpStats OBJECT IDENTIFIER
    ::= { smtpModule 1 }

  sipStats OBJECT IDENTIFIER
    ::= { sipModule 1 }

  congestionManagement OBJECT IDENTIFIER
    ::= { sipModule 2 }

  capStats OBJECT IDENTIFIER
    ::= { capModule 1 }

  smdiStats OBJECT IDENTIFIER
    ::= { smdiModule 1 }

  mediaStats OBJECT IDENTIFIER
    ::= { mediaModule 1 }

  wspStats OBJECT IDENTIFIER
    ::= { wspModule 1 }

  realtimeAccountingStats OBJECT IDENTIFIER
    ::= { realtimeAccountingModule 1 }

  externalCallLogsStats OBJECT IDENTIFIER
    ::= { externalCallLogsModule 1 }

  commonCommStats OBJECT IDENTIFIER
    ::= { commonCommModule 1 }

  tcpStats OBJECT IDENTIFIER
    ::= { tcpModule 1 }
                
  concurrentStats OBJECT IDENTIFIER
    ::= { concurrentModule 1 }
                
  soapStats OBJECT IDENTIFIER
    ::= { soapModule 1 }

  smppStats OBJECT IDENTIFIER
    ::= { smppModule 1 }

  dnsStats OBJECT IDENTIFIER
    ::= { dnsModule 1 }

  offlineChargingStats OBJECT IDENTIFIER
    ::= { offlineChargingModule 1 }

  ocicStats OBJECT IDENTIFIER
    ::= { ocicModule 1 }

  onlineChargingStats OBJECT IDENTIFIER
    ::= { onlineChargingModule 1 }

  accountCodes OBJECT IDENTIFIER
    ::= { services 1 }

  anonymousCallRejection OBJECT IDENTIFIER
    ::= { services 2 }

  authentication OBJECT IDENTIFIER
    ::= { services 3 }

  autoAttendant OBJECT IDENTIFIER
    ::= { services 4 }

  callCapacity OBJECT IDENTIFIER
    ::= { services 5 }

  callForwardingAlways OBJECT IDENTIFIER
    ::= { services 6 }

  callForwardingBusy OBJECT IDENTIFIER
    ::= { services 7 }

  callForwardingNoAnswer OBJECT IDENTIFIER
    ::= { services 8 }

  callNotify OBJECT IDENTIFIER
    ::= { services 9 }

  callPark OBJECT IDENTIFIER
    ::= { services 10 }

  callPickup OBJECT IDENTIFIER
    ::= { services 11 }

  callReturn OBJECT IDENTIFIER
    ::= { services 12 }

  commPilotCallManager OBJECT IDENTIFIER
    ::= { services 13 }

  doNotDisturb OBJECT IDENTIFIER
    ::= { services 14 }

  flashCallTransfer OBJECT IDENTIFIER
    ::= { services 15 }

  flashCallWaiting OBJECT IDENTIFIER
    ::= { services 16 }

  flashConsultation OBJECT IDENTIFIER
    ::= { services 17 }

  flashThreeWayCall OBJECT IDENTIFIER
    ::= { services 18 }

  huntGroups OBJECT IDENTIFIER
    ::= { services 19 }

  incomingCallingPlan OBJECT IDENTIFIER
    ::= { services 20 }

  ipPhone OBJECT IDENTIFIER
    ::= { services 21 }

  lastNumberRedial OBJECT IDENTIFIER
    ::= { services 22 }

  outgoingCallingPlan OBJECT IDENTIFIER
    ::= { services 23 }

  priorityAlert OBJECT IDENTIFIER
    ::= { services 24 }

  selectiveCallAcceptance OBJECT IDENTIFIER
    ::= { services 25 }

  selectiveCallForward OBJECT IDENTIFIER
    ::= { services 26 }

  selectiveCallRejection OBJECT IDENTIFIER
    ::= { services 27 }

  simRingPersonal OBJECT IDENTIFIER
    ::= { services 28 }

  voiceMessaging OBJECT IDENTIFIER
    ::= { services 29 }

  intercept OBJECT IDENTIFIER
    ::= { services 31 }

  callingLineIDDeliveryBlock OBJECT IDENTIFIER
    ::= { services 33 }

  sessionAudit OBJECT IDENTIFIER
    ::= { services 34 }

  callWaiting OBJECT IDENTIFIER
    ::= { services 36 }

  alternateNumbers OBJECT IDENTIFIER
    ::= { services 37 }

  cot OBJECT IDENTIFIER
    ::= { services 38 }

  sd8 OBJECT IDENTIFIER
    ::= { services 39 }

  musicOnHold OBJECT IDENTIFIER
    ::= { services 40 }

  thirdPartyMWIControl OBJECT IDENTIFIER
    ::= { services 42 }

  callForwardGroupNoAnswer OBJECT IDENTIFIER
    ::= { services 44 }

  sd100 OBJECT IDENTIFIER
    ::= { services 45 }

  thirdPartyVMail OBJECT IDENTIFIER
    ::= { services 46 }

  directedCallPickup OBJECT IDENTIFIER
    ::= { services 47 }

  flashCallHold OBJECT IDENTIFIER
    ::= { services 48 }

  dpubi OBJECT IDENTIFIER
    ::= { services 50 }

  acb OBJECT IDENTIFIER
    ::= { services 51 }

  sequentialRing OBJECT IDENTIFIER
    ::= { services 52 }

  ringTimeout OBJECT IDENTIFIER
    ::= { services 53 }

  mct OBJECT IDENTIFIER
    ::= { services 55 }

  preferredCarrier OBJECT IDENTIFIER
    ::= { services 58 }
  
  familySimRing OBJECT IDENTIFIER
    ::= { services 59 }

  diversionInhibitor OBJECT IDENTIFIER
    ::= { services 60 }

  customRingback OBJECT IDENTIFIER
    ::= { services 64 }

  faxMessaging   OBJECT IDENTIFIER
    ::= { services 66 }
          
  externalemergencyrouting OBJECT IDENTIFIER
    ::= { services 67 }

  callForwardingNotReachable OBJECT IDENTIFIER
    ::= { services 69 }

  expensiveCallNotification OBJECT IDENTIFIER
    ::= { services 74 }

  locationControl OBJECT IDENTIFIER
    ::= { services 75 }

  callRetrieve OBJECT IDENTIFIER
    ::= { services 76 }

  broadworksAnywhere OBJECT IDENTIFIER
    ::= { services 77 }

  communicationBarring OBJECT IDENTIFIER
    ::= { services 79 }

  callBridge OBJECT IDENTIFIER
    ::= { services 80 }

  directoryNumberHunting OBJECT IDENTIFIER
    ::= { services 81 }

  adviceOfCharge OBJECT IDENTIFIER
    ::= { services 82 }

  serviceCentralizationContinuity OBJECT IDENTIFIER
    ::= { services 83 }

  callLogs OBJECT IDENTIFIER
    ::= { services 84 }

  externalCustomRingback OBJECT IDENTIFIER
    ::= { services 85 }

  callForwardingGroupNotReachable OBJECT IDENTIFIER
    ::= { services 86 }

  groupNightForwarding OBJECT IDENTIFIER
    ::= { services 87 }

  preAlertingAnnouncement OBJECT IDENTIFIER
    ::= { services 88 }

  hoteling OBJECT IDENTIFIER
    ::= { services 89 }

  mssStats OBJECT IDENTIFIER
    ::= { mssModule 1 }

  nrsStats OBJECT IDENTIFIER
    ::= { nrsModule 1 }

  pmtStats OBJECT IDENTIFIER
    ::= { pmtModule 1 }

  diameterStats OBJECT IDENTIFIER
    ::= { diameterModule 1 }

  shRelayInterfaceStats OBJECT IDENTIFIER
    ::= { shRelayInterfaceModule 1 }

  callLogQueue OBJECT IDENTIFIER
    ::= { callLogs 1 }

  callLogProcessors OBJECT IDENTIFIER
    ::= { callLogs 2 }

  shStats OBJECT IDENTIFIER
    ::= { shModule 1 }


-- Protocol :: Incoming Mail Server ...........................................

  bwDXSIMSSuccessfulConnectionAttempts OBJECT-TYPE
    SYNTAX      Counter32
    MAX-ACCESS  read-write
    STATUS      current
    DESCRIPTION 
        "This counter reflects the number of successful connection to incoming mail server."
    ::= { imsStats 1 }

  bwDXSIMSUnsuccessfulConnectionAttempts OBJECT-TYPE
    SYNTAX      Counter32
    MAX-ACCESS  read-write
    STATUS      current
    DESCRIPTION 
        "This counter reflects the total number of unsuccessful connection to incoming mail server."
    ::= { imsStats 2 }

  bwDXSIMSSuccessfulDownLoadAttempts OBJECT-TYPE
    SYNTAX      Counter32
    MAX-ACCESS  read-write
    STATUS      current
    DESCRIPTION 
        "This counter reflects the number of messages downloaded  from incoming mail server."
    ::= { imsStats 3 }

  bwDXSIMSUnsuccessfulDownLoadAttempts OBJECT-TYPE
    SYNTAX      Counter32
    MAX-ACCESS  read-write
    STATUS      current
    DESCRIPTION 
        "This counter reflects the number of unsuccessful   message download attempted on incoming mail server."
    ::= { imsStats 4 }

  bwDXSIMSMaxSessions OBJECT-TYPE
    SYNTAX      Gauge32
    MAX-ACCESS  read-only
    STATUS      current
    DESCRIPTION 
        "Maximum number of incoming mail server sessions simultaneously active since the system was started. A session is defined as a complete dialog between the execution server and the incoming mail server, and includes elements such as mailbox information requests, message download requests, and idle time."
    ::= { imsStats 5 }

  bwDXSIMSAvgSessions OBJECT-TYPE
    SYNTAX      Gauge32
    MAX-ACCESS  read-only
    STATUS      current
    DESCRIPTION 
        "Average number of incoming mail server sessions simultaneously active, based on a rolling average over the last 100 sessions.  Each data point is computed right after the creation of a session. A session is defined as a complete dialog between the execution server and the incoming mail server, and includes elements such as mailbox information requests, message download requests, and idle time."
    ::= { imsStats 6 }

  bwDXSIMSMaxThreads OBJECT-TYPE
    SYNTAX      Gauge32
    MAX-ACCESS  read-only
    STATUS      current
    DESCRIPTION 
        "Maximum number of incoming mail server threads simultaneously active since the system was started.  IMS threads are used when a session actively communicates with an IMS, and waits for a response.  A session does not use an IMS thread while it is idle, e.g. prompting or waiting for user input."
    ::= { imsStats 7 }

  bwDXSIMSAvgThreads OBJECT-TYPE
    SYNTAX      Gauge32
    MAX-ACCESS  read-only
    STATUS      current
    DESCRIPTION 
        "Average number of incoming mail server threads simultaneously active, based on a rolling average over the last 100 sessions. Each data point is computed right after the creation of a session. IMS threads are used when a session actively communicates with an IMS, and waits for a response.  A session does not use an IMS thread while it is idle, e.g. prompting or waiting for user input."
    ::= { imsStats 8 }

  bwDXSIMSMaxServiceTime OBJECT-TYPE
    SYNTAX      Gauge32
    MAX-ACCESS  read-only
    STATUS      current
    DESCRIPTION 
        "Maximum time in milliseconds required to process an incoming mail server request, since the system was started.  This service time includes any queuing time if applicable.  This time also includes the time required by the IMS to respond to a request such as a mailbox information request, or a message download request."
    ::= { imsStats 9 }

  bwDXSIMSAvgServiceTime OBJECT-TYPE
    SYNTAX      Gauge32
    MAX-ACCESS  read-only
    STATUS      current
    DESCRIPTION 
        "Average time in milliseconds required to process an incoming mail server request, based on a rolling average over the last 100 requests.  This service time includes any queuing time if applicable.  This time also includes the time required by the IMS to respond to a request such as a mailbox information request, or a message download request."
    ::= { imsStats 10 }

  bwDXSIMSNumKeepAlive OBJECT-TYPE
    SYNTAX      Counter32
    MAX-ACCESS  read-write
    STATUS      current
    DESCRIPTION 
        "Number of times a keep-alive message was sent to an incoming mail server.  Such a keep-alive message is sent when an IMS session lasts several minutes."
    ::= { imsStats 11 }

  bwDXSIMSNumDroppedRequests OBJECT-TYPE
    SYNTAX      Counter32
    MAX-ACCESS  read-write
    STATUS      current
    DESCRIPTION 
        "Number of incoming mail server requests dropped because the number of IMS threads was too low, and the queue was full.  Note that a single session can make several requests to the IMS."
    ::= { imsStats 12 }

-- CallP ...........................................

  bwDXSCallpNetworkOriginationAttempts OBJECT-TYPE
    SYNTAX      Counter32
    MAX-ACCESS  read-write
    STATUS      current
    DESCRIPTION 
        "This count indicates the total number of originations
         from the network."
    ::= { callpStats 1 }

  bwDXSCallpNetworkTerminationAttempts OBJECT-TYPE
    SYNTAX      Counter32
    MAX-ACCESS  read-write
    STATUS      current
    DESCRIPTION 
        "This count indicates the total number of termination
         attempts to the network."
    ::= { callpStats 2 }

  bwDXSCallpNetworkTerminationsAnswered OBJECT-TYPE
    SYNTAX      Counter32
    MAX-ACCESS  read-write
    STATUS      current
    DESCRIPTION 
        "This count indicates the total number of termination
         attempts to the network answered."
    ::= { callpStats 3 }

  bwDXSCallpUserOriginationAttempts OBJECT-TYPE
    SYNTAX      Counter32
    MAX-ACCESS  read-write
    STATUS      current
    DESCRIPTION 
        "This counts indicates the total number of origination
         attempts from the access network(BroadWorks user/virtual user)."
    ::= { callpStats 4 }

  bwDXSCallpUserTerminationAttempts OBJECT-TYPE
    SYNTAX      Counter32
    MAX-ACCESS  read-write
    STATUS      current
    DESCRIPTION 
        "This counts indicates the total number of termination
         attempts to the access network(BroadWorks user/virtual user)."
    ::= { callpStats 5 }

  bwDXSCallpUserTerminationsAnswered OBJECT-TYPE
    SYNTAX      Counter32
    MAX-ACCESS  read-write
    STATUS      current
    DESCRIPTION 
        "This counts indicates the total number of termination
         attempts to the access network answered."
    ::= { callpStats 6 }

  bwDXSCallpEmergencyCallAttempts OBJECT-TYPE
    SYNTAX      Counter32
    MAX-ACCESS  read-write
    STATUS      current
    DESCRIPTION 
        "This counter represents the number of Emergency call originations made by user's of the system"
    ::= { callpStats 7 }

  bwDXSCallpEmergencyCallAlarms OBJECT-TYPE
    SYNTAX      Counter32
    MAX-ACCESS  read-write
    STATUS      current
    DESCRIPTION 
        "The counter represents the number of times an alarm is generated for an emergency call routing failure"
    ::= { callpStats 8 }

  bwDXSCallpSPTable OBJECT-TYPE
    SYNTAX      SEQUENCE OF BwCallpSPEntry
    MAX-ACCESS  not-accessible
    STATUS      current
    DESCRIPTION 
        "This table contains the counters for CallP measurements for service providers"
    ::= { callpStats 9 }

  bwDXSCallpSPEntry OBJECT-TYPE
    SYNTAX      BwCallpSPEntry
    MAX-ACCESS  not-accessible
    STATUS      current
    DESCRIPTION 
        "This row contains the counters for CallP measurements for a service provider"
    INDEX       { bwDXSCallpSPIndex }
    ::= { bwDXSCallpSPTable 1 }

  BwCallpSPEntry ::= SEQUENCE {
    bwDXSCallpSPIndex                                      Unsigned32,
    bwDXSCallpSPID                                         DisplayString,
    bwDXSCallpSPUserOriginationAttempts                    Counter32,
    bwDXSCallpSPUserTerminationAttempts                    Counter32,
    bwDXSCallpSPUserTerminationsAnswered                   Counter32,
    bwDXSCallpSPEmergencyCallAttempts                      Counter32,
    bwDXSCallpSPMaximumNumberofSimCallsExceeded            Counter32,
    bwDXSCallpSPMaximumCallTimeforAnsweredCallsExceeded    Counter32,
    bwDXSCallpSPMaximumCallTimeforUnansweredCallsExceeded  Counter32,
    bwDXSCallpSPMaximumNumberofSimVideoCallsExceeded       Counter32,
    bwDXSCallpSPMediaTypeNotSupported                      Counter32,
    bwDXSCallpSPGETSOrigSessionCount                       Counter32,
    bwDXSCallpSPGETSTermSessionCount                       Counter32,
    bwDXSCallpSPE911PSAPCallBackAttempts                   Counter32
  }

  bwDXSCallpSPIndex OBJECT-TYPE
    SYNTAX      Unsigned32
    MAX-ACCESS  read-only
    STATUS      current
    DESCRIPTION 
        "This integer represents the a service provider index in the system"
    ::= { bwDXSCallpSPEntry 1 }

  bwDXSCallpSPID OBJECT-TYPE
    SYNTAX      DisplayString
    MAX-ACCESS  read-only
    STATUS      current
    DESCRIPTION 
        "This string represents a service provider ID"
    ::= { bwDXSCallpSPEntry 2 }

  bwDXSCallpSPUserOriginationAttempts OBJECT-TYPE
    SYNTAX      Counter32
    MAX-ACCESS  read-write
    STATUS      current
    DESCRIPTION 
        "This counts indicates the total number of origination attempts from the access network(BroadWorks user/virtual user) for a service provider"
    ::= { bwDXSCallpSPEntry 3 }

  bwDXSCallpSPUserTerminationAttempts OBJECT-TYPE
    SYNTAX      Counter32
    MAX-ACCESS  read-write
    STATUS      current
    DESCRIPTION 
        "This counts indicates the total number of termination attempts to the access network(BroadWorks user/virtual user) for a service provider"
    ::= { bwDXSCallpSPEntry 4 }

  bwDXSCallpSPUserTerminationsAnswered OBJECT-TYPE
    SYNTAX      Counter32
    MAX-ACCESS  read-write
    STATUS      current
    DESCRIPTION 
        "This counts indicates the total number of termination attempts to the access network answered for a service provider"
    ::= { bwDXSCallpSPEntry 5 }

  bwDXSCallpSPEmergencyCallAttempts OBJECT-TYPE
    SYNTAX      Counter32
    MAX-ACCESS  read-write
    STATUS      current
    DESCRIPTION 
        "This counter represents the number of Emergency call originations made by Broadworks users for a service provider"
    ::= { bwDXSCallpSPEntry 6 }

  bwDXSCallpSPMaximumNumberofSimCallsExceeded OBJECT-TYPE
    SYNTAX      Counter32
    MAX-ACCESS  read-write
    STATUS      current
    DESCRIPTION 
        "This counter reflects the number of times that the maximum number of simultaneous calls for a user is exceeded for a service provider."
    ::= { bwDXSCallpSPEntry 7 }

  bwDXSCallpSPMaximumCallTimeforAnsweredCallsExceeded OBJECT-TYPE
    SYNTAX      Counter32
    MAX-ACCESS  read-write
    STATUS      current
    DESCRIPTION 
        "This counter reflects the number of times that the maximum call time for answered calls is exceeded for a service provider."
    ::= { bwDXSCallpSPEntry 8 }

  bwDXSCallpSPMaximumCallTimeforUnansweredCallsExceeded OBJECT-TYPE
    SYNTAX      Counter32
    MAX-ACCESS  read-write
    STATUS      current
    DESCRIPTION 
        "This counter reflects the number of times that the maximum call time for unanswered calls is exceeded for a service provider."
    ::= { bwDXSCallpSPEntry 9 }

  bwDXSCallpSPMaximumNumberofSimVideoCallsExceeded OBJECT-TYPE
    SYNTAX      Counter32
    MAX-ACCESS  read-write
    STATUS      current
    DESCRIPTION 
        "The counter reflects the number of times that the maximum number of simultaneous video calls for a user is exceeded."
    ::= { bwDXSCallpSPEntry 10 }

  bwDXSCallpSPMediaTypeNotSupported OBJECT-TYPE
    SYNTAX      Counter32
    MAX-ACCESS  read-write
    STATUS      current
    DESCRIPTION 
        "The counter reflects the number of times that the media type (codec) within a service provider has not been supported for a user."
    ::= { bwDXSCallpSPEntry 11 }

  bwDXSCallpSPGETSOrigSessionCount OBJECT-TYPE
    SYNTAX      Counter32
    MAX-ACCESS  read-write
    STATUS      current
    DESCRIPTION 
        "The number of GETS originating sessions for a service provider."
-- @feature:191436
    ::= { bwDXSCallpSPEntry 12 }

  bwDXSCallpSPGETSTermSessionCount OBJECT-TYPE
    SYNTAX      Counter32
    MAX-ACCESS  read-write
    STATUS      current
    DESCRIPTION 
        "The number of GETS terminating sessions for a service provider."
-- @feature:191436
    ::= { bwDXSCallpSPEntry 13 }

  bwDXSCallpSPE911PSAPCallBackAttempts OBJECT-TYPE
    SYNTAX      Counter32
    MAX-ACCESS  read-write
    STATUS      current
    DESCRIPTION 
        "This service provider counter tracks the number of times an E911 Public Safety Answering Point (PSAP) attempts to call back users that previously made emergency calls."
-- @feature:BW-2320
    ::= { bwDXSCallpSPEntry 14 }

  bwDXSCallpActiveCalls OBJECT-TYPE
    SYNTAX      Gauge32
    MAX-ACCESS  read-only
    STATUS      current
    DESCRIPTION 
        "This counts indicates the total number of active session.
         An active session is define as an active originating session.
         Any call that needs to perform a lookup in a NetworkServer/LocationServer
         will be counted as 2 calls, once for each call leg."
    ::= { callpStats 10 }

  bwDXSCallpGroupTable OBJECT-TYPE
    SYNTAX      SEQUENCE OF BwCallpGroupEntry
    MAX-ACCESS  not-accessible
    STATUS      current
    DESCRIPTION 
        "This table contains the counters for CallP measurements for groups"
    ::= { callpStats 11 }

  bwDXSCallpGroupEntry OBJECT-TYPE
    SYNTAX      BwCallpGroupEntry
    MAX-ACCESS  not-accessible
    STATUS      current
    DESCRIPTION 
        "This row contains the counters for CallP measurements for a group"
    INDEX       { bwDXSCallpGroupIndex }
    ::= { bwDXSCallpGroupTable 1 }

  BwCallpGroupEntry ::= SEQUENCE {
    bwDXSCallpGroupIndex                                       Unsigned32,
    bwDXSCallpGroupID                                          DisplayString,
    bwDXSCallpGroupUserOriginationAttempts                     Counter32,
    bwDXSCallpGroupUserTerminationAttempts                     Counter32,
    bwDXSCallpGroupUserTerminationsAnswered                    Counter32,
    bwDXSCallpGroupEmergencyCallAttempts                       Counter32,
    bwDXSCallpGroupMaximumNumberofSimCallsExceeded             Counter32,
    bwDXSCallpGroupMaximumCallTimeforAnsweredCallsExceeded     Counter32,
    bwDXSCallpGroupMaximumCallTimeforUnansweredCallsExceeded   Counter32,
    bwDXSCallpGroupMaximumNumberofSimVideoCallsExceeded        Counter32,
    bwDXSCallpGroupMediaTypeNotSupported                       Counter32,
    bwDXSCallpGroupGETSOrigSessionCount                        Counter32,
    bwDXSCallpGroupGETSTermSessionCount                        Counter32,
    bwDXSCallpGroupE911PSAPCallBackAttempts                    Counter32
  }

  bwDXSCallpGroupIndex OBJECT-TYPE
    SYNTAX      Unsigned32
    MAX-ACCESS  read-only
    STATUS      current
    DESCRIPTION 
        "This integer represents the a group index in the system"
    ::= { bwDXSCallpGroupEntry 1 }

  bwDXSCallpGroupID OBJECT-TYPE
    SYNTAX      DisplayString
    MAX-ACCESS  read-only
    STATUS      current
    DESCRIPTION 
        "This string represents a group ID"
    ::= { bwDXSCallpGroupEntry 2 }

  bwDXSCallpGroupUserOriginationAttempts OBJECT-TYPE
    SYNTAX      Counter32
    MAX-ACCESS  read-write
    STATUS      current
    DESCRIPTION 
        "This counts indicates the total number of origination attempts from the access network(BroadWorks user/virtual user) for a group"
    ::= { bwDXSCallpGroupEntry 3 }

  bwDXSCallpGroupUserTerminationAttempts OBJECT-TYPE
    SYNTAX      Counter32
    MAX-ACCESS  read-write
    STATUS      current
    DESCRIPTION 
        "This counts indicates the total number of termination attempts to the access network(BroadWorks user/virtual user) for a group"
    ::= { bwDXSCallpGroupEntry 4 }

  bwDXSCallpGroupUserTerminationsAnswered OBJECT-TYPE
    SYNTAX      Counter32
    MAX-ACCESS  read-write
    STATUS      current
    DESCRIPTION 
        "This counts indicates the total number of termination attempts to the access network answered for a group"
    ::= { bwDXSCallpGroupEntry 5 }

  bwDXSCallpGroupEmergencyCallAttempts OBJECT-TYPE
    SYNTAX      Counter32
    MAX-ACCESS  read-write
    STATUS      current
    DESCRIPTION 
        "This counter represents the number of Emergency call originations made by Broadworks users for a group"
    ::= { bwDXSCallpGroupEntry 6 }

  bwDXSCallpGroupMaximumNumberofSimCallsExceeded OBJECT-TYPE
    SYNTAX      Counter32
    MAX-ACCESS  read-write
    STATUS      current
    DESCRIPTION 
        "This counter reflects the number of times that the maximum number of simultaneous calls for a user is exceeded for a group."
    ::= { bwDXSCallpGroupEntry 7 }

  bwDXSCallpGroupMaximumCallTimeforAnsweredCallsExceeded OBJECT-TYPE
    SYNTAX      Counter32
    MAX-ACCESS  read-write
    STATUS      current
    DESCRIPTION 
        "This counter reflects the number of times that the maximum call time for answered calls is exceeded for a group."
    ::= { bwDXSCallpGroupEntry 8 }

  bwDXSCallpGroupMaximumCallTimeforUnansweredCallsExceeded OBJECT-TYPE
    SYNTAX      Counter32
    MAX-ACCESS  read-write
    STATUS      current
    DESCRIPTION 
        "This counter reflects the number of times that the maximum call time for unanswered calls is exceeded for a group."
    ::= { bwDXSCallpGroupEntry 9 }

  bwDXSCallpGroupMaximumNumberofSimVideoCallsExceeded OBJECT-TYPE
    SYNTAX      Counter32
    MAX-ACCESS  read-write
    STATUS      current
    DESCRIPTION 
        "This counter reflects the number of times that the maximum number of simultaneous video calls for a user is exceeded."
    ::= { bwDXSCallpGroupEntry 10 }

  bwDXSCallpGroupMediaTypeNotSupported OBJECT-TYPE
    SYNTAX      Counter32
    MAX-ACCESS  read-write
    STATUS      current
    DESCRIPTION 
        "This counter reflects the number of times that a call is rejected because the media type was not valid for a user."
    ::= { bwDXSCallpGroupEntry 11 }

  bwDXSCallpGroupGETSOrigSessionCount OBJECT-TYPE
    SYNTAX      Counter32
    MAX-ACCESS  read-write
    STATUS      current
    DESCRIPTION 
        "The number of GETS originating sessions for a group."
-- @feature:191436
    ::= { bwDXSCallpGroupEntry 12 }

  bwDXSCallpGroupGETSTermSessionCount OBJECT-TYPE
    SYNTAX      Counter32
    MAX-ACCESS  read-write
    STATUS      current
    DESCRIPTION 
        "The number of GETS terminating sessions for a group."
-- @feature:191436
    ::= { bwDXSCallpGroupEntry 13 }

  bwDXSCallpGroupE911PSAPCallBackAttempts OBJECT-TYPE
    SYNTAX      Counter32
    MAX-ACCESS  read-write
    STATUS      current
    DESCRIPTION 
        "This group counter tracks the number of times an E911 Public Safety Answering Point (PSAP) attempts to call back users that previously made emergency calls."
-- @feature:BW-2320
    ::= { bwDXSCallpGroupEntry 14 }

  bwDXSCallpCallsPerSecond OBJECT-TYPE
    SYNTAX      Gauge32
    MAX-ACCESS  read-only
    STATUS      current
    DESCRIPTION 
        "This gauge measures the rate at which network origination attempts and user origination attempts occur.  It uses the timestamps of up to the last 100 network origination attempts and user origination attempts in calculating the rate.  The criteria for capturing such attempts is the same as that for pegging the bwDXSCallPNetworkOriginationAttempts and bwCallPUserOriginationAttempts PM's."
    ::= { callpStats 12 }

  bwDXSCallpMaximumNumberofSimCallsExceeded OBJECT-TYPE
    SYNTAX      Counter32
    MAX-ACCESS  read-write
    STATUS      current
    DESCRIPTION 
        "This counter reflects the number of times that the maximum number of simultaneous calls for a user is exceeded."
    ::= { callpStats 13 }

  bwDXSCallpMaximumCallTimeforAnsweredCallsExceeded OBJECT-TYPE
    SYNTAX      Counter32
    MAX-ACCESS  read-write
    STATUS      current
    DESCRIPTION 
        "This counter reflects the number of times that the maximum call time for answered calls is exceeded."
    ::= { callpStats 14 }

  bwDXSCallpMaximumCallTimeforUnansweredCallsExceeded OBJECT-TYPE
    SYNTAX      Counter32
    MAX-ACCESS  read-write
    STATUS      current
    DESCRIPTION 
        "This counter reflects the number of times that the maximum call time for unanswered calls is exceeded."
    ::= { callpStats 15 }

  bwDXSCallpActiveCallsAsPercentOfLicense OBJECT-TYPE
    SYNTAX      Gauge32
    MAX-ACCESS  read-only
    STATUS      current
    DESCRIPTION 
        "This gauge reports the number of active calls as a percentage of the maximum concurrent calls licensed value. If the concurrent calls licensed value is unlimited, the gauge is zero."
    ::= { callpStats 16 }

  bwDXSCallpMaximumNumberofSimVideoCallsExceeded OBJECT-TYPE
    SYNTAX      Counter32
    MAX-ACCESS  read-write
    STATUS      current
    DESCRIPTION 
        "This counter reflects the number of times that the maximum number of simultaneous video calls for a user is exceeded."
    ::= { callpStats 17 }

  bwDXSCallpMediaTypeNotSupported OBJECT-TYPE
    SYNTAX      Counter32
    MAX-ACCESS  read-write
    STATUS      current
    DESCRIPTION 
        "This counter reflects the number of times that the media type (codec) has not been supported for a user."
    ::= { callpStats 18 }

  bwDXSCallpRemoteOfficeEmergencyCallsBlocked OBJECT-TYPE
    SYNTAX      Counter32
    MAX-ACCESS  read-write
    STATUS      current
    DESCRIPTION 
        "This is the number of times an emergency call origination attempt from a network location (i.e. remote office or BroadWorks anywhere) has been blocked."
    ::= { callpStats 19 }

  bwDXSStateReplicationMessageSent OBJECT-TYPE
    SYNTAX      Counter32
    MAX-ACCESS  read-write
    STATUS      current
    DESCRIPTION 
        "This is the number of state replication messages sent to the peer server."
    ::= { callpStats 20 }

  bwDXSStateReplicationMessageReceived OBJECT-TYPE
    SYNTAX      Counter32
    MAX-ACCESS  read-write
    STATUS      current
    DESCRIPTION 
        "This is the number of state replication messages received from the peer server."
    ::= { callpStats 21 }

  bwDXSStateReplicationOwnershipTaken OBJECT-TYPE
    SYNTAX      Counter32
    MAX-ACCESS  read-write
    STATUS      current
    DESCRIPTION 
        "This is the number of call processing migration units that this server has taken over ownership."
    ::= { callpStats 22 }

  bwDXSStateReplicationOwnershipGranted OBJECT-TYPE
    SYNTAX      Counter32
    MAX-ACCESS  read-write
    STATUS      current
    DESCRIPTION 
        "This is the number of call processing migration units that this server has relinquished ownership."
    ::= { callpStats 23 }

  bwDXSStateReplicationRemoteLockTaken OBJECT-TYPE
    SYNTAX      Counter32
    MAX-ACCESS  read-write
    STATUS      current
    DESCRIPTION 
        "This is the number of shared data locks that this server has taken over ownership."
    ::= { callpStats 24 }

  bwDXSStateReplicationRemoteLockGranted OBJECT-TYPE
    SYNTAX      Counter32
    MAX-ACCESS  read-write
    STATUS      current
    DESCRIPTION 
        "This is the number of shared data locks that this server relinquished ownership."
    ::= { callpStats 25 }

  bwDXSCallpGETSOrigSessionCount OBJECT-TYPE
    SYNTAX      Counter32
    MAX-ACCESS  read-write
    STATUS      current
    DESCRIPTION 
        "The number of GETS originating sessions."
-- @feature:191436
    ::= { callpStats 26 }

  bwDXSCallpGETSTermSessionCount OBJECT-TYPE
    SYNTAX      Counter32
    MAX-ACCESS  read-write
    STATUS      current
    DESCRIPTION 
        "The number of GETS terminating sessions."
-- @feature:191436
    ::= { callpStats 27 }

  bwDXSCallpInvalidGETSCount OBJECT-TYPE
    SYNTAX      Counter32
    MAX-ACCESS  read-write
    STATUS      current
    DESCRIPTION 
        "The number of SIP INVITE messages received with an invalid Resource-Priority header."
-- @feature:191436
    ::= { callpStats 28 }

  bwDXSCallpE911PSAPCallBackAttempts OBJECT-TYPE
    SYNTAX      Counter32
    MAX-ACCESS  read-write
    STATUS      current
    DESCRIPTION 
        "This counter tracks the number of times an E911 PSAP Center attempts to call back users that previously made emergency calls."
-- @feature:BW-2320
    ::= { callpStats 29 }

-- CallPStats :: profileLoading ...........................................

  bwDXSProfileLoadingCallNumRequests OBJECT-TYPE
    SYNTAX      Counter32
    MAX-ACCESS  read-write
    STATUS      current
    DESCRIPTION 
        "This is the total number of requests for profile loading during call setup."
    ::= { profileLoading 1 }

  bwDXSProfileLoadingCallMinDelay OBJECT-TYPE
    SYNTAX      Gauge32
    MAX-ACCESS  read-write
    STATUS      current
    DESCRIPTION 
        "This represents the lowest waiting time for loading a profile during call setup."
    ::= { profileLoading 2 }

  bwDXSProfileLoadingCallMaxDelay OBJECT-TYPE
    SYNTAX      Gauge32
    MAX-ACCESS  read-write
    STATUS      current
    DESCRIPTION 
        "This represents the highest waiting time for loading a profile during call setup."
    ::= { profileLoading 3 }

  bwDXSProfileLoadingCallAvgDelay OBJECT-TYPE
    SYNTAX      Gauge32
    MAX-ACCESS  read-write
    STATUS      current
    DESCRIPTION 
        "This represents the average waiting time for loading a profile during call setup."
    ::= { profileLoading 4 }

  bwDXSProfileLoadingNonCallNumRequests OBJECT-TYPE
    SYNTAX      Counter32
    MAX-ACCESS  read-write
    STATUS      current
    DESCRIPTION 
        "This is the total number of requests for profile loading when processing a non-call request."
    ::= { profileLoading 5 }

  bwDXSProfileLoadingNonCallMinDelay OBJECT-TYPE
    SYNTAX      Gauge32
    MAX-ACCESS  read-write
    STATUS      current
    DESCRIPTION 
        "This represents the lowest waiting time for loading a profile during processing of a non-call request."
    ::= { profileLoading 6 }

  bwDXSProfileLoadingNonCallMaxDelay OBJECT-TYPE
    SYNTAX      Gauge32
    MAX-ACCESS  read-write
    STATUS      current
    DESCRIPTION 
        "This represents the highest waiting time for loading a profile during processing of a non-call request."
    ::= { profileLoading 7 }

  bwDXSProfileLoadingNonCallAvgDelay OBJECT-TYPE
    SYNTAX      Gauge32
    MAX-ACCESS  read-write
    STATUS      current
    DESCRIPTION 
        "This represents the average waiting time for loading a profile during processing of a non-call request."
    ::= { profileLoading 8 }

  bwDXSProfileLoadingMidCallNumRequests OBJECT-TYPE
    SYNTAX      Counter32
    MAX-ACCESS  read-write
    STATUS      current
    DESCRIPTION 
        "This is the total number of requests for profile loading that occurred during processing of a call."
    ::= { profileLoading 9 }

  bwDXSProfileLoadingMidCallMinDelay OBJECT-TYPE
    SYNTAX      Gauge32
    MAX-ACCESS  read-write
    STATUS      current
    DESCRIPTION 
        "This represents the lowest waiting time for loading a profile in the middle of call processing."
    ::= { profileLoading 10 }

  bwDXSProfileLoadingMidCallMaxDelay OBJECT-TYPE
    SYNTAX      Gauge32
    MAX-ACCESS  read-write
    STATUS      current
    DESCRIPTION 
        "This represents the highest waiting time for loading a profile in the middle of call processing."
    ::= { profileLoading 11 }

  bwDXSProfileLoadingMidCallAvgDelay OBJECT-TYPE
    SYNTAX      Gauge32
    MAX-ACCESS  read-write
    STATUS      current
    DESCRIPTION 
        "This represents the average waiting time for loading a profile in the middle of call processing."
    ::= { profileLoading 12 }

  bwDXSProfileLoadingCallPoolMaxThreads OBJECT-TYPE
    SYNTAX      Gauge32
    MAX-ACCESS  read-write
    STATUS      current
    DESCRIPTION 
        "This is the maximum number of threads that were used for profile loading for call requests."
    ::= { profileLoading 13 }

  bwDXSProfileLoadingCallPoolAvgThreads OBJECT-TYPE
    SYNTAX      Gauge32
    MAX-ACCESS  read-write
    STATUS      current
    DESCRIPTION 
        "This is the average number of threads that were used for profile loading for call requests."
    ::= { profileLoading 14 }

  bwDXSProfileLoadingNonCallPoolMaxThreads OBJECT-TYPE
    SYNTAX      Gauge32
    MAX-ACCESS  read-write
    STATUS      current
    DESCRIPTION 
        "This is the maximum number of threads that were used for profile loading for non-call requests."
    ::= { profileLoading 15 }

  bwDXSProfileLoadingNonCallPoolAvgThreads OBJECT-TYPE
    SYNTAX      Gauge32
    MAX-ACCESS  read-write
    STATUS      current
    DESCRIPTION 
        "This is the average number of threads that were used for profile loading for non-call requests."
    ::= { profileLoading 16 }

  bwDXSUserProfilesRegisteredInCache OBJECT-TYPE
    SYNTAX      Gauge32
    MAX-ACCESS  read-write
    STATUS      current
    DESCRIPTION 
        "This is the current number of user profiles for which the Execution Server process is registered, so that they are kept in cache."
    ::= { profileLoading 17 }

  bwDXSGroupProfilesRegisteredInCache OBJECT-TYPE
    SYNTAX      Gauge32
    MAX-ACCESS  read-write
    STATUS      current
    DESCRIPTION 
        "This is the current number of group profiles for which the Execution Server process is registered, so that they are kept in cache."
    ::= { profileLoading 18 }

  bwDXSServiceProviderProfilesRegisteredInCache OBJECT-TYPE
    SYNTAX      Gauge32
    MAX-ACCESS  read-write
    STATUS      current
    DESCRIPTION 
        "This is the current number of service provider profiles for which the Execution Server process is registered, so that they are kept in cache."
    ::= { profileLoading 19 }

-- Protocol :: SMTP ...........................................

  bwDXSSMTPTotalPrimaryEmailSendAttempts OBJECT-TYPE
    SYNTAX      Counter32
    MAX-ACCESS  read-write
    STATUS      current
    DESCRIPTION 
        "This counter reflects the total number of message send attempted on the primary SMTP server."
    ::= { smtpStats 1 }

  bwDXSSMTPTotalSecondaryEmailSendAttempts OBJECT-TYPE
    SYNTAX      Counter32
    MAX-ACCESS  read-write
    STATUS      current
    DESCRIPTION 
        "This counter reflects the total number of message send attempted on the secondary SMTP server."
    ::= { smtpStats 2 }

  bwDXSSMTPPrimaryUnSuccessfulEmailSendAttempts OBJECT-TYPE
    SYNTAX      Counter32
    MAX-ACCESS  read-write
    STATUS      current
    DESCRIPTION 
        "This counter reflects the total number of message deliveries that failed on the primary SMTP server."
    ::= { smtpStats 3 }

  bwDXSSMTPSecondaryUnSuccessfulEmailSendAttempts OBJECT-TYPE
    SYNTAX      Counter32
    MAX-ACCESS  read-write
    STATUS      current
    DESCRIPTION 
        "This counter reflects the total number of message deliveries that failed on the secondary SMTP server."
    ::= { smtpStats 4 }

-- Protocol :: SIP ...........................................

  bwDXSSipSummaryTotalTransactions OBJECT-TYPE
    SYNTAX      Counter32
    MAX-ACCESS  read-write
    STATUS      current
    DESCRIPTION 
        "This counter contains a count of the number of transactions completed or in progress."
    ::= { sipStats 1 }

  bwDXSSipStatsInviteIns OBJECT-TYPE
    SYNTAX      Counter32
    MAX-ACCESS  read-write
    STATUS      current
    DESCRIPTION 
        "This counter reflects the total number of INVITE requests received by BroadWorks."
    ::= { sipStats 2 }

  bwDXSSipStatsInviteOuts OBJECT-TYPE
    SYNTAX      Counter32
    MAX-ACCESS  read-write
    STATUS      current
    DESCRIPTION 
        "This counter reflects the total number of INVITE requests sent by BroadWorks."
    ::= { sipStats 3 }

  bwDXSSipStatsAckIns OBJECT-TYPE
    SYNTAX      Counter32
    MAX-ACCESS  read-write
    STATUS      current
    DESCRIPTION 
        "This counter reflects the total number of ACK requests received by BroadWorks."
    ::= { sipStats 4 }

  bwDXSSipStatsAckOuts OBJECT-TYPE
    SYNTAX      Counter32
    MAX-ACCESS  read-write
    STATUS      current
    DESCRIPTION 
        "This counter reflects the total number of ACK requests sent by BroadWorks."
    ::= { sipStats 5 }

  bwDXSSipStatsByeIns OBJECT-TYPE
    SYNTAX      Counter32
    MAX-ACCESS  read-write
    STATUS      current
    DESCRIPTION 
        "This counter reflects the total number of BYE requests received by BroadWorks."
    ::= { sipStats 6 }

  bwDXSSipStatsByeOuts OBJECT-TYPE
    SYNTAX      Counter32
    MAX-ACCESS  read-write
    STATUS      current
    DESCRIPTION 
        "This counter reflects the total number of BYE requests sent by BroadWorks."
    ::= { sipStats 7 }

  bwDXSSipStatsCancelIns OBJECT-TYPE
    SYNTAX      Counter32
    MAX-ACCESS  read-write
    STATUS      current
    DESCRIPTION 
        "This counter reflects the total number of CANCEL requests received by BroadWorks."
    ::= { sipStats 8 }

  bwDXSSipStatsCancelOuts OBJECT-TYPE
    SYNTAX      Counter32
    MAX-ACCESS  read-write
    STATUS      current
    DESCRIPTION 
        "This counter reflects the total number of CANCEL requests sent by BroadWorks."
    ::= { sipStats 9 }

  bwDXSSipStatsOptionsIns OBJECT-TYPE
    SYNTAX      Counter32
    MAX-ACCESS  read-write
    STATUS      current
    DESCRIPTION 
        "This counter reflects the total number of OPTIONS requests received by BroadWorks."
    ::= { sipStats 10 }

  bwDXSSipStatsOptionsOuts OBJECT-TYPE
    SYNTAX      Counter32
    MAX-ACCESS  read-write
    STATUS      current
    DESCRIPTION 
        "This counter reflects the total number of OPTIONS requests sent by BroadWorks."
    ::= { sipStats 11 }

  bwDXSSipStatsRegisterIns OBJECT-TYPE
    SYNTAX      Counter32
    MAX-ACCESS  read-write
    STATUS      current
    DESCRIPTION 
        "This counter reflects the total number of REGISTER requests received by BroadWorks."
    ::= { sipStats 12 }

  bwDXSSipStatsRegisterOuts OBJECT-TYPE
    SYNTAX      Counter32
    MAX-ACCESS  read-write
    STATUS      current
    DESCRIPTION 
        "This counter reflects the total number of REGISTER requests sent by BroadWorks."
    ::= { sipStats 13 }

  bwDXSSipStatsInfoIns OBJECT-TYPE
    SYNTAX      Counter32
    MAX-ACCESS  read-write
    STATUS      current
    DESCRIPTION 
        "This counter reflects the total number of INFO requests received by BroadWorks"
    ::= { sipStats 14 }

  bwDXSSipStatsInfoOuts OBJECT-TYPE
    SYNTAX      Counter32
    MAX-ACCESS  read-write
    STATUS      current
    DESCRIPTION 
        "This counter reflects the total number of INFO requests sent by BroadWorks"
    ::= { sipStats 15 }

  bwDXSSipStatsNotifyIns OBJECT-TYPE
    SYNTAX      Counter32
    MAX-ACCESS  read-write
    STATUS      current
    DESCRIPTION 
        "This counter reflects the total number of NOTIFY requests received by BroadWorks"
    ::= { sipStats 16 }

  bwDXSSipStatsNotifyOuts OBJECT-TYPE
    SYNTAX      Counter32
    MAX-ACCESS  read-write
    STATUS      current
    DESCRIPTION 
        "This counter reflects the total number of NOTIFY requests sent by BroadWorks"
    ::= { sipStats 17 }

  bwDXSSipStatsPrackIns OBJECT-TYPE
    SYNTAX      Counter32
    MAX-ACCESS  read-write
    STATUS      current
    DESCRIPTION 
        "This counter reflects the total number of PRACK requests received by BroadWorks"
    ::= { sipStats 18 }

  bwDXSSipStatsPrackOuts OBJECT-TYPE
    SYNTAX      Counter32
    MAX-ACCESS  read-write
    STATUS      current
    DESCRIPTION 
        "This counter reflects the total number of PRACK requests sent by BroadWorks"
    ::= { sipStats 19 }

  bwDXSSipStatsOtherIns OBJECT-TYPE
    SYNTAX      Counter32
    MAX-ACCESS  read-write
    STATUS      current
    DESCRIPTION 
        "This counter reflects the total number of unsupported requests (other than INFO and NOTIFY) received by BroadWorks"
    ::= { sipStats 20 }

  bwDXSSipStatsOtherOuts OBJECT-TYPE
    SYNTAX      Counter32
    MAX-ACCESS  read-write
    STATUS      current
    DESCRIPTION 
        "This counter reflects the total number of UNKNOWN requests sent by BroadWorks"
    ::= { sipStats 21 }

  bwDXSSipStatsInviteResponsesTable OBJECT-TYPE
    SYNTAX      SEQUENCE OF BwSipStatsInviteResponsesEntry
    MAX-ACCESS  not-accessible
    STATUS      current
    DESCRIPTION 
        "This table contains the counters for all SIP responses to the Invite requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 22 }

  bwDXSSipStatsInviteResponsesEntry OBJECT-TYPE
    SYNTAX      BwSipStatsInviteResponsesEntry
    MAX-ACCESS  not-accessible
    STATUS      current
    DESCRIPTION 
        "This row contains information on a particular SIP status code received or sent in response to an Invite"
    INDEX       { bwDXSSipStatsInviteResponseCodeValue }
    ::= { bwDXSSipStatsInviteResponsesTable 1 }

  BwSipStatsInviteResponsesEntry ::= SEQUENCE {
    bwDXSSipStatsInviteResponseCodeValue   Integer32,
    bwDXSSipStatsInviteResponseIns         Counter32,
    bwDXSSipStatsInviteResponseOuts        Counter32
  }

  bwDXSSipStatsInviteResponseCodeValue OBJECT-TYPE
    SYNTAX      Integer32 (100..999)
    MAX-ACCESS  not-accessible
    STATUS      current
    DESCRIPTION 
        "This integer represents a SIP status code.  The rest of the information in this row is related to this value."
    ::= { bwDXSSipStatsInviteResponsesEntry 1 }

  bwDXSSipStatsInviteResponseIns OBJECT-TYPE
    SYNTAX      Counter32
    MAX-ACCESS  read-write
    STATUS      current
    DESCRIPTION 
        "This counter represents the number of SIP responses received in response to an Invite"
    ::= { bwDXSSipStatsInviteResponsesEntry 2 }

  bwDXSSipStatsInviteResponseOuts OBJECT-TYPE
    SYNTAX      Counter32
    MAX-ACCESS  read-write
    STATUS      current
    DESCRIPTION 
        "This counter represents the number of SIP responses sent in response to an Invite"
    ::= { bwDXSSipStatsInviteResponsesEntry 3 }

  bwDXSSipStatsByeResponsesTable OBJECT-TYPE
    SYNTAX      SEQUENCE OF BwSipStatsByeResponsesEntry
    MAX-ACCESS  not-accessible
    STATUS      current
    DESCRIPTION 
        "This table contains the counters for all SIP responses to the BYE requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 23 }

  bwDXSSipStatsByeResponsesEntry OBJECT-TYPE
    SYNTAX      BwSipStatsByeResponsesEntry
    MAX-ACCESS  not-accessible
    STATUS      current
    DESCRIPTION 
        "This row contains information on a particular SIP status code received or sent in response to a Bye"
    INDEX       { bwDXSSipStatsByeResponseCodeValue }
    ::= { bwDXSSipStatsByeResponsesTable 1 }

  BwSipStatsByeResponsesEntry ::= SEQUENCE {
    bwDXSSipStatsByeResponseCodeValue  Integer32,
    bwDXSSipStatsByeResponseIns        Counter32,
    bwDXSSipStatsByeResponseOuts       Counter32
  }

  bwDXSSipStatsByeResponseCodeValue OBJECT-TYPE
    SYNTAX      Integer32 (100..999)
    MAX-ACCESS  not-accessible
    STATUS      current
    DESCRIPTION 
        "This integer represents a SIP status code.  The rest of the information in this row is related to this value."
    ::= { bwDXSSipStatsByeResponsesEntry 1 }

  bwDXSSipStatsByeResponseIns OBJECT-TYPE
    SYNTAX      Counter32
    MAX-ACCESS  read-write
    STATUS      current
    DESCRIPTION 
        "This counter represents the number of SIP responses received in response to a Bye"
    ::= { bwDXSSipStatsByeResponsesEntry 2 }

  bwDXSSipStatsByeResponseOuts OBJECT-TYPE
    SYNTAX      Counter32
    MAX-ACCESS  read-write
    STATUS      current
    DESCRIPTION 
        "This counter represents the number of SIP responses sent in response to a Bye"
    ::= { bwDXSSipStatsByeResponsesEntry 3 }

  bwDXSSipStatsCancelResponsesTable OBJECT-TYPE
    SYNTAX      SEQUENCE OF BwSipStatsCancelResponsesEntry
    MAX-ACCESS  not-accessible
    STATUS      current
    DESCRIPTION 
        "This table contains the counters for all SIP responses to the Cancel requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 24 }

  bwDXSSipStatsCancelResponsesEntry OBJECT-TYPE
    SYNTAX      BwSipStatsCancelResponsesEntry
    MAX-ACCESS  not-accessible
    STATUS      current
    DESCRIPTION 
        "This row contains information on a particular SIP status code received or sent in response to a Cancel"
    INDEX       { bwDXSSipStatsCancelResponseCodeValue }
    ::= { bwDXSSipStatsCancelResponsesTable 1 }

  BwSipStatsCancelResponsesEntry ::= SEQUENCE {
    bwDXSSipStatsCancelResponseCodeValue   Integer32,
    bwDXSSipStatsCancelResponseIns         Counter32,
    bwDXSSipStatsCancelResponseOuts        Counter32
  }

  bwDXSSipStatsCancelResponseCodeValue OBJECT-TYPE
    SYNTAX      Integer32 (100..999)
    MAX-ACCESS  not-accessible
    STATUS      current
    DESCRIPTION 
        "This integer represents a SIP status code.  The rest of the information in this row is related to this value."
    ::= { bwDXSSipStatsCancelResponsesEntry 1 }

  bwDXSSipStatsCancelResponseIns OBJECT-TYPE
    SYNTAX      Counter32
    MAX-ACCESS  read-write
    STATUS      current
    DESCRIPTION 
        "This counter represents the number of SIP responses received in response to a Cancel"
    ::= { bwDXSSipStatsCancelResponsesEntry 2 }

  bwDXSSipStatsCancelResponseOuts OBJECT-TYPE
    SYNTAX      Counter32
    MAX-ACCESS  read-write
    STATUS      current
    DESCRIPTION 
        "This counter represents the number of SIP responses sent in response to a Cancel"
    ::= { bwDXSSipStatsCancelResponsesEntry 3 }

  bwDXSSipStatsOptionsResponsesTable OBJECT-TYPE
    SYNTAX      SEQUENCE OF BwSipStatsOptionsResponsesEntry
    MAX-ACCESS  not-accessible
    STATUS      current
    DESCRIPTION 
        "This table contains the counters for all SIP responses to the Options requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 25 }

  bwDXSSipStatsOptionsResponsesEntry OBJECT-TYPE
    SYNTAX      BwSipStatsOptionsResponsesEntry
    MAX-ACCESS  not-accessible
    STATUS      current
    DESCRIPTION 
        "This row contains information on a particular SIP status code received or sent in response to a Options"
    INDEX       { bwDXSSipStatsOptionsResponseCodeValue }
    ::= { bwDXSSipStatsOptionsResponsesTable 1 }

  BwSipStatsOptionsResponsesEntry ::= SEQUENCE {
    bwDXSSipStatsOptionsResponseCodeValue  Integer32,
    bwDXSSipStatsOptionsResponseIns        Counter32,
    bwDXSSipStatsOptionsResponseOuts       Counter32
  }

  bwDXSSipStatsOptionsResponseCodeValue OBJECT-TYPE
    SYNTAX      Integer32 (100..999)
    MAX-ACCESS  not-accessible
    STATUS      current
    DESCRIPTION 
        "This integer represents a SIP status code.  The rest of the information in this row is related to this value."
    ::= { bwDXSSipStatsOptionsResponsesEntry 1 }

  bwDXSSipStatsOptionsResponseIns OBJECT-TYPE
    SYNTAX      Counter32
    MAX-ACCESS  read-write
    STATUS      current
    DESCRIPTION 
        "This counter represents the number of SIP responses received in response to an Options"
    ::= { bwDXSSipStatsOptionsResponsesEntry 2 }

  bwDXSSipStatsOptionsResponseOuts OBJECT-TYPE
    SYNTAX      Counter32
    MAX-ACCESS  read-write
    STATUS      current
    DESCRIPTION 
        "This counter represents the number of SIP responses sent in response to an Options"
    ::= { bwDXSSipStatsOptionsResponsesEntry 3 }

  bwDXSSipStatsRegisterResponsesTable OBJECT-TYPE
    SYNTAX      SEQUENCE OF BwSipStatsRegisterResponsesEntry
    MAX-ACCESS  not-accessible
    STATUS      current
    DESCRIPTION 
        "This table contains the counters for all SIP responses to the Register requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 26 }

  bwDXSSipStatsRegisterResponsesEntry OBJECT-TYPE
    SYNTAX      BwSipStatsRegisterResponsesEntry
    MAX-ACCESS  not-accessible
    STATUS      current
    DESCRIPTION 
        "This row contains information on a particular SIP status code received or sent in response to a Register"
    INDEX       { bwDXSSipStatsRegisterResponseCodeValue }
    ::= { bwDXSSipStatsRegisterResponsesTable 1 }

  BwSipStatsRegisterResponsesEntry ::= SEQUENCE {
    bwDXSSipStatsRegisterResponseCodeValue     Integer32,
    bwDXSSipStatsRegisterResponseIns           Counter32,
    bwDXSSipStatsRegisterResponseOuts          Counter32
  }

  bwDXSSipStatsRegisterResponseCodeValue OBJECT-TYPE
    SYNTAX      Integer32 (100..999)
    MAX-ACCESS  not-accessible
    STATUS      current
    DESCRIPTION 
        "This integer represents a SIP status code.  The rest of the information in this row is related to this value."
    ::= { bwDXSSipStatsRegisterResponsesEntry 1 }

  bwDXSSipStatsRegisterResponseIns OBJECT-TYPE
    SYNTAX      Counter32
    MAX-ACCESS  read-write
    STATUS      current
    DESCRIPTION 
        "This counter represents the number of SIP responses received in response to a Register"
    ::= { bwDXSSipStatsRegisterResponsesEntry 2 }

  bwDXSSipStatsRegisterResponseOuts OBJECT-TYPE
    SYNTAX      Counter32
    MAX-ACCESS  read-write
    STATUS      current
    DESCRIPTION 
        "This counter represents the number of SIP responses sent in response to a Register"
    ::= { bwDXSSipStatsRegisterResponsesEntry 3 }

  bwDXSSipStatsPrackResponsesTable OBJECT-TYPE
    SYNTAX      SEQUENCE OF BwSipStatsPrackResponsesEntry
    MAX-ACCESS  not-accessible
    STATUS      current
    DESCRIPTION 
        "This table contains the counters for all SIP responses to the Prack requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 27 }

  bwDXSSipStatsPrackResponsesEntry OBJECT-TYPE
    SYNTAX      BwSipStatsPrackResponsesEntry
    MAX-ACCESS  not-accessible
    STATUS      current
    DESCRIPTION 
        "This row contains information on a particular SIP status code received or sent in response to a Prack"
    INDEX       { bwDXSSipStatsPrackResponseCodeValue }
    ::= { bwDXSSipStatsPrackResponsesTable 1 }

  BwSipStatsPrackResponsesEntry ::= SEQUENCE {
    bwDXSSipStatsPrackResponseCodeValue    Integer32,
    bwDXSSipStatsPrackResponseIns          Counter32,
    bwDXSSipStatsPrackResponseOuts         Counter32
  }

  bwDXSSipStatsPrackResponseCodeValue OBJECT-TYPE
    SYNTAX      Integer32 (100..999)
    MAX-ACCESS  not-accessible
    STATUS      current
    DESCRIPTION 
        "This integer represents a SIP status code.  The rest of the information in this row is related to this value."
    ::= { bwDXSSipStatsPrackResponsesEntry 1 }

  bwDXSSipStatsPrackResponseIns OBJECT-TYPE
    SYNTAX      Counter32
    MAX-ACCESS  read-write
    STATUS      current
    DESCRIPTION 
        "This counter represents the number of SIP responses received in response to a Prack"
    ::= { bwDXSSipStatsPrackResponsesEntry 2 }

  bwDXSSipStatsPrackResponseOuts OBJECT-TYPE
    SYNTAX      Counter32
    MAX-ACCESS  read-write
    STATUS      current
    DESCRIPTION 
        "This counter represents the number of SIP responses sent in response to a Prack"
    ::= { bwDXSSipStatsPrackResponsesEntry 3 }

  bwDXSSipStatsInfoResponsesTable OBJECT-TYPE
    SYNTAX      SEQUENCE OF BwSipStatsInfoResponsesEntry
    MAX-ACCESS  not-accessible
    STATUS      current
    DESCRIPTION 
        "This table contains the counters for all SIP responses to the Info requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 28 }

  bwDXSSipStatsInfoResponsesEntry OBJECT-TYPE
    SYNTAX      BwSipStatsInfoResponsesEntry
    MAX-ACCESS  not-accessible
    STATUS      current
    DESCRIPTION 
        "This row contains information on a particular SIP status code received or sent in response to an Info"
    INDEX       { bwDXSSipStatsInfoResponseCodeValue }
    ::= { bwDXSSipStatsInfoResponsesTable 1 }

  BwSipStatsInfoResponsesEntry ::= SEQUENCE {
    bwDXSSipStatsInfoResponseCodeValue     Integer32,
    bwDXSSipStatsInfoResponseIns           Counter32,
    bwDXSSipStatsInfoResponseOuts          Counter32
  }

  bwDXSSipStatsInfoResponseCodeValue OBJECT-TYPE
    SYNTAX      Integer32 (100..999)
    MAX-ACCESS  not-accessible
    STATUS      current
    DESCRIPTION 
        "This integer represents a SIP status code.  The rest of the information in this row is related to this value."
    ::= { bwDXSSipStatsInfoResponsesEntry 1 }

  bwDXSSipStatsInfoResponseIns OBJECT-TYPE
    SYNTAX      Counter32
    MAX-ACCESS  read-write
    STATUS      current
    DESCRIPTION 
        "This counter represents the number of SIP responses received in response to an Info"
    ::= { bwDXSSipStatsInfoResponsesEntry 2 }

  bwDXSSipStatsInfoResponseOuts OBJECT-TYPE
    SYNTAX      Counter32
    MAX-ACCESS  read-write
    STATUS      current
    DESCRIPTION 
        "This counter represents the number of SIP responses sent in response to an Info"
    ::= { bwDXSSipStatsInfoResponsesEntry 3 }

  bwDXSSipStatsNotifyResponsesTable OBJECT-TYPE
    SYNTAX      SEQUENCE OF BwSipStatsNotifyResponsesEntry
    MAX-ACCESS  not-accessible
    STATUS      current
    DESCRIPTION 
        "This table contains the counters for all SIP responses to the Notify requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 29 }

  bwDXSSipStatsNotifyResponsesEntry OBJECT-TYPE
    SYNTAX      BwSipStatsNotifyResponsesEntry
    MAX-ACCESS  not-accessible
    STATUS      current
    DESCRIPTION 
        "This row contains information on a particular SIP status code received or sent in response to an Notify"
    INDEX       { bwDXSSipStatsNotifyResponseCodeValue }
    ::= { bwDXSSipStatsNotifyResponsesTable 1 }

  BwSipStatsNotifyResponsesEntry ::= SEQUENCE {
    bwDXSSipStatsNotifyResponseCodeValue   Integer32,
    bwDXSSipStatsNotifyResponseIns         Counter32,
    bwDXSSipStatsNotifyResponseOuts        Counter32
  }

  bwDXSSipStatsNotifyResponseCodeValue OBJECT-TYPE
    SYNTAX      Integer32 (100..999)
    MAX-ACCESS  not-accessible
    STATUS      current
    DESCRIPTION 
        "This integer represents a SIP status code.  The rest of the information in this row is related to this value."
    ::= { bwDXSSipStatsNotifyResponsesEntry 1 }

  bwDXSSipStatsNotifyResponseIns OBJECT-TYPE
    SYNTAX      Counter32
    MAX-ACCESS  read-write
    STATUS      current
    DESCRIPTION 
        "This counter represents the number of SIP responses received in response to a Notify"
    ::= { bwDXSSipStatsNotifyResponsesEntry 2 }

  bwDXSSipStatsNotifyResponseOuts OBJECT-TYPE
    SYNTAX      Counter32
    MAX-ACCESS  read-write
    STATUS      current
    DESCRIPTION 
        "This counter represents the number of SIP responses sent in response to a Notify"
    ::= { bwDXSSipStatsNotifyResponsesEntry 3 }

  bwDXSSipStatsOtherResponsesTable OBJECT-TYPE
    SYNTAX      SEQUENCE OF BwSipStatsOtherResponsesEntry
    MAX-ACCESS  not-accessible
    STATUS      current
    DESCRIPTION 
        "This table contains the counters for all SIP responses to the Other requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 30 }

  bwDXSSipStatsOtherResponsesEntry OBJECT-TYPE
    SYNTAX      BwSipStatsOtherResponsesEntry
    MAX-ACCESS  not-accessible
    STATUS      current
    DESCRIPTION 
        "This row contains information on a particular SIP status code received or sent in response to an Other"
    INDEX       { bwDXSSipStatsOtherResponseCodeValue }
    ::= { bwDXSSipStatsOtherResponsesTable 1 }

  BwSipStatsOtherResponsesEntry ::= SEQUENCE {
    bwDXSSipStatsOtherResponseCodeValue    Integer32,
    bwDXSSipStatsOtherResponseIns          Counter32,
    bwDXSSipStatsOtherResponseOuts         Counter32
  }

  bwDXSSipStatsOtherResponseCodeValue OBJECT-TYPE
    SYNTAX      Integer32 (100..999)
    MAX-ACCESS  not-accessible
    STATUS      current
    DESCRIPTION 
        "This integer represents a SIP status code.  The rest of the information in this row is related to this value."
    ::= { bwDXSSipStatsOtherResponsesEntry 1 }

  bwDXSSipStatsOtherResponseIns OBJECT-TYPE
    SYNTAX      Counter32
    MAX-ACCESS  read-write
    STATUS      current
    DESCRIPTION 
        "This counter represents the number of SIP responses received in response to an Other"
    ::= { bwDXSSipStatsOtherResponsesEntry 2 }

  bwDXSSipStatsOtherResponseOuts OBJECT-TYPE
    SYNTAX      Counter32
    MAX-ACCESS  read-write
    STATUS      current
    DESCRIPTION 
        "This counter represents the number of SIP responses sent in response to an Other"
    ::= { bwDXSSipStatsOtherResponsesEntry 3 }

  bwDXSSipStatsRetryInvites OBJECT-TYPE
    SYNTAX      Counter32
    MAX-ACCESS  read-write
    STATUS      current
    DESCRIPTION 
        "This counter reflects the total number of INVITE retries that have been sent by the user agent."
    ::= { sipStats 31 }

  bwDXSSipStatsRetryByes OBJECT-TYPE
    SYNTAX      Counter32
    MAX-ACCESS  read-write
    STATUS      current
    DESCRIPTION 
        "This counter reflects the total number of BYE retries that have been sent by the user agent."
    ::= { sipStats 32 }

  bwDXSSipStatsRetryCancels OBJECT-TYPE
    SYNTAX      Counter32
    MAX-ACCESS  read-write
    STATUS      current
    DESCRIPTION 
        "This counter reflects the total number of CANCEL retries that have been sent by the user agent."
    ::= { sipStats 33 }

  bwDXSSipStatsRetryResponses OBJECT-TYPE
    SYNTAX      Counter32
    MAX-ACCESS  read-write
    STATUS      current
    DESCRIPTION 
        "This counter reflects the total number of RESPONSES retries that have been sent by the user agent."
    ::= { sipStats 34 }

  bwDXSSipStatsSubscribeIns OBJECT-TYPE
    SYNTAX      Counter32
    MAX-ACCESS  read-write
    STATUS      current
    DESCRIPTION 
        "This counter reflects the total number of SUBSCRIBE message that have been received at the AS."
    ::= { sipStats 35 }

  bwDXSSipStatsSubscribeOuts OBJECT-TYPE
    SYNTAX      Counter32
    MAX-ACCESS  read-write
    STATUS      current
    DESCRIPTION 
        "This counter reflects the total number of SUBSCRIBE message that have been sent by the AS."
    ::= { sipStats 36 }

  bwDXSSipStatsMessageIns OBJECT-TYPE
    SYNTAX      Counter32
    MAX-ACCESS  read-write
    STATUS      current
    DESCRIPTION 
        "This counter reflects the total number of MESSAGE message that have been received at the AS."
    ::= { sipStats 37 }

  bwDXSSipStatsMessageOuts OBJECT-TYPE
    SYNTAX      Counter32
    MAX-ACCESS  read-write
    STATUS      current
    DESCRIPTION 
        "This counter reflects the total number of MESSAGE message that have been sent by the AS."
    ::= { sipStats 38 }

  bwDXSSipStatsSubscribeResponsesTable OBJECT-TYPE
    SYNTAX      SEQUENCE OF BwSipStatsSubscribeResponsesEntry
    MAX-ACCESS  not-accessible
    STATUS      current
    DESCRIPTION 
        "This table contains the counters for all SIP responses to the Subscribe requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 39 }

  bwDXSSipStatsSubscribeResponsesEntry OBJECT-TYPE
    SYNTAX      BwSipStatsSubscribeResponsesEntry
    MAX-ACCESS  not-accessible
    STATUS      current
    DESCRIPTION 
        "This row contains information on a particular SIP status code received or sent in response to a Subscribe"
    INDEX       { bwDXSSipStatsSubscribeResponseCodeValue }
    ::= { bwDXSSipStatsSubscribeResponsesTable 1 }

  BwSipStatsSubscribeResponsesEntry ::= SEQUENCE {
    bwDXSSipStatsSubscribeResponseCodeValue    Integer32,
    bwDXSSipStatsSubscribeResponseIns          Counter32,
    bwDXSSipStatsSubscribeResponseOuts         Counter32
  }

  bwDXSSipStatsSubscribeResponseCodeValue OBJECT-TYPE
    SYNTAX      Integer32 (100..999)
    MAX-ACCESS  not-accessible
    STATUS      current
    DESCRIPTION 
        "This integer represents a SIP status code.  The rest of the information in this row is related to this value."
    ::= { bwDXSSipStatsSubscribeResponsesEntry 1 }

  bwDXSSipStatsSubscribeResponseIns OBJECT-TYPE
    SYNTAX      Counter32
    MAX-ACCESS  read-write
    STATUS      current
    DESCRIPTION 
        "This counter represents the number of SIP responses received in response to a Subscribe"
    ::= { bwDXSSipStatsSubscribeResponsesEntry 2 }

  bwDXSSipStatsSubscribeResponseOuts OBJECT-TYPE
    SYNTAX      Counter32
    MAX-ACCESS  read-write
    STATUS      current
    DESCRIPTION 
        "This counter represents the number of SIP responses sent in response to a Subscribe"
    ::= { bwDXSSipStatsSubscribeResponsesEntry 3 }

  bwDXSSipStatsMessageResponsesTable OBJECT-TYPE
    SYNTAX      SEQUENCE OF BwSipStatsMessageResponsesEntry
    MAX-ACCESS  not-accessible
    STATUS      current
    DESCRIPTION 
        "This table contains the counters for all SIP responses to the Message requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 40 }

  bwDXSSipStatsMessageResponsesEntry OBJECT-TYPE
    SYNTAX      BwSipStatsMessageResponsesEntry
    MAX-ACCESS  not-accessible
    STATUS      current
    DESCRIPTION 
        "This row contains information on a particular SIP status code received or sent in response to a Message"
    INDEX       { bwDXSSipStatsMessageResponseCodeValue }
    ::= { bwDXSSipStatsMessageResponsesTable 1 }

  BwSipStatsMessageResponsesEntry ::= SEQUENCE {
    bwDXSSipStatsMessageResponseCodeValue  Integer32,
    bwDXSSipStatsMessageResponseIns        Counter32,
    bwDXSSipStatsMessageResponseOuts       Counter32
  }

  bwDXSSipStatsMessageResponseCodeValue OBJECT-TYPE
    SYNTAX      Integer32 (100..999)
    MAX-ACCESS  not-accessible
    STATUS      current
    DESCRIPTION 
        "This integer represents a SIP status code.  The rest of the information in this row is related to this value."
    ::= { bwDXSSipStatsMessageResponsesEntry 1 }

  bwDXSSipStatsMessageResponseIns OBJECT-TYPE
    SYNTAX      Counter32
    MAX-ACCESS  read-write
    STATUS      current
    DESCRIPTION 
        "This counter represents the number of SIP responses received in response to a Message"
    ::= { bwDXSSipStatsMessageResponsesEntry 2 }

  bwDXSSipStatsMessageResponseOuts OBJECT-TYPE
    SYNTAX      Counter32
    MAX-ACCESS  read-write
    STATUS      current
    DESCRIPTION 
        "This counter represents the number of SIP responses sent in response to a Message"
    ::= { bwDXSSipStatsMessageResponsesEntry 3 }

  bwDXSSipStatsUpdateIns OBJECT-TYPE
    SYNTAX      Counter32
    MAX-ACCESS  read-write
    STATUS      current
    DESCRIPTION 
        "This counter reflects the total number of UPDATE requests received by BroadWorks."
    ::= { sipStats 41 }

  bwDXSSipStatsUpdateOuts OBJECT-TYPE
    SYNTAX      Counter32
    MAX-ACCESS  read-write
    STATUS      current
    DESCRIPTION 
        "This counter reflects the total number of UPDATE requests sent by BroadWorks."
    ::= { sipStats 42 }

  bwDXSSipStatsUpdateResponseTable OBJECT-TYPE
    SYNTAX      SEQUENCE OF BwSipStatsUpdateResponseEntry
    MAX-ACCESS  not-accessible
    STATUS      current
    DESCRIPTION 
        "This table contains the counters for all SIP responses to the Message requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606"
    ::= { sipStats 43 }

  bwDXSSipStatsUpdateResponseEntry OBJECT-TYPE
    SYNTAX      BwSipStatsUpdateResponseEntry
    MAX-ACCESS  not-accessible
    STATUS      current
    DESCRIPTION 
        "This row contains information on a particular SIP status code received or sent in response to an Update message"
    INDEX       { bwDXSSipStatsUpdateResponseCodeValue }
    ::= { bwDXSSipStatsUpdateResponseTable 1 }

  BwSipStatsUpdateResponseEntry ::= SEQUENCE {
    bwDXSSipStatsUpdateResponseCodeValue   Integer32,
    bwDXSSipStatsUpdateResponseIns         Counter32,
    bwDXSSipStatsUpdateResponseOuts        Counter32
  }

  bwDXSSipStatsUpdateResponseCodeValue OBJECT-TYPE
    SYNTAX      Integer32 (100..999)
    MAX-ACCESS  not-accessible
    STATUS      current
    DESCRIPTION 
        "This integer represents a SIP status code.  The rest of the information in this row is related to this value."
    ::= { bwDXSSipStatsUpdateResponseEntry 1 }

  bwDXSSipStatsUpdateResponseIns OBJECT-TYPE
    SYNTAX      Counter32
    MAX-ACCESS  read-write
    STATUS      current
    DESCRIPTION 
        "This counter represents the number of SIP responses received in response to an Update message"
    ::= { bwDXSSipStatsUpdateResponseEntry 2 }

  bwDXSSipStatsUpdateResponseOuts OBJECT-TYPE
    SYNTAX      Counter32
    MAX-ACCESS  read-write
    STATUS      current
    DESCRIPTION 
        "This counter represents the number of SIP responses sent in response to an Update message"
    ::= { bwDXSSipStatsUpdateResponseEntry 3 }

  bwDXSSipStatsSetupSignalDelay OBJECT-TYPE
    SYNTAX      Gauge32
    MAX-ACCESS  read-write
    STATUS      current
    DESCRIPTION 
        "This gauge is applicable to SIP originated calls.  It measures the average time (in milliseconds) it takes between the receipt of an INVITE message for the origination of a new call and the transmission of an INVITE (Sip terminator), RQNT (MGCP terminator with in-band ringback), or CRCX (MGCP terminator without in-band ringback) to the primary device of the original called party (in the case of intra-group call) or to the network element of the original called party (in the case of a call to the PSTN).  Delays incurred by a query to an external element (e.g. - dip to the Network Server, CNAME query, any external database interaction incurred by CPL scripting) are part of the measurement.  This measurement is intended to reflect the elapsed delay between receipt of the call setup signal from the caller and transmission of the call setup signal to the called party"
    ::= { sipStats 44 }

  bwDXSSipStatsMinSetupSignalDelay OBJECT-TYPE
    SYNTAX      Gauge32
    MAX-ACCESS  read-write
    STATUS      current
    DESCRIPTION 
        "This measures the shortest SIP setup-signal delay sampled since the system was started or since this measurement was cleared"
    ::= { sipStats 45 }

  bwDXSSipStatsMaxSetupSignalDelay OBJECT-TYPE
    SYNTAX      Gauge32
    MAX-ACCESS  read-write
    STATUS      current
    DESCRIPTION 
        "This measures the longest SIP setup-signal delay sampled since the system was started or since this measurement was cleared"
    ::= { sipStats 46 }

  bwDXSSipStatsAnswerSignalDelay OBJECT-TYPE
    SYNTAX      Gauge32
    MAX-ACCESS  read-write
    STATUS      current
    DESCRIPTION 
        "This gauge measures the average time (in milliseconds) between the receipt of a 200 OK message indicating answer or a NTFY off-hook indicating answer and the transmission of a 200 OK indicating answer to the originator.   This measurement is intended to reflect internal queuing, scheduling, and processing delays.
         This gauge is applicable to only the SIP originated calls for which the setup-signal delay is measured.  Answer signal delay is not measured when the call has been forwarded, redirected, or when the call has encountered route advancing"
    ::= { sipStats 47 }

  bwDXSSipStatsMinAnswerSignalDelay OBJECT-TYPE
    SYNTAX      Gauge32
    MAX-ACCESS  read-write
    STATUS      current
    DESCRIPTION 
        "This measures the shortest SIP answer-signal delay sampled since the system was started or since this measurement was cleared"
    ::= { sipStats 49 }

  bwDXSSipStatsMaxAnswerSignalDelay OBJECT-TYPE
    SYNTAX      Gauge32
    MAX-ACCESS  read-write
    STATUS      current
    DESCRIPTION 
        "This measures the longest SIP answer-signal delay sampled since the system was started or since this measurement was cleared"
    ::= { sipStats 50 }

  bwDXSSipStatsRegistrationsPerMinute OBJECT-TYPE
    SYNTAX      Gauge32
    MAX-ACCESS  read-only
    STATUS      current
    DESCRIPTION 
        "This gauge measures the rate at which the Application Server receives SIP REGISTER messages.  It uses the timestamps of up to the last 100 registrations received in calculating the rate"
    ::= { sipStats 51 }

  bwDXSSipStatsMsgRetryPercentageToOther OBJECT-TYPE
    SYNTAX      Gauge32
    MAX-ACCESS  read-only
    STATUS      current
    DESCRIPTION 
        "This gauge measures the percentage of SIP requests and reliable responses sent (to nodes other than those covered by bwDXSSipStatsMsgRetryToNeTable) due to retry.  Of up to the last 100 requests and reliable responses sent, this gauge calculates the percentage sent due to retransmission (i.e. - gauge = (SIP request retransmissions + SIP reliable response retransmissions) / (SIP request initial transmissions + SIP request retransmissions + SIP reliable response initial transmissions + SIP reliable response retransmissions)"
    ::= { sipStats 52 }

  bwDXSSipStatsMsgRetryToNeTable OBJECT-TYPE
    SYNTAX      SEQUENCE OF BwSipStatsMsgRetryToNeEntry
    MAX-ACCESS  not-accessible
    STATUS      current
    DESCRIPTION 
        "This gauge table consists of a bwDXSSipStatsMsgRetryToNEEntry per Network Element address.  A Network Element can be a Network Server, Media Server, a Network Gateway, etc - anything but an access device."
    ::= { sipStats 53 }

  bwDXSSipStatsMsgRetryToNeEntry OBJECT-TYPE
    SYNTAX      BwSipStatsMsgRetryToNeEntry
    MAX-ACCESS  not-accessible
    STATUS      current
    DESCRIPTION 
        "This row contains information on a particular Network Element"
    INDEX       { bwDXSSipStatsMsgRetryToNeID }
    ::= { bwDXSSipStatsMsgRetryToNeTable 1 }

  BwSipStatsMsgRetryToNeEntry ::= SEQUENCE {
    bwDXSSipStatsMsgRetryToNeID            Unsigned32,
    bwDXSSipStatsMsgRetryToNeAddr          DisplayString,
    bwDXSSipStatsMsgRetryToNePercentage    Gauge32
  }

  bwDXSSipStatsMsgRetryToNeID OBJECT-TYPE
    SYNTAX      Unsigned32
    MAX-ACCESS  read-only
    STATUS      current
    DESCRIPTION 
        "This integer represents the unique index of a Network Element"
    ::= { bwDXSSipStatsMsgRetryToNeEntry 1 }

  bwDXSSipStatsMsgRetryToNeAddr OBJECT-TYPE
    SYNTAX      DisplayString
    MAX-ACCESS  read-only
    STATUS      current
    DESCRIPTION 
        "This string represents a Network Element address"
    ::= { bwDXSSipStatsMsgRetryToNeEntry 2 }

  bwDXSSipStatsMsgRetryToNePercentage OBJECT-TYPE
    SYNTAX      Gauge32
    MAX-ACCESS  read-only
    STATUS      current
    DESCRIPTION 
        "The gauge measures for that particular Network Element the percentage of SIP requests and reliable responses sent due to retry.  Of up to the last 100 requests and reliable responses sent to a particular NetworkElement address, this gauge calculates the percentage sent due to retransmission (i.e. - gauge = (SIP request retransmissions + SIP reliable response retransmissions) / (SIP request initial transmissions + SIP request retransmissions + SIP reliable response initial transmissions + SIP reliable response retransmissions)."
    ::= { bwDXSSipStatsMsgRetryToNeEntry 3 }

  bwDXSSipStatsActiveTcpConnections OBJECT-TYPE
    SYNTAX      Gauge32
    MAX-ACCESS  read-only
    STATUS      current
    DESCRIPTION 
        "This gauge is incremented whenever a SIP TCP connection is established.   It decremented whenever a connection is closed."
    ::= { sipStats 54 }

  bwDXSSipStatsTcpIns OBJECT-TYPE
    SYNTAX      Counter32
    MAX-ACCESS  read-write
    STATUS      current
    DESCRIPTION 
        "This counter is incremented whenever a SIP message is received via TCP."
    ::= { sipStats 55 }

  bwDXSSipStatsTcpOuts OBJECT-TYPE
    SYNTAX      Counter32
    MAX-ACCESS  read-write
    STATUS      current
    DESCRIPTION 
        "This counter is incremented whenever a SIP message is sent via TCP."
    ::= { sipStats 56 }

  bwDXSSipStatsTcpFailures OBJECT-TYPE
    SYNTAX      Counter32
    MAX-ACCESS  read-write
    STATUS      current
    DESCRIPTION 
        "This counter is incremented whenever a SIP message was attempted to be sent via TCP but failed."
    ::= { sipStats 57 }

  bwDXSSipStatsUdpIns OBJECT-TYPE
    SYNTAX      Counter32
    MAX-ACCESS  read-write
    STATUS      current
    DESCRIPTION 
        "This counter is incremented whenever a SIP message is received via UDP."
    ::= { sipStats 58 }

  bwDXSSipStatsUdpOuts OBJECT-TYPE
    SYNTAX      Counter32
    MAX-ACCESS  read-write
    STATUS      current
    DESCRIPTION 
        "This counter is incremented whenever a SIP message is sent via UDP."
    ::= { sipStats 59 }

  bwDXSSIPReclaimedStaleTcpConnections OBJECT-TYPE
    SYNTAX      Counter32
    MAX-ACCESS  read-write
    STATUS      current
    DESCRIPTION 
        "This counter is incremented every time a SIP TCP connection is reclaimed because it is stale."
    ::= { sipStats 60 }

  bwDXSSipStatsPublishIns OBJECT-TYPE
    SYNTAX      Counter32
    MAX-ACCESS  read-write
    STATUS      current
    DESCRIPTION 
        "This counter displays the total number of PUBLISH requests received by BroadWorks."
-- @feature:213832
    ::= { sipStats 61 }

  bwDXSSipStatsPublishOuts OBJECT-TYPE
    SYNTAX      Counter32
    MAX-ACCESS  read-write
    STATUS      current
    DESCRIPTION 
        "This counter displays the total number of PUBLISH requests sent by BroadWorks."
-- @feature:213832
    ::= { sipStats 62 }

  bwDXSSipStatsPublishResponsesTable OBJECT-TYPE
    SYNTAX      SEQUENCE OF BwSipStatsPublishResponsesEntry
    MAX-ACCESS  not-accessible
    STATUS      current
    DESCRIPTION 
        "This table contains the counters for all SIP responses to the PUBLISH requests received or sent by BroadWorks. Each counter is a 32-Bit counter. The response code is used to index into the table. Here are all the response codes:  100, 180, 181, 182, 183, 200, 300, 301, 302, 305, 380, 400, 401, 402, 403, 404, 405, 406, 407, 408, 409, 410, 411, 412, 413, 414, 415, 420, 480, 481, 482, 483, 484, 485, 486, 487, 500, 501, 502, 503, 504, 505, 600, 603, 604, 606."
-- @feature:213832
    ::= { sipStats 63 }

  bwSipStatsPublishResponsesEntry OBJECT-TYPE
    SYNTAX      BwSipStatsPublishResponsesEntry
    MAX-ACCESS  not-accessible
    STATUS      current
    DESCRIPTION 
        "This row contains information on a particular SIP status code received or sent in response to a PUBLISH."
    INDEX       { bwDXSSipStatsPublishResponseCodeValue }
    ::= { bwDXSSipStatsPublishResponsesTable 1 }

  BwSipStatsPublishResponsesEntry ::= SEQUENCE {
    bwDXSSipStatsPublishResponseCodeValue Integer32,
    bwDXSSipStatsPublishResponseIns       Counter32,
    bwDXSSipStatsPublishResponseOuts      Counter32
  }

  bwDXSSipStatsPublishResponseCodeValue OBJECT-TYPE
    SYNTAX      Integer32 (100..999)
    MAX-ACCESS  not-accessible
    STATUS      current
    DESCRIPTION 
        "This integer represents a SIP status code.  The rest of the information in this row is related to this value."
-- @feature:213832
    ::= { bwSipStatsPublishResponsesEntry 1 }

  bwDXSSipStatsPublishResponseIns OBJECT-TYPE
    SYNTAX      Counter32
    MAX-ACCESS  read-write
    STATUS      current
    DESCRIPTION 
        "This counter represents the number of SIP responses received in response to a PUBLISH."
-- @feature:213832
    ::= { bwSipStatsPublishResponsesEntry 2 }

  bwDXSSipStatsPublishResponseOuts OBJECT-TYPE
    SYNTAX      Counter32
    MAX-ACCESS  read-write
    STATUS      current
    DESCRIPTION 
        "This counter represents the number of SIP responses sent in response to a PUBLISH."
-- @feature:213832
    ::= { bwSipStatsPublishResponsesEntry 3 }

bwDXSCongestionManagementNeighborTable OBJECT-TYPE
    SYNTAX      SEQUENCE OF BwCongestionManagementNeighborEntry
    MAX-ACCESS  not-accessible
    STATUS      current
    DESCRIPTION 
        "This table consists of bwDXSCongestionManagementNeighborEntry. "
    ::= { congestionManagement 1 }

  bwDXSCongestionManagementNeighborEntry OBJECT-TYPE
    SYNTAX      BwCongestionManagementNeighborEntry
    MAX-ACCESS  not-accessible
    STATUS      current
    DESCRIPTION 
        "This row contains information on a particular neighbor."
    INDEX       { bwDXSCongestionManagementNeighborIndex }
    ::= { bwDXSCongestionManagementNeighborTable 1 }

  BwCongestionManagementNeighborEntry ::= SEQUENCE {
    bwDXSCongestionManagementNeighborIndex                     Unsigned32,
    bwDXSCongestionManagementNeighborIpAddress                 DisplayString,
    bwDXSCongestionManagementNeighborInviteIn                  Counter32,
    bwDXSCongestionManagementNeighborInviteOut                 Counter32,
    bwDXSCongestionManagementNeighborRegisterIn                Counter32,
    bwDXSCongestionManagementNeighborOptionsIn                 Counter32,
    bwDXSCongestionManagementNeighborOptionsOut                Counter32,
    bwDXSCongestionManagementNeighborSubscribeNotifyIn         Counter32,
    bwDXSCongestionManagementNeighborSubscribeNotifyOut        Counter32,
    bwDXSCongestionManagementNeighbor5xxIn                     Counter32,
    bwDXSCongestionManagementNeighborCallpMessageInRate        Gauge32,
    bwDXSCongestionManagementNeighborCallpMessageOutRate       Gauge32,
    bwDXSCongestionManagementNeighborCallpRequestInRate        Gauge32,
    bwDXSCongestionManagementNeighborNonCallpMessageInRate     Gauge32,
    bwDXSCongestionManagementNeighborNonCallpMessageOutRate    Gauge32,
    bwDXSCongestionManagementNeighborNonCallpRequestInRate     Gauge32,
    bwDXSCongestionManagementNeighborState                     DisplayString,
    bwDXSCongestionManagementNeighborCapability                DisplayString
  }

  bwDXSCongestionManagementNeighborIndex OBJECT-TYPE
    SYNTAX      Unsigned32
    MAX-ACCESS  read-only
    STATUS      current
    DESCRIPTION 
        "This integer represents the neighbor index in the system"
    ::= { bwDXSCongestionManagementNeighborEntry 1 }

  bwDXSCongestionManagementNeighborIpAddress OBJECT-TYPE
    SYNTAX      DisplayString
    MAX-ACCESS  read-only
    STATUS      current
    DESCRIPTION 
        "The IP address of the neighbor."
    ::= { bwDXSCongestionManagementNeighborEntry 2 }

  bwDXSCongestionManagementNeighborInviteIn OBJECT-TYPE
    SYNTAX      Counter32
    MAX-ACCESS  read-write
    STATUS      current
    DESCRIPTION 
        "This is the number of Invite requests that the neighbor sends to the AS."
    ::= { bwDXSCongestionManagementNeighborEntry 3 }

  bwDXSCongestionManagementNeighborInviteOut OBJECT-TYPE
    SYNTAX      Counter32
    MAX-ACCESS  read-write
    STATUS      current
    DESCRIPTION 
        "This is the number of Invite requests that the AS sends to the neighbor."
    ::= { bwDXSCongestionManagementNeighborEntry 4 }

  bwDXSCongestionManagementNeighborRegisterIn OBJECT-TYPE
    SYNTAX      Counter32
    MAX-ACCESS  read-write
    STATUS      current
    DESCRIPTION 
        "This is the number of Register requests that the neighbor sends to the AS."
    ::= { bwDXSCongestionManagementNeighborEntry 5 }

  bwDXSCongestionManagementNeighborOptionsIn OBJECT-TYPE
    SYNTAX      Counter32
    MAX-ACCESS  read-write
    STATUS      current
    DESCRIPTION 
        "This is the number of Options requests that the neighbor sends to the AS."
    ::= { bwDXSCongestionManagementNeighborEntry 6 }

  bwDXSCongestionManagementNeighborOptionsOut OBJECT-TYPE
    SYNTAX      Counter32
    MAX-ACCESS  read-write
    STATUS      current
    DESCRIPTION 
        "This is the number of Options requests that the AS sends to the neighbor."
    ::= { bwDXSCongestionManagementNeighborEntry 7 }

  bwDXSCongestionManagementNeighborSubscribeNotifyIn OBJECT-TYPE
    SYNTAX      Counter32
    MAX-ACCESS  read-write
    STATUS      current
    DESCRIPTION 
        "This is the number of Subscribe and Notify requests that the neighbor sends to the AS."
    ::= { bwDXSCongestionManagementNeighborEntry 8 }

  bwDXSCongestionManagementNeighborSubscribeNotifyOut OBJECT-TYPE
    SYNTAX      Counter32
    MAX-ACCESS  read-write
    STATUS      current
    DESCRIPTION 
        "This is the number of Subscribe and Notify requests that the AS sends to the neighbor."
    ::= { bwDXSCongestionManagementNeighborEntry 9 }

  bwDXSCongestionManagementNeighbor5xxIn OBJECT-TYPE
    SYNTAX      Counter32
    MAX-ACCESS  read-write
    STATUS      current
    DESCRIPTION 
        "This is the number of 5xx responses that the neighbor sends to the AS."
    ::= { bwDXSCongestionManagementNeighborEntry 10 }

  bwDXSCongestionManagementNeighborCallpMessageInRate OBJECT-TYPE
    SYNTAX      Gauge32
    MAX-ACCESS  read-only
    STATUS      current
    DESCRIPTION 
        "This is the incoming callp messages (requests and responses) rate."
    ::= { bwDXSCongestionManagementNeighborEntry 11 }

  bwDXSCongestionManagementNeighborCallpMessageOutRate OBJECT-TYPE
    SYNTAX      Gauge32
    MAX-ACCESS  read-only
    STATUS      current
    DESCRIPTION 
        "This is the outgoing callp messages (requests and responses) rate."
    ::= { bwDXSCongestionManagementNeighborEntry 12 }

  bwDXSCongestionManagementNeighborCallpRequestInRate OBJECT-TYPE
    SYNTAX      Gauge32
    MAX-ACCESS  read-only
    STATUS      current
    DESCRIPTION 
        "This is the incoming callp requests rate."
    ::= { bwDXSCongestionManagementNeighborEntry 13 }

  bwDXSCongestionManagementNeighborNonCallpMessageInRate OBJECT-TYPE
    SYNTAX      Gauge32
    MAX-ACCESS  read-only
    STATUS      current
    DESCRIPTION 
        "This is the incoming non-callp messages (requests and responses) rate."
    ::= { bwDXSCongestionManagementNeighborEntry 14 }

  bwDXSCongestionManagementNeighborNonCallpMessageOutRate OBJECT-TYPE
    SYNTAX      Gauge32
    MAX-ACCESS  read-only
    STATUS      current
    DESCRIPTION 
        "This is the outgoing non-callp messages (requests and responses) rate."
    ::= { bwDXSCongestionManagementNeighborEntry 15 }

  bwDXSCongestionManagementNeighborNonCallpRequestInRate OBJECT-TYPE
    SYNTAX      Gauge32
    MAX-ACCESS  read-only
    STATUS      current
    DESCRIPTION 
        "This is the incoming non-callp requests rate."
    ::= { bwDXSCongestionManagementNeighborEntry 16 }

  bwDXSCongestionManagementNeighborState OBJECT-TYPE
    SYNTAX      DisplayString
    MAX-ACCESS  read-only
    STATUS      current
    DESCRIPTION 
        "The current congestion management state of the neighbor."
    ::= { bwDXSCongestionManagementNeighborEntry 17 }

  bwDXSCongestionManagementNeighborCapability OBJECT-TYPE
    SYNTAX      DisplayString
    MAX-ACCESS  read-only
    STATUS      current
    DESCRIPTION 
        "The congestion management capability of the neighbor."
    ::= { bwDXSCongestionManagementNeighborEntry 18 }

-- SERVICES

  bwDXSAuthCodeNumAttempts OBJECT-TYPE
    SYNTAX      Counter32
    MAX-ACCESS  read-write
    STATUS      current
    DESCRIPTION 
        "This counter reflects the number of authorization attempts"
    ::= { accountCodes 1 }

  bwDXSAuthCodeNumValidations OBJECT-TYPE
    SYNTAX      Counter32
    MAX-ACCESS  read-write
    STATUS      current
    DESCRIPTION 
        "This counter reflects the number of successful validations"
    ::= { accountCodes 2 }

  bwDXSAccountCodeNumAttempts OBJECT-TYPE
    SYNTAX      Counter32
    MAX-ACCESS  read-write
    STATUS      current
    DESCRIPTION 
        "This counter is incremented whenever the user is prompted for an account code in Automatic mode"
    ::= { accountCodes 3 }

  bwDXSAccountCodesSPTable OBJECT-TYPE
    SYNTAX      SEQUENCE OF BwAccountCodesSPEntry
    MAX-ACCESS  not-accessible
    STATUS      current
    DESCRIPTION 
        "This table contains the counters for Account/Authorization Codes service measurements for service providers"
    ::= { accountCodes 4 }

  bwDXSAccountCodesSPEntry OBJECT-TYPE
    SYNTAX      BwAccountCodesSPEntry
    MAX-ACCESS  not-accessible
    STATUS      current
    DESCRIPTION 
        "This row contains the counters for Account/Authorization Codes service measurements for a service provider"
    INDEX       { bwDXSAccountCodesSPIndex }
    ::= { bwDXSAccountCodesSPTable 1 }

  BwAccountCodesSPEntry ::= SEQUENCE {
    bwDXSAccountCodesSPIndex               Unsigned32,
    bwDXSAccountCodesSPID                  DisplayString,
    bwDXSAuthCodeSPNumAttempts             Counter32,
    bwDXSAuthCodeSPNumValidations          Counter32,
    bwDXSAccountCodeSPNumAttempts          Counter32,
    bwDXSAccountCodeSPNumPerCallAttempts   Counter32
  }

  bwDXSAccountCodesSPIndex OBJECT-TYPE
    SYNTAX      Unsigned32
    MAX-ACCESS  read-only
    STATUS      current
    DESCRIPTION 
        "This integer represents the a service provider index in the system"
    ::= { bwDXSAccountCodesSPEntry 1 }

  bwDXSAccountCodesSPID OBJECT-TYPE
    SYNTAX      DisplayString
    MAX-ACCESS  read-only
    STATUS      current
    DESCRIPTION 
        "This string represents a service provider ID"
    ::= { bwDXSAccountCodesSPEntry 2 }

  bwDXSAuthCodeSPNumAttempts OBJECT-TYPE
    SYNTAX      Counter32
    MAX-ACCESS  read-write
    STATUS      current
    DESCRIPTION 
        "This counter reflects the number of authorization attempts for a service provider"
    ::= { bwDXSAccountCodesSPEntry 3 }

  bwDXSAuthCodeSPNumValidations OBJECT-TYPE
    SYNTAX      Counter32
    MAX-ACCESS  read-write
    STATUS      current
    DESCRIPTION 
        "This counter reflects the number of successful validations for a service provider"
    ::= { bwDXSAccountCodesSPEntry 4 }

  bwDXSAccountCodeSPNumAttempts OBJECT-TYPE
    SYNTAX      Counter32
    MAX-ACCESS  read-write
    STATUS      current
    DESCRIPTION 
        "Number of attempts to validate an Account Code (for a given service provider)."
    ::= { bwDXSAccountCodesSPEntry 5 }

  bwDXSAccountCodeSPNumPerCallAttempts OBJECT-TYPE
    SYNTAX      Counter32
    MAX-ACCESS  read-write
    STATUS      current
    DESCRIPTION 
        "Number of attempts to validate an Account Code (for a given service provider)."
    ::= { bwDXSAccountCodesSPEntry 6 }

  bwDXSAccountCodesGroupTable OBJECT-TYPE
    SYNTAX      SEQUENCE OF BwAccountCodesGroupEntry
    MAX-ACCESS  not-accessible
    STATUS      current
    DESCRIPTION 
        "This table contains the counters for Account/Authorization Codes service measurements for groups"
    ::= { accountCodes 5 }

  bwDXSAccountCodesGroupEntry OBJECT-TYPE
    SYNTAX      BwAccountCodesGroupEntry
    MAX-ACCESS  not-accessible
    STATUS      current
    DESCRIPTION 
        "This row contains the counters for Account/Authorization Codes service measurements for a group"
    INDEX       { bwDXSAccountCodesGroupIndex }
    ::= { bwDXSAccountCodesGroupTable 1 }

  BwAccountCodesGroupEntry ::= SEQUENCE {
    bwDXSAccountCodesGroupIndex                Unsigned32,
    bwDXSAccountCodesGroupID                   DisplayString,
    bwDXSAuthCodeGroupNumAttempts              Counter32,
    bwDXSAuthCodeGroupNumValidations           Counter32,
    bwDXSAccountCodeGroupNumAttempts           Counter32,
    bwDXSAccountCodeGroupNumPerCallAttempts    Counter32
  }

  bwDXSAccountCodesGroupIndex OBJECT-TYPE
    SYNTAX      Unsigned32
    MAX-ACCESS  read-only
    STATUS      current
    DESCRIPTION 
        "This integer represents the a group index in the system"
    ::= { bwDXSAccountCodesGroupEntry 1 }

  bwDXSAccountCodesGroupID OBJECT-TYPE
    SYNTAX      DisplayString
    MAX-ACCESS  read-only
    STATUS      current
    DESCRIPTION 
        "This string represents a Group ID"
    ::= { bwDXSAccountCodesGroupEntry 2 }

  bwDXSAuthCodeGroupNumAttempts OBJECT-TYPE
    SYNTAX      Counter32
    MAX-ACCESS  read-write
    STATUS      current
    DESCRIPTION 
        "This counter reflects the number of authorization attempts for a group"
    ::= { bwDXSAccountCodesGroupEntry 3 }

  bwDXSAuthCodeGroupNumValidations OBJECT-TYPE
    SYNTAX      Counter32
    MAX-ACCESS  read-write
    STATUS      current
    DESCRIPTION 
        "This counter reflects the number of successful validations for a group"
    ::= { bwDXSAccountCodesGroupEntry 4 }

  bwDXSAccountCodeGroupNumAttempts OBJECT-TYPE
    SYNTAX      Counter32
    MAX-ACCESS  read-write
    STATUS      current
    DESCRIPTION 
        "This counter reflects the number of Account code attempts for a group"
    ::= { bwDXSAccountCodesGroupEntry 5 }

  bwDXSAccountCodeGroupNumPerCallAttempts OBJECT-TYPE
    SYNTAX      Counter32
    MAX-ACCESS  read-write
    STATUS      current
    DESCRIPTION 
        "Number of attempts to validate an Account Code (for a given group)."
    ::= { bwDXSAccountCodesGroupEntry 6 }

  bwDXSAccountCodeNumPerCallAttempts OBJECT-TYPE
    SYNTAX      Counter32
    MAX-ACCESS  read-write
    STATUS      current
    DESCRIPTION 
        "This counter is incremented whenever the user is prompted for an account code in FAC-based mode"
    ::= { accountCodes 6 }

  bwDXSAnonymousCallsNumRejected OBJECT-TYPE
    SYNTAX      Counter32
    MAX-ACCESS  read-write
    STATUS      current
    DESCRIPTION 
        "This counter reflects the number of incoming anonymous calls rejected"
    ::= { anonymousCallRejection 1 }

  bwDXSAnonymousCallRejectionSPTable OBJECT-TYPE
    SYNTAX      SEQUENCE OF BwAnonymousCallRejectionSPEntry
    MAX-ACCESS  not-accessible
    STATUS      current
    DESCRIPTION 
        "This table contains the counters for Anonymous Call Rejection service measurements for service providers"
    ::= { anonymousCallRejection 2 }

  bwDXSAnonymousCallRejectionSPEntry OBJECT-TYPE
    SYNTAX      BwAnonymousCallRejectionSPEntry
    MAX-ACCESS  not-accessible
    STATUS      current
    DESCRIPTION 
        "This row contains the counters for Anonymous Call Rejection service measurements for a service provider"
    INDEX       { bwDXSAnonymousCallRejectionSPIndex }
    ::= { bwDXSAnonymousCallRejectionSPTable 1 }

  BwAnonymousCallRejectionSPEntry ::= SEQUENCE {
    bwDXSAnonymousCallRejectionSPIndex     Unsigned32,
    bwDXSAnonymousCallRejectionSPID        DisplayString,
    bwDXSAnonymousCallsSPNumRejected       Counter32
  }

  bwDXSAnonymousCallRejectionSPIndex OBJECT-TYPE
    SYNTAX      Unsigned32
    MAX-ACCESS  read-only
    STATUS      current
    DESCRIPTION 
        "This integer represents the a service provider index in the system"
    ::= { bwDXSAnonymousCallRejectionSPEntry 1 }

  bwDXSAnonymousCallRejectionSPID OBJECT-TYPE
    SYNTAX      DisplayString
    MAX-ACCESS  read-only
    STATUS      current
    DESCRIPTION 
        "This string represents a service provider ID"
    ::= { bwDXSAnonymousCallRejectionSPEntry 2 }

  bwDXSAnonymousCallsSPNumRejected OBJECT-TYPE
    SYNTAX      Counter32
    MAX-ACCESS  read-write
    STATUS      current
    DESCRIPTION 
        "This counter reflects the number of incoming anonymous calls rejected by a service provider"
    ::= { bwDXSAnonymousCallRejectionSPEntry 3 }

  bwDXSAnonymousCallRejectionGroupTable OBJECT-TYPE
    SYNTAX      SEQUENCE OF BwAnonymousCallRejectionGroupEntry
    MAX-ACCESS  not-accessible
    STATUS      current
    DESCRIPTION 
        "This table contains the counters for Anonymous Call Rejection service measurements for group"
    ::= { anonymousCallRejection 3 }

  bwDXSAnonymousCallRejectionGroupEntry OBJECT-TYPE
    SYNTAX      BwAnonymousCallRejectionGroupEntry
    MAX-ACCESS  not-accessible
    STATUS      current
    DESCRIPTION 
        "This row contains the counters for Anonymous Call Rejection service measurements for a group"
    INDEX       { bwDXSAnonymousCallRejectionGroupIndex }
    ::= { bwDXSAnonymousCallRejectionGroupTable 1 }

  BwAnonymousCallRejectionGroupEntry ::= SEQUENCE {
    bwDXSAnonymousCallRejectionGroupIndex  Unsigned32,
    bwDXSAnonymousCallRejectionGroupID     DisplayString,
    bwDXSAnonymousCallsGroupNumRejected    Counter32
  }

  bwDXSAnonymousCallRejectionGroupIndex OBJECT-TYPE
    SYNTAX      Unsigned32
    MAX-ACCESS  read-only
    STATUS      current
    DESCRIPTION 
        "This integer represents the a group index in the system"
    ::= { bwDXSAnonymousCallRejectionGroupEntry 1 }

  bwDXSAnonymousCallRejectionGroupID OBJECT-TYPE
    SYNTAX      DisplayString
    MAX-ACCESS  read-only
    STATUS      current
    DESCRIPTION 
        "This string represents a group ID"
    ::= { bwDXSAnonymousCallRejectionGroupEntry 2 }

  bwDXSAnonymousCallsGroupNumRejected OBJECT-TYPE
    SYNTAX      Counter32
    MAX-ACCESS  read-write
    STATUS      current
    DESCRIPTION 
        "This counter reflects the number of incoming anonymous calls rejected by a group"
    ::= { bwDXSAnonymousCallRejectionGroupEntry 3 }

  bwDXSAuthenticationNumChallenges OBJECT-TYPE
    SYNTAX      Counter32
    MAX-ACCESS  read-write
    STATUS      current
    DESCRIPTION 
        "This counter reflects the number of authentication challenges"
    ::= { authentication 1 }

  bwDXSAuthenticationNumValidResponses OBJECT-TYPE
    SYNTAX      Counter32
    MAX-ACCESS  read-write
    STATUS      current
    DESCRIPTION 
        "This counter reflects the number of valid client authentication responses"
    ::= { authentication 2 }

  bwDXSAuthenticationSPTable OBJECT-TYPE
    SYNTAX      SEQUENCE OF BwAuthenticationSPEntry
    MAX-ACCESS  not-accessible
    STATUS      current
    DESCRIPTION 
        "This table contains the counters for Authentication service measurements for service providers"
    ::= { authentication 3 }

  bwDXSAuthenticationSPEntry OBJECT-TYPE
    SYNTAX      BwAuthenticationSPEntry
    MAX-ACCESS  not-accessible
    STATUS      current
    DESCRIPTION 
        "This row contains the counters for Authentication service measurements for a service provider"
    INDEX       { bwDXSAuthenticationSPIndex }
    ::= { bwDXSAuthenticationSPTable 1 }

  BwAuthenticationSPEntry ::= SEQUENCE {
    bwDXSAuthenticationSPIndex                 Unsigned32,
    bwDXSAuthenticationSPID                    DisplayString,
    bwDXSAuthenticationSPNumChallenges         Counter32,
    bwDXSAuthenticationSPNumValidResponses     Counter32
  }

  bwDXSAuthenticationSPIndex OBJECT-TYPE
    SYNTAX      Unsigned32
    MAX-ACCESS  read-only
    STATUS      current
    DESCRIPTION 
        "This integer represents the a service provider index in the system"
    ::= { bwDXSAuthenticationSPEntry 1 }

  bwDXSAuthenticationSPID OBJECT-TYPE
    SYNTAX      DisplayString
    MAX-ACCESS  read-only
    STATUS      current
    DESCRIPTION 
        "This string represents a service provider ID"
    ::= { bwDXSAuthenticationSPEntry 2 }

  bwDXSAuthenticationSPNumChallenges OBJECT-TYPE
    SYNTAX      Counter32
    MAX-ACCESS  read-write
    STATUS      current
    DESCRIPTION 
        "This counter reflects the number of authentication challenges by a service provider"
    ::= { bwDXSAuthenticationSPEntry 3 }

  bwDXSAuthenticationSPNumValidResponses OBJECT-TYPE
    SYNTAX      Counter32
    MAX-ACCESS  read-write
    STATUS      current
    DESCRIPTION 
        "This counter reflects the number of valid client authentication responses by a service provider"
    ::= { bwDXSAuthenticationSPEntry 4 }

  bwDXSAuthenticationGroupTable OBJECT-TYPE
    SYNTAX      SEQUENCE OF BwAuthenticationGroupEntry
    MAX-ACCESS  not-accessible
    STATUS      current
    DESCRIPTION 
        "This table contains the counters for Authentication service measurements for groups"
    ::= { authentication 4 }

  bwDXSAuthenticationGroupEntry OBJECT-TYPE
    SYNTAX      BwAuthenticationGroupEntry
    MAX-ACCESS  not-accessible
    STATUS      current
    DESCRIPTION 
        "This row contains the counters for Authentication service measurements for a group"
    INDEX       { bwDXSAuthenticationGroupIndex }
    ::= { bwDXSAuthenticationGroupTable 1 }

  BwAuthenticationGroupEntry ::= SEQUENCE {
    bwDXSAuthenticationGroupIndex              Unsigned32,
    bwDXSAuthenticationGroupID                 DisplayString,
    bwDXSAuthenticationGroupNumChallenges      Counter32,
    bwDXSAuthenticationGroupNumValidResponses  Counter32
  }

  bwDXSAuthenticationGroupIndex OBJECT-TYPE
    SYNTAX      Unsigned32
    MAX-ACCESS  read-only
    STATUS      current
    DESCRIPTION 
        "This integer represents the a group index in the system"
    ::= { bwDXSAuthenticationGroupEntry 1 }

  bwDXSAuthenticationGroupID OBJECT-TYPE
    SYNTAX      DisplayString
    MAX-ACCESS  read-only
    STATUS      current
    DESCRIPTION 
        "This string represents a group ID"
    ::= { bwDXSAuthenticationGroupEntry 2 }

  bwDXSAuthenticationGroupNumChallenges OBJECT-TYPE
    SYNTAX      Counter32
    MAX-ACCESS  read-write
    STATUS      current
    DESCRIPTION 
        "This counter reflects the number of authentication challenges by a group"
    ::= { bwDXSAuthenticationGroupEntry 3 }

  bwDXSAuthenticationGroupNumValidResponses OBJECT-TYPE
    SYNTAX      Counter32
    MAX-ACCESS  read-write
    STATUS      current
    DESCRIPTION 
        "This counter reflects the number of valid client authentication responses by a group"
    ::= { bwDXSAuthenticationGroupEntry 4 }

  bwDXSAutoAttendantNumAnswers OBJECT-TYPE
    SYNTAX      Counter32
    MAX-ACCESS  read-write
    STATUS      current
    DESCRIPTION 
        "This counter reflects the number of times the Auto Attendant answers an incoming call"
    ::= { autoAttendant 1 }

  bwDXSAutoAttendantNumTransfers OBJECT-TYPE
    SYNTAX      Counter32
    MAX-ACCESS  read-write
    STATUS      current
    DESCRIPTION 
        "This counter reflects the number times a call is transferred to another party
         (name dialing, ext. dialing, etc.) by the Auto Attendant"
    ::= { autoAttendant 2 }

  bwDXSAutoAttendantSPTable OBJECT-TYPE
    SYNTAX      SEQUENCE OF BwAutoAttendantSPEntry
    MAX-ACCESS  not-accessible
    STATUS      current
    DESCRIPTION 
        "This table contains the counters for Auto Attendant service measurements for service providers"
    ::= { autoAttendant 3 }

  bwDXSAutoAttendantSPEntry OBJECT-TYPE
    SYNTAX      BwAutoAttendantSPEntry
    MAX-ACCESS  not-accessible
    STATUS      current
    DESCRIPTION 
        "This row contains the counters for Auto Attendant Rejection service measurements for a service provider"
    INDEX       { bwDXSAutoAttendantSPIndex }
    ::= { bwDXSAutoAttendantSPTable 1 }

  BwAutoAttendantSPEntry ::= SEQUENCE {
    bwDXSAutoAttendantSPIndex          Unsigned32,
    bwDXSAutoAttendantSPID             DisplayString,
    bwDXSAutoAttendantSPNumAnswers     Counter32,
    bwDXSAutoAttendantSPNumTransfers   Counter32
  }

  bwDXSAutoAttendantSPIndex OBJECT-TYPE
    SYNTAX      Unsigned32
    MAX-ACCESS  read-only
    STATUS      current
    DESCRIPTION 
        "This integer represents the a service provider index in the system"
    ::= { bwDXSAutoAttendantSPEntry 1 }

  bwDXSAutoAttendantSPID OBJECT-TYPE
    SYNTAX      DisplayString
    MAX-ACCESS  read-only
    STATUS      current
    DESCRIPTION 
        "This string represents a service provider ID"
    ::= { bwDXSAutoAttendantSPEntry 2 }

  bwDXSAutoAttendantSPNumAnswers OBJECT-TYPE
    SYNTAX      Counter32
    MAX-ACCESS  read-write
    STATUS      current
    DESCRIPTION 
        "This counter reflects the number of times the Auto Attendant answers an incoming call by a service provider"
    ::= { bwDXSAutoAttendantSPEntry 3 }

  bwDXSAutoAttendantSPNumTransfers OBJECT-TYPE
    SYNTAX      Counter32
    MAX-ACCESS  read-write
    STATUS      current
    DESCRIPTION 
        "This counter reflects the number times a call is transferred to another party (name dialing, ext. dialing, etc.) by the Auto Attendant by a service provider"
    ::= { bwDXSAutoAttendantSPEntry 4 }

  bwDXSAutoAttendantGroupTable OBJECT-TYPE
    SYNTAX      SEQUENCE OF BwAutoAttendantGroupEntry
    MAX-ACCESS  not-accessible
    STATUS      current
    DESCRIPTION 
        "This table contains the counters for Auto Attendant service measurements for Groups"
    ::= { autoAttendant 4 }

  bwDXSAutoAttendantGroupEntry OBJECT-TYPE
    SYNTAX      BwAutoAttendantGroupEntry
    MAX-ACCESS  not-accessible
    STATUS      current
    DESCRIPTION 
        "This row contains the counters for Auto Attendant Rejection service measurements for a group"
    INDEX       { bwDXSAutoAttendantGroupIndex }
    ::= { bwDXSAutoAttendantGroupTable 1 }

  BwAutoAttendantGroupEntry ::= SEQUENCE {
    bwDXSAutoAttendantGroupIndex           Unsigned32,
    bwDXSAutoAttendantGroupID              DisplayString,
    bwDXSAutoAttendantGroupNumAnswers      Counter32,
    bwDXSAutoAttendantGroupNumTransfers    Counter32
  }

  bwDXSAutoAttendantGroupIndex OBJECT-TYPE
    SYNTAX      Unsigned32
    MAX-ACCESS  read-only
    STATUS      current
    DESCRIPTION 
        "This integer represents the a group index in the system"
    ::= { bwDXSAutoAttendantGroupEntry 1 }

  bwDXSAutoAttendantGroupID OBJECT-TYPE
    SYNTAX      DisplayString
    MAX-ACCESS  read-only
    STATUS      current
    DESCRIPTION 
        "This string represents a group ID"
    ::= { bwDXSAutoAttendantGroupEntry 2 }

  bwDXSAutoAttendantGroupNumAnswers OBJECT-TYPE
    SYNTAX      Counter32
    MAX-ACCESS  read-write
    STATUS      current
    DESCRIPTION 
        "This counter reflects the number of times the Auto Attendant answers an incoming call by a group"
    ::= { bwDXSAutoAttendantGroupEntry 3 }

  bwDXSAutoAttendantGroupNumTransfers OBJECT-TYPE
    SYNTAX      Counter32
    MAX-ACCESS  read-write
    STATUS      current
    DESCRIPTION 
        "This counter reflects the number times a call is transferred to another party (name dialing, ext. dialing, etc.) by the Auto Attendant by a group"
    ::= { bwDXSAutoAttendantGroupEntry 4 }

  bwDXSCallCapacityNumCallsAttempted OBJECT-TYPE
    SYNTAX      Counter32
    MAX-ACCESS  read-write
    STATUS      current
    DESCRIPTION 
        "This counter reflects the number of calls attempted"
    ::= { callCapacity 1 }

  bwDXSCallCapacityNumCallsBlocked OBJECT-TYPE
    SYNTAX      Counter32
    MAX-ACCESS  read-write
    STATUS      current
    DESCRIPTION 
        "This counter reflects the number of calls blocked by this service"
    ::= { callCapacity 2 }

  bwDXSCallCapacitySPTable OBJECT-TYPE
    SYNTAX      SEQUENCE OF BwCallCapacitySPEntry
    MAX-ACCESS  not-accessible
    STATUS      current
    DESCRIPTION 
        "This table contains the counters for Call Capacity Management service measurements for service providers"
    ::= { callCapacity 3 }

  bwDXSCallCapacitySPEntry OBJECT-TYPE
    SYNTAX      BwCallCapacitySPEntry
    MAX-ACCESS  not-accessible
    STATUS      current
    DESCRIPTION 
        "This row contains the counters for Call Capacity Management service measurements for a service provider"
    INDEX       { bwDXSCallCapacitySPIndex }
    ::= { bwDXSCallCapacitySPTable 1 }

  BwCallCapacitySPEntry ::= SEQUENCE {
    bwDXSCallCapacitySPIndex               Unsigned32,
    bwDXSCallCapacitySPID                  DisplayString,
    bwDXSCallCapacitySPNumCallsAttempted   Counter32,
    bwDXSCallCapacitySPNumCallsBlocked     Counter32
  }

  bwDXSCallCapacitySPIndex OBJECT-TYPE
    SYNTAX      Unsigned32
    MAX-ACCESS  read-only
    STATUS      current
    DESCRIPTION 
        "This integer represents the a service provider index in the system"
    ::= { bwDXSCallCapacitySPEntry 1 }

  bwDXSCallCapacitySPID OBJECT-TYPE
    SYNTAX      DisplayString
    MAX-ACCESS  read-only
    STATUS      current
    DESCRIPTION 
        "This string represents a service provider ID"
    ::= { bwDXSCallCapacitySPEntry 2 }

  bwDXSCallCapacitySPNumCallsAttempted OBJECT-TYPE
    SYNTAX      Counter32
    MAX-ACCESS  read-write
    STATUS      current
    DESCRIPTION 
        "This counter reflects the number of calls attempted by a service provider"
    ::= { bwDXSCallCapacitySPEntry 3 }

  bwDXSCallCapacitySPNumCallsBlocked OBJECT-TYPE
    SYNTAX      Counter32
    MAX-ACCESS  read-write
    STATUS      current
    DESCRIPTION 
        "This counter reflects the number of calls blocked by this service by a service provider"
    ::= { bwDXSCallCapacitySPEntry 4 }

  bwDXSCallCapacityGroupTable OBJECT-TYPE
    SYNTAX      SEQUENCE OF BwCallCapacityGroupEntry
    MAX-ACCESS  not-accessible
    STATUS      current
    DESCRIPTION 
        "This table contains the counters for Call Capacity Management service measurements for groups"
    ::= { callCapacity 4 }

  bwDXSCallCapacityGroupEntry OBJECT-TYPE
    SYNTAX      BwCallCapacityGroupEntry
    MAX-ACCESS  not-accessible
    STATUS      current
    DESCRIPTION 
        "This row contains the counters for Call Capacity Management service measurements for a group"
    INDEX       { bwDXSCallCapacityGroupIndex }
    ::= { bwDXSCallCapacityGroupTable 1 }

  BwCallCapacityGroupEntry ::= SEQUENCE {
    bwDXSCallCapacityGroupIndex                Unsigned32,
    bwDXSCallCapacityGroupID                   DisplayString,
    bwDXSCallCapacityGroupNumCallsAttempted    Counter32,
    bwDXSCallCapacityGroupNumCallsBlocked      Counter32
  }

  bwDXSCallCapacityGroupIndex OBJECT-TYPE
    SYNTAX      Unsigned32
    MAX-ACCESS  read-only
    STATUS      current
    DESCRIPTION 
        "This integer represents the a group index in the system"
    ::= { bwDXSCallCapacityGroupEntry 1 }

  bwDXSCallCapacityGroupID OBJECT-TYPE
    SYNTAX      DisplayString
    MAX-ACCESS  read-only
    STATUS      current
    DESCRIPTION 
        "This string represents a group ID"
    ::= { bwDXSCallCapacityGroupEntry 2 }

  bwDXSCallCapacityGroupNumCallsAttempted OBJECT-TYPE
    SYNTAX      Counter32
    MAX-ACCESS  read-write
    STATUS      current
    DESCRIPTION 
        "This counter reflects the number of calls attempted by a group"
    ::= { bwDXSCallCapacityGroupEntry 3 }

  bwDXSCallCapacityGroupNumCallsBlocked OBJECT-TYPE
    SYNTAX      Counter32
    MAX-ACCESS  read-write
    STATUS      current
    DESCRIPTION 
        "This counter reflects the number of calls blocked by this service by a group"
    ::= { bwDXSCallCapacityGroupEntry 4 }

  bwDXSCFANumForwarded OBJECT-TYPE
    SYNTAX      Counter32
    MAX-ACCESS  read-write
    STATUS      current
    DESCRIPTION 
        "This counter reflects the number of calls forwarded"
    ::= { callForwardingAlways 1 }

  bwDXSCFANumPhoneActivations OBJECT-TYPE
    SYNTAX      Counter32
    MAX-ACCESS  read-write
    STATUS      current
    DESCRIPTION 
        "Incremented whenever a user activates CFA via FAC"
    ::= { callForwardingAlways 2 }

  bwDXSCFANumPhoneDeactivations OBJECT-TYPE
    SYNTAX      Counter32
    MAX-ACCESS  read-write
    STATUS      current
    DESCRIPTION 
        "Incremented whenever a user deactivates CFN via FAC"
    ::= { callForwardingAlways 3 }

  bwDXSCallForwardingAlwaysSPTable OBJECT-TYPE
    SYNTAX      SEQUENCE OF BwCallForwardingAlwaysSPEntry
    MAX-ACCESS  not-accessible
    STATUS      current
    DESCRIPTION 
        "This table contains the counters for Call Forwarding Always service measurements for service providers"
    ::= { callForwardingAlways 4 }

  bwDXSCallForwardingAlwaysSPEntry OBJECT-TYPE
    SYNTAX      BwCallForwardingAlwaysSPEntry
    MAX-ACCESS  not-accessible
    STATUS      current
    DESCRIPTION 
        "This row contains the counters for Call Forwarding Always service measurements for a service provider"
    INDEX       { bwDXSCallForwardingAlwaysSPIndex }
    ::= { bwDXSCallForwardingAlwaysSPTable 1 }

  BwCallForwardingAlwaysSPEntry ::= SEQUENCE {
    bwDXSCallForwardingAlwaysSPIndex   Unsigned32,
    bwDXSCallForwardingAlwaysSPID      DisplayString,
    bwDXSCFASPNumForwarded             Counter32,
    bwDXSCFASPNumPhoneActivations      Counter32,
    bwDXSCFASPNumPhoneDeactivations    Counter32,
    bwDXSCFASPDestinationChanged       Counter32,
    bwDXSCFASPNumPhoneInterrogation    Counter32
  }

  bwDXSCallForwardingAlwaysSPIndex OBJECT-TYPE
    SYNTAX      Unsigned32
    MAX-ACCESS  read-only
    STATUS      current
    DESCRIPTION 
        "This integer represents the a service provider index in the system"
    ::= { bwDXSCallForwardingAlwaysSPEntry 1 }

  bwDXSCallForwardingAlwaysSPID OBJECT-TYPE
    SYNTAX      DisplayString
    MAX-ACCESS  read-only
    STATUS      current
    DESCRIPTION 
        "This string represents a service provider ID"
    ::= { bwDXSCallForwardingAlwaysSPEntry 2 }

  bwDXSCFASPNumForwarded OBJECT-TYPE
    SYNTAX      Counter32
    MAX-ACCESS  read-write
    STATUS      current
    DESCRIPTION 
        "This counter reflects the number of calls forwarded for a given service provider"
    ::= { bwDXSCallForwardingAlwaysSPEntry 3 }

  bwDXSCFASPNumPhoneActivations OBJECT-TYPE
    SYNTAX      Counter32
    MAX-ACCESS  read-write
    STATUS      current
    DESCRIPTION 
        "Number of times CFA has been activated via FAC for users in a given service provider"
    ::= { bwDXSCallForwardingAlwaysSPEntry 4 }

  bwDXSCFASPNumPhoneDeactivations OBJECT-TYPE
    SYNTAX      Counter32
    MAX-ACCESS  read-write
    STATUS      current
    DESCRIPTION 
        "Number of times CFA has been deactivated via FAC for users in a given service provider"
    ::= { bwDXSCallForwardingAlwaysSPEntry 5 }

  bwDXSCFASPDestinationChanged OBJECT-TYPE
    SYNTAX      Counter32
    MAX-ACCESS  read-write
    STATUS      current
    DESCRIPTION 
        "Number of times CFA destination has been changed, by FAC only for a given service provider"
    ::= { bwDXSCallForwardingAlwaysSPEntry 6 }

  bwDXSCFASPNumPhoneInterrogation OBJECT-TYPE
    SYNTAX      Counter32
    MAX-ACCESS  read-write
    STATUS      current
    DESCRIPTION 
        "This is the number of times CFA has been interrogated via FAC for users in a given service provider."
    ::= { bwDXSCallForwardingAlwaysSPEntry 7 }

  bwDXSCFADestinationChanged OBJECT-TYPE
    SYNTAX      Counter32
    MAX-ACCESS  read-write
    STATUS      current
    DESCRIPTION 
        "Incremented whenever a user changes the CFA destination via FAC"
    ::= { callForwardingAlways 5 }

  bwDXSCallForwardingAlwaysGroupTable OBJECT-TYPE
    SYNTAX      SEQUENCE OF BwCallForwardingAlwaysGroupEntry
    MAX-ACCESS  not-accessible
    STATUS      current
    DESCRIPTION 
        "This table contains the counters for Call Forwarding Always service measurements for groups"
    ::= { callForwardingAlways 6 }

  bwDXSCallForwardingAlwaysGroupEntry OBJECT-TYPE
    SYNTAX      BwCallForwardingAlwaysGroupEntry
    MAX-ACCESS  not-accessible
    STATUS      current
    DESCRIPTION 
        "This row contains the counters for Call Forwarding Always service measurements for a group"
    INDEX       { bwDXSCallForwardingAlwaysGroupIndex }
    ::= { bwDXSCallForwardingAlwaysGroupTable 1 }

  BwCallForwardingAlwaysGroupEntry ::= SEQUENCE {
    bwDXSCallForwardingAlwaysGroupIndex    Unsigned32,
    bwDXSCallForwardingAlwaysGroupID       DisplayString,
    bwDXSCFAGroupNumForwarded              Counter32,
    bwDXSCFAGroupNumPhoneActivations       Counter32,
    bwDXSCFAGroupNumPhoneDeactivations     Counter32,
    bwDXSCFAGroupDestinationChanged        Counter32,
    bwDXSCFAGroupNumPhoneInterrogation     Counter32
  }

  bwDXSCallForwardingAlwaysGroupIndex OBJECT-TYPE
    SYNTAX      Unsigned32
    MAX-ACCESS  read-only
    STATUS      current
    DESCRIPTION 
        "This integer represents the a group index in the system"
    ::= { bwDXSCallForwardingAlwaysGroupEntry 1 }

  bwDXSCallForwardingAlwaysGroupID OBJECT-TYPE
    SYNTAX      DisplayString
    MAX-ACCESS  read-only
    STATUS      current
    DESCRIPTION 
        "This string represents a group ID"
    ::= { bwDXSCallForwardingAlwaysGroupEntry 2 }

  bwDXSCFAGroupNumForwarded OBJECT-TYPE
    SYNTAX      Counter32
    MAX-ACCESS  read-write
    STATUS      current
    DESCRIPTION 
        "This counter reflects the number of calls forwarded for a given group"
    ::= { bwDXSCallForwardingAlwaysGroupEntry 3 }

  bwDXSCFAGroupNumPhoneActivations OBJECT-TYPE
    SYNTAX      Counter32
    MAX-ACCESS  read-write
    STATUS      current
    DESCRIPTION 
        "Number of times CFA has been activated via FAC for users in a given group"
    ::= { bwDXSCallForwardingAlwaysGroupEntry 4 }

  bwDXSCFAGroupNumPhoneDeactivations OBJECT-TYPE
    SYNTAX      Counter32
    MAX-ACCESS  read-write
    STATUS      current
    DESCRIPTION 
        "Number of times CFA has been deactivated via FAC for users in a given group"
    ::= { bwDXSCallForwardingAlwaysGroupEntry 5 }

  bwDXSCFAGroupDestinationChanged OBJECT-TYPE
    SYNTAX      Counter32
    MAX-ACCESS  read-write
    STATUS      current
    DESCRIPTION 
        "Number of times CFA destination has been changed, by FAC only for a given group"
    ::= { bwDXSCallForwardingAlwaysGroupEntry 6 }

  bwDXSCFAGroupNumPhoneInterrogation OBJECT-TYPE
    SYNTAX      Counter32
    MAX-ACCESS  read-write
    STATUS      current
    DESCRIPTION 
        "This is the number of times CFA has been interrogated via FAC for users in a given group."
    ::= { bwDXSCallForwardingAlwaysGroupEntry 7 }

  bwDXSCFANumPhoneInterrogation OBJECT-TYPE
    SYNTAX      Counter32
    MAX-ACCESS  read-write
    STATUS      current
    DESCRIPTION 
        "This is the number of times CFA has been interrogated via FAC."
    ::= { callForwardingAlways 7 }

  bwDXSCFBNumForwarded OBJECT-TYPE
    SYNTAX      Counter32
    MAX-ACCESS  read-write
    STATUS      current
    DESCRIPTION 
        "This counter reflects the number of times a call is forwarded by this service"
    ::= { callForwardingBusy 1 }

  bwDXSCallForwardingBusySPTable OBJECT-TYPE
    SYNTAX      SEQUENCE OF BwCallForwardingBusySPEntry
    MAX-ACCESS  not-accessible
    STATUS      current
    DESCRIPTION 
        "This table contains the counters for Call Forwarding Busy service measurements for service providers"
    ::= { callForwardingBusy 2 }

  bwDXSCallForwardingBusySPEntry OBJECT-TYPE
    SYNTAX      BwCallForwardingBusySPEntry
    MAX-ACCESS  not-accessible
    STATUS      current
    DESCRIPTION 
        "This row contains the counters for Call Forwarding Busy service measurements for a service provider"
    INDEX       { bwDXSCallForwardingBusySPIndex }
    ::= { bwDXSCallForwardingBusySPTable 1 }

  BwCallForwardingBusySPEntry ::= SEQUENCE {
    bwDXSCallForwardingBusySPIndex     Unsigned32,
    bwDXSCallForwardingBusySPID        DisplayString,
    bwDXSCFBSPNumForwarded             Counter32,
    bwDXSCFBSPNumPhoneActivations      Counter32,
    bwDXSCFBSPNumPhoneDeactivations    Counter32,
    bwDXSCFBSPDestinationChanged       Counter32,
    bwDXSCFBSPNumPhoneInterrogation    Counter32
  }

  bwDXSCallForwardingBusySPIndex OBJECT-TYPE
    SYNTAX      Unsigned32
    MAX-ACCESS  read-only
    STATUS      current
    DESCRIPTION 
        "This integer represents the a service provider index in the system"
    ::= { bwDXSCallForwardingBusySPEntry 1 }

  bwDXSCallForwardingBusySPID OBJECT-TYPE
    SYNTAX      DisplayString
    MAX-ACCESS  read-only
    STATUS      current
    DESCRIPTION 
        "This string represents a service provider ID"
    ::= { bwDXSCallForwardingBusySPEntry 2 }

  bwDXSCFBSPNumForwarded OBJECT-TYPE
    SYNTAX      Counter32
    MAX-ACCESS  read-write
    STATUS      current
    DESCRIPTION 
        "This counter reflects the number of times a call is forwarded by this service by a service provider"
    ::= { bwDXSCallForwardingBusySPEntry 3 }

  bwDXSCFBSPNumPhoneActivations OBJECT-TYPE
    SYNTAX      Counter32
    MAX-ACCESS  read-write
    STATUS      current
    DESCRIPTION 
        "Number of times CFB has been activated via FAC for users in a given service provider"
    ::= { bwDXSCallForwardingBusySPEntry 4 }

  bwDXSCFBSPNumPhoneDeactivations OBJECT-TYPE
    SYNTAX      Counter32
    MAX-ACCESS  read-write
    STATUS      current
    DESCRIPTION 
        "Number of times CFB has been deactivated via FAC for users in a given service provider"
    ::= { bwDXSCallForwardingBusySPEntry 5 }

  bwDXSCFBSPDestinationChanged OBJECT-TYPE
    SYNTAX      Counter32
    MAX-ACCESS  read-write
    STATUS      current
    DESCRIPTION 
        "Number of times CFB destination has been changed, by FAC only for a given service provider"
    ::= { bwDXSCallForwardingBusySPEntry 6 }

  bwDXSCFBSPNumPhoneInterrogation OBJECT-TYPE
    SYNTAX      Counter32
    MAX-ACCESS  read-write
    STATUS      current
    DESCRIPTION 
        "This is the number of times CFB has been interrogated via FAC for users in a given service provider."
    ::= { bwDXSCallForwardingBusySPEntry 7 }

  bwDXSCFBNumPhoneActivations OBJECT-TYPE
    SYNTAX      Counter32
    MAX-ACCESS  read-write
    STATUS      current
    DESCRIPTION 
        "Total number of times CFB has been activated via FAC"
    ::= { callForwardingBusy 3 }

  bwDXSCFBNumPhoneDeactivations OBJECT-TYPE
    SYNTAX      Counter32
    MAX-ACCESS  read-write
    STATUS      current
    DESCRIPTION 
        "Total number of times CFB has been deactivated via FAC"
    ::= { callForwardingBusy 4 }

  bwDXSCFBDestinationChanged OBJECT-TYPE
    SYNTAX      Counter32
    MAX-ACCESS  read-write
    STATUS      current
    DESCRIPTION 
        "Incremented whenever a user changes the CFB destination via FAC"
    ::= { callForwardingBusy 5 }

  bwDXSCallForwardingBusyGroupTable OBJECT-TYPE
    SYNTAX      SEQUENCE OF BwCallForwardingBusyGroupEntry
    MAX-ACCESS  not-accessible
    STATUS      current
    DESCRIPTION 
        "This table contains the counters for Call Forwarding Busy service measurements for groups"
    ::= { callForwardingBusy 6 }

  bwDXSCallForwardingBusyGroupEntry OBJECT-TYPE
    SYNTAX      BwCallForwardingBusyGroupEntry
    MAX-ACCESS  not-accessible
    STATUS      current
    DESCRIPTION 
        "This row contains the counters for Call Forwarding Busy service measurements for a group"
    INDEX       { bwDXSCallForwardingBusyGroupIndex }
    ::= { bwDXSCallForwardingBusyGroupTable 1 }

  BwCallForwardingBusyGroupEntry ::= SEQUENCE {
    bwDXSCallForwardingBusyGroupIndex      Unsigned32,
    bwDXSCallForwardingBusyGroupID         DisplayString,
    bwDXSCFBGroupNumForwarded              Counter32,
    bwDXSCFBGroupNumPhoneActivations       Counter32,
    bwDXSCFBGroupNumPhoneDeactivations     Counter32,
    bwDXSCFBGroupDestinationChanged        Counter32,
    bwDXSCFBGroupNumPhoneInterrogation     Counter32
  }

  bwDXSCallForwardingBusyGroupIndex OBJECT-TYPE
    SYNTAX      Unsigned32
    MAX-ACCESS  read-only
    STATUS      current
    DESCRIPTION 
        "This integer represents the a group index in the system"
    ::= { bwDXSCallForwardingBusyGroupEntry 1 }

  bwDXSCallForwardingBusyGroupID OBJECT-TYPE
    SYNTAX      DisplayString
    MAX-ACCESS  read-only
    STATUS      current
    DESCRIPTION 
        "This string represents a group ID"
    ::= { bwDXSCallForwardingBusyGroupEntry 2 }

  bwDXSCFBGroupNumForwarded OBJECT-TYPE
    SYNTAX      Counter32
    MAX-ACCESS  read-write
    STATUS      current
    DESCRIPTION 
        "This counter reflects the number of times a call is forwarded by this service by a group"
    ::= { bwDXSCallForwardingBusyGroupEntry 3 }

  bwDXSCFBGroupNumPhoneActivations OBJECT-TYPE
    SYNTAX      Counter32
    MAX-ACCESS  read-write
    STATUS      current
    DESCRIPTION 
        "Number of times CFB has been activated via FAC for users in a given group"
    ::= { bwDXSCallForwardingBusyGroupEntry 4 }

  bwDXSCFBGroupNumPhoneDeactivations OBJECT-TYPE
    SYNTAX      Counter32
    MAX-ACCESS  read-write
    STATUS      current
    DESCRIPTION 
        "Number of times CFB has been deactivated via FAC for users in a given group"
    ::= { bwDXSCallForwardingBusyGroupEntry 5 }

  bwDXSCFBGroupDestinationChanged OBJECT-TYPE
    SYNTAX      Counter32
    MAX-ACCESS  read-write
    STATUS      current
    DESCRIPTION 
        "Number of times CFB destination has been changed, by FAC only for a given group"
    ::= { bwDXSCallForwardingBusyGroupEntry 6 }

  bwDXSCFBGroupNumPhoneInterrogation OBJECT-TYPE
    SYNTAX      Counter32
    MAX-ACCESS  read-write
    STATUS      current
    DESCRIPTION 
        "This is the number of times CFB has been interrogated via FAC for users in a given group."
    ::= { bwDXSCallForwardingBusyGroupEntry 7 }

  bwDXSCFBNumPhoneInterrogation OBJECT-TYPE
    SYNTAX      Counter32
    MAX-ACCESS  read-write
    STATUS      current
    DESCRIPTION 
        "This is the number of times CFB has been interrogated via FAC."
    ::= { callForwardingBusy 7 }

  bwDXSCFNANumForwarded OBJECT-TYPE
    SYNTAX      Counter32
    MAX-ACCESS  read-write
    STATUS      current
    DESCRIPTION 
        "This counter reflects the number of times a call is forwarded by this service"
    ::= { callForwardingNoAnswer 1 }

  bwDXSCallForwardingNoAnswerSPTable OBJECT-TYPE
    SYNTAX      SEQUENCE OF BwCallForwardingNoAnswerSPEntry
    MAX-ACCESS  not-accessible
    STATUS      current
    DESCRIPTION 
        "This table contains the counters for Call Forwarding No Answer service measurements for service providers"
    ::= { callForwardingNoAnswer 2 }

  bwDXSCallForwardingNoAnswerSPEntry OBJECT-TYPE
    SYNTAX      BwCallForwardingNoAnswerSPEntry
    MAX-ACCESS  not-accessible
    STATUS      current
    DESCRIPTION 
        "This row contains the counters for Call Forwarding No Answer service measurements for a service provider"
    INDEX       { bwDXSCallForwardingNoAnswerSPIndex }
    ::= { bwDXSCallForwardingNoAnswerSPTable 1 }

  BwCallForwardingNoAnswerSPEntry ::= SEQUENCE {
    bwDXSCallForwardingNoAnswerSPIndex     Integer32,
    bwDXSCallForwardingNoAnswerSPID        DisplayString,
    bwDXSCFNASPNumForwarded                Counter32,
    bwDXSCFNASPDestinationChanged          Counter32,
    bwDXSCFNASPNumPhoneActivations         Counter32,
    bwDXSCFNASPNumPhoneDeactivations       Counter32,
    bwDXSCFNASPNumPhoneInterrogation       Counter32
  }

  bwDXSCallForwardingNoAnswerSPIndex OBJECT-TYPE
    SYNTAX      Integer32 (-2147483648..2147483647)
    MAX-ACCESS  read-only
    STATUS      current
    DESCRIPTION 
        "This integer represents the a service provider index in the system"
    ::= { bwDXSCallForwardingNoAnswerSPEntry 1 }

  bwDXSCallForwardingNoAnswerSPID OBJECT-TYPE
    SYNTAX      DisplayString
    MAX-ACCESS  read-only
    STATUS      current
    DESCRIPTION 
        "This string represents a service provider ID"
    ::= { bwDXSCallForwardingNoAnswerSPEntry 2 }

  bwDXSCFNASPNumForwarded OBJECT-TYPE
    SYNTAX      Counter32
    MAX-ACCESS  read-write
    STATUS      current
    DESCRIPTION 
        "This counter reflects the number of times a call is forwarded by this service by a service provider"
    ::= { bwDXSCallForwardingNoAnswerSPEntry 3 }

  bwDXSCFNASPDestinationChanged OBJECT-TYPE
    SYNTAX      Counter32
    MAX-ACCESS  read-write
    STATUS      current
    DESCRIPTION 
        "Number of times CFNA destination has been changed, by FAC only for a given service provider"
    ::= { bwDXSCallForwardingNoAnswerSPEntry 4 }

  bwDXSCFNASPNumPhoneActivations OBJECT-TYPE
    SYNTAX      Counter32
    MAX-ACCESS  read-write
    STATUS      current
    DESCRIPTION 
        "Number of times CFNA has been activated via FAC for users in a given service provider"
    ::= { bwDXSCallForwardingNoAnswerSPEntry 5 }

  bwDXSCFNASPNumPhoneDeactivations OBJECT-TYPE
    SYNTAX      Counter32
    MAX-ACCESS  read-write
    STATUS      current
    DESCRIPTION 
        "Number of times CFNA has been deactivated via FAC for users in a given service provider"
    ::= { bwDXSCallForwardingNoAnswerSPEntry 6 }

  bwDXSCFNASPNumPhoneInterrogation OBJECT-TYPE
    SYNTAX      Counter32
    MAX-ACCESS  read-write
    STATUS      current
    DESCRIPTION 
        "This is the number of times CFNA has been interrogated via FAC for users in a given service provider."
    ::= { bwDXSCallForwardingNoAnswerSPEntry 7 }

  bwDXSCFNADestinationChanged OBJECT-TYPE
    SYNTAX      Counter32
    MAX-ACCESS  read-write
    STATUS      current
    DESCRIPTION 
        "Incremented whenever a user changes the CFNA destination via FAC"
    ::= { callForwardingNoAnswer 3 }

  bwDXSCFNANumPhoneActivations OBJECT-TYPE
    SYNTAX      Counter32
    MAX-ACCESS  read-write
    STATUS      current
    DESCRIPTION 
        "Total number of times CFNA has been activated via FAC"
    ::= { callForwardingNoAnswer 4 }

  bwDXSCFNANumPhoneDeactivations OBJECT-TYPE
    SYNTAX      Counter32
    MAX-ACCESS  read-write
    STATUS      current
    DESCRIPTION 
        "Total number of times CFNA has been deactivated via FAC"
    ::= { callForwardingNoAnswer 5 }

  bwDXSCallForwardingNoAnswerGroupTable OBJECT-TYPE
    SYNTAX      SEQUENCE OF BwCallForwardingNoAnswerGroupEntry
    MAX-ACCESS  not-accessible
    STATUS      current
    DESCRIPTION 
        "This table contains the counters for Call Forwarding No Answer service measurements for groups"
    ::= { callForwardingNoAnswer 6 }

  bwDXSCallForwardingNoAnswerGroupEntry OBJECT-TYPE
    SYNTAX      BwCallForwardingNoAnswerGroupEntry
    MAX-ACCESS  not-accessible
    STATUS      current
    DESCRIPTION 
        "This row contains the counters for Call Forwarding No Answer service measurements for a group"
    INDEX       { bwDXSCallForwardingNoAnswerGroupIndex }
    ::= { bwDXSCallForwardingNoAnswerGroupTable 1 }

  BwCallForwardingNoAnswerGroupEntry ::= SEQUENCE {
    bwDXSCallForwardingNoAnswerGroupIndex  Integer32,
    bwDXSCallForwardingNoAnswerGroupID     DisplayString,
    bwDXSCFNAGroupNumForwarded             Counter32,
    bwDXSCFNAGroupDestinationChanged       Counter32,
    bwDXSCFNAGroupNumPhoneActivations      Counter32,
    bwDXSCFNAGroupNumPhoneDeactivations    Counter32,
    bwDXSCFNAGroupNumPhoneInterrogation    Counter32
  }

  bwDXSCallForwardingNoAnswerGroupIndex OBJECT-TYPE
    SYNTAX      Integer32 (-2147483648..2147483647)
    MAX-ACCESS  read-only
    STATUS      current
    DESCRIPTION 
        "This integer represents the a group index in the system"
    ::= { bwDXSCallForwardingNoAnswerGroupEntry 1 }

  bwDXSCallForwardingNoAnswerGroupID OBJECT-TYPE
    SYNTAX      DisplayString
    MAX-ACCESS  read-only
    STATUS      current
    DESCRIPTION 
        "This string represents a group ID"
    ::= { bwDXSCallForwardingNoAnswerGroupEntry 2 }

  bwDXSCFNAGroupNumForwarded OBJECT-TYPE
    SYNTAX      Counter32
    MAX-ACCESS  read-write
    STATUS      current
    DESCRIPTION 
        "This counter reflects the number of times a call is forwarded by this service by a group"
    ::= { bwDXSCallForwardingNoAnswerGroupEntry 3 }

  bwDXSCFNAGroupDestinationChanged OBJECT-TYPE
    SYNTAX      Counter32
    MAX-ACCESS  read-write
    STATUS      current
    DESCRIPTION 
        "Number of times CFNA destination has been changed, by FAC only for a given group"
    ::= { bwDXSCallForwardingNoAnswerGroupEntry 4 }

  bwDXSCFNAGroupNumPhoneActivations OBJECT-TYPE
    SYNTAX      Counter32
    MAX-ACCESS  read-write
    STATUS      current
    DESCRIPTION 
        "Number of times CFNA has been activated via FAC for users in a given group"
    ::= { bwDXSCallForwardingNoAnswerGroupEntry 5 }

  bwDXSCFNAGroupNumPhoneDeactivations OBJECT-TYPE
    SYNTAX      Counter32
    MAX-ACCESS  read-write
    STATUS      current
    DESCRIPTION 
        "Number of times CFNA has been deactivated via FAC for users in a given group"
    ::= { bwDXSCallForwardingNoAnswerGroupEntry 6 }

  bwDXSCFNAGroupNumPhoneInterrogation OBJECT-TYPE
    SYNTAX      Counter32
    MAX-ACCESS  read-write
    STATUS      current
    DESCRIPTION 
        "This is the number of times CFNA has been interrogated via FAC for users in a given group."
    ::= { bwDXSCallForwardingNoAnswerGroupEntry 7 }

  bwDXSCFNANumPhoneInterrogation OBJECT-TYPE
    SYNTAX      Counter32
    MAX-ACCESS  read-write
    STATUS      current
    DESCRIPTION 
        "This is the number of times CFNA has been interrogated via FAC."
    ::= { callForwardingNoAnswer 7 }

  bwDXSCallNotifyNumNotifications OBJECT-TYPE
    SYNTAX      Counter32
    MAX-ACCESS  read-write
    STATUS      current
    DESCRIPTION 
        "This counter reflects the number of times a criteria evaluates successfully and the
         service executes"
    ::= { callNotify 1 }

  bwDXSCallNotifySPTable OBJECT-TYPE
    SYNTAX      SEQUENCE OF BwCallNotifySPEntry
    MAX-ACCESS  not-accessible
    STATUS      current
    DESCRIPTION 
        "This table contains the counters for Call Notify service measurements for service providers"
    ::= { callNotify 2 }

  bwDXSCallNotifySPEntry OBJECT-TYPE
    SYNTAX      BwCallNotifySPEntry
    MAX-ACCESS  not-accessible
    STATUS      current
    DESCRIPTION 
        "This row contains the counters for Call Notify service measurements for a service provider"
    INDEX       { bwDXSCallNotifySPIndex }
    ::= { bwDXSCallNotifySPTable 1 }

  BwCallNotifySPEntry ::= SEQUENCE {
    bwDXSCallNotifySPIndex             Unsigned32,
    bwDXSCallNotifySPID                DisplayString,
    bwDXSCallNotifySPNumNotifications  Counter32
  }

  bwDXSCallNotifySPIndex OBJECT-TYPE
    SYNTAX      Unsigned32
    MAX-ACCESS  read-only
    STATUS      current
    DESCRIPTION 
        "This integer represents the a service provider index in the system"
    ::= { bwDXSCallNotifySPEntry 1 }

  bwDXSCallNotifySPID OBJECT-TYPE
    SYNTAX      DisplayString
    MAX-ACCESS  read-only
    STATUS      current
    DESCRIPTION 
        "This string represents a service provider ID"
    ::= { bwDXSCallNotifySPEntry 2 }

  bwDXSCallNotifySPNumNotifications OBJECT-TYPE
    SYNTAX      Counter32
    MAX-ACCESS  read-write
    STATUS      current
    DESCRIPTION 
        "This counter reflects the number of times a criteria evaluates successfully and the service executes by a service provider"
    ::= { bwDXSCallNotifySPEntry 3 }

  bwDXSCallNotifyGroupTable OBJECT-TYPE
    SYNTAX      SEQUENCE OF BwCallNotifyGroupEntry
    MAX-ACCESS  not-accessible
    STATUS      current
    DESCRIPTION 
        "This table contains the counters for Call Notify service measurements for groups"
    ::= { callNotify 3 }

  bwDXSCallNotifyGroupEntry OBJECT-TYPE
    SYNTAX      BwCallNotifyGroupEntry
    MAX-ACCESS  not-accessible
    STATUS      current
    DESCRIPTION 
        "This row contains the counters for Call Notify service measurements for a group"
    INDEX       { bwDXSCallNotifyGroupIndex }
    ::= { bwDXSCallNotifyGroupTable 1 }

  BwCallNotifyGroupEntry ::= SEQUENCE {
    bwDXSCallNotifyGroupIndex              Unsigned32,
    bwDXSCallNotifyGroupID                 DisplayString,
    bwDXSCallNotifyGroupNumNotifications   Counter32
  }

  bwDXSCallNotifyGroupIndex OBJECT-TYPE
    SYNTAX      Unsigned32
    MAX-ACCESS  read-only
    STATUS      current
    DESCRIPTION 
        "This integer represents the a group index in the system"
    ::= { bwDXSCallNotifyGroupEntry 1 }

  bwDXSCallNotifyGroupID OBJECT-TYPE
    SYNTAX      DisplayString
    MAX-ACCESS  read-only
    STATUS      current
    DESCRIPTION 
        "This string represents a group ID"
    ::= { bwDXSCallNotifyGroupEntry 2 }

  bwDXSCallNotifyGroupNumNotifications OBJECT-TYPE
    SYNTAX      Counter32
    MAX-ACCESS  read-write
    STATUS      current
    DESCRIPTION 
        "This counter reflects the number of times a criteria evaluates successfully and the service executes by a group"
    ::= { bwDXSCallNotifyGroupEntry 3 }

  bwDXSCallParkNumAttempts OBJECT-TYPE
    SYNTAX      Counter32
    MAX-ACCESS  read-write
    STATUS      current
    DESCRIPTION 
        "This counter reflects the number of times a user attempts to park a call"
    ::= { callPark 1 }

  bwDXSCallParkNumFailures OBJECT-TYPE
    SYNTAX      Counter32
    MAX-ACCESS  read-write
    STATUS      current
    DESCRIPTION 
        "This counter reflects the number of failed attempts to park a call"
    ::= { callPark 2 }

  bwDXSCallParkNumRetrieveAttempts OBJECT-TYPE
    SYNTAX      Counter32
    MAX-ACCESS  read-write
    STATUS      current
    DESCRIPTION 
        "This counter reflects the number of times a user attempts to retrieve a parked call"
    ::= { callPark 3 }

  bwDXSCallParkNumRetrieveFailures OBJECT-TYPE
    SYNTAX      Counter32
    MAX-ACCESS  read-write
    STATUS      current
    DESCRIPTION 
        "This counter reflects the number of times an attempt to retrieve a parked call fails"
    ::= { callPark 4 }

  bwDXSCallParkSPTable OBJECT-TYPE
    SYNTAX      SEQUENCE OF BwCallParkSPEntry
    MAX-ACCESS  not-accessible
    STATUS      current
    DESCRIPTION 
        "This table contains the counters for Call Park service measurements for service providers"
    ::= { callPark 5 }

  bwDXSCallParkSPEntry OBJECT-TYPE
    SYNTAX      BwCallParkSPEntry
    MAX-ACCESS  not-accessible
    STATUS      current
    DESCRIPTION 
        "This row contains the counters for Call Park service measurements for a service provider"
    INDEX       { bwDXSCallParkSPIndex }
    ::= { bwDXSCallParkSPTable 1 }

  BwCallParkSPEntry ::= SEQUENCE {
    bwDXSCallParkSPIndex                   Unsigned32,
    bwDXSCallParkSPID                      DisplayString,
    bwDXSCallParkSPNumAttempts             Counter32,
    bwDXSCallParkSPNumFailures             Counter32,
    bwDXSCallParkSPNumRetrieveAttempts     Counter32,
    bwDXSCallParkSPNumRetrieveFailures     Counter32
  }

  bwDXSCallParkSPIndex OBJECT-TYPE
    SYNTAX      Unsigned32
    MAX-ACCESS  read-only
    STATUS      current
    DESCRIPTION 
        "This integer represents the a service provider index in the system"
    ::= { bwDXSCallParkSPEntry 1 }

  bwDXSCallParkSPID OBJECT-TYPE
    SYNTAX      DisplayString
    MAX-ACCESS  read-only
    STATUS      current
    DESCRIPTION 
        "This string represents a service provider ID"
    ::= { bwDXSCallParkSPEntry 2 }

  bwDXSCallParkSPNumAttempts OBJECT-TYPE
    SYNTAX      Counter32
    MAX-ACCESS  read-write
    STATUS      current
    DESCRIPTION 
        "This counter reflects the number of times a user attempts to park a call by a service provider"
    ::= { bwDXSCallParkSPEntry 3 }

  bwDXSCallParkSPNumFailures OBJECT-TYPE
    SYNTAX      Counter32
    MAX-ACCESS  read-write
    STATUS      current
    DESCRIPTION 
        "This counter reflects the number of failed attempts to park a call by a service provider"
    ::= { bwDXSCallParkSPEntry 4 }

  bwDXSCallParkSPNumRetrieveAttempts OBJECT-TYPE
    SYNTAX      Counter32
    MAX-ACCESS  read-write
    STATUS      current
    DESCRIPTION 
        "This counter reflects the number of times a user attempts to retrieve a parked call by a service provider"
    ::= { bwDXSCallParkSPEntry 5 }

  bwDXSCallParkSPNumRetrieveFailures OBJECT-TYPE
    SYNTAX      Counter32
    MAX-ACCESS  read-write
    STATUS      current
    DESCRIPTION 
        "This counter reflects the number of times an attempt to retrieve a parked call fails by a service provider"
    ::= { bwDXSCallParkSPEntry 6 }

  bwDXSCallParkGroupTable OBJECT-TYPE
    SYNTAX      SEQUENCE OF BwCallParkGroupEntry
    MAX-ACCESS  not-accessible
    STATUS      current
    DESCRIPTION 
        "This table contains the counters for Call Park service measurements for groups"
    ::= { callPark 6 }

  bwDXSCallParkGroupEntry OBJECT-TYPE
    SYNTAX      BwCallParkGroupEntry
    MAX-ACCESS  not-accessible
    STATUS      current
    DESCRIPTION 
        "This row contains the counters for Call Park service measurements for a group"
    INDEX       { bwDXSCallParkGroupIndex }
    ::= { bwDXSCallParkGroupTable 1 }

  BwCallParkGroupEntry ::= SEQUENCE {
    bwDXSCallParkGroupIndex                Unsigned32,
    bwDXSCallParkGroupID                   DisplayString,
    bwDXSCallParkGroupNumAttempts          Counter32,
    bwDXSCallParkGroupNumFailures          Counter32,
    bwDXSCallParkGroupNumRetrieveAttempts  Counter32,
    bwDXSCallParkGroupNumRetrieveFailures  Counter32
  }

  bwDXSCallParkGroupIndex OBJECT-TYPE
    SYNTAX      Unsigned32
    MAX-ACCESS  read-only
    STATUS      current
    DESCRIPTION 
        "This integer represents the a group index in the system"
    ::= { bwDXSCallParkGroupEntry 1 }

  bwDXSCallParkGroupID OBJECT-TYPE
    SYNTAX      DisplayString
    MAX-ACCESS  read-only
    STATUS      current
    DESCRIPTION 
        "This string represents a group ID"
    ::= { bwDXSCallParkGroupEntry 2 }

  bwDXSCallParkGroupNumAttempts OBJECT-TYPE
    SYNTAX      Counter32
    MAX-ACCESS  read-write
    STATUS      current
    DESCRIPTION 
        "This counter reflects the number of times a user attempts to park a call by a group"
    ::= { bwDXSCallParkGroupEntry 3 }

  bwDXSCallParkGroupNumFailures OBJECT-TYPE
    SYNTAX      Counter32
    MAX-ACCESS  read-write
    STATUS      current
    DESCRIPTION 
        "This counter reflects the number of failed attempts to park a call by a group"
    ::= { bwDXSCallParkGroupEntry 4 }

  bwDXSCallParkGroupNumRetrieveAttempts OBJECT-TYPE
    SYNTAX      Counter32
    MAX-ACCESS  read-write
    STATUS      current
    DESCRIPTION 
        "This counter reflects the number of times a user attempts to retrieve a parked call by a group"
    ::= { bwDXSCallParkGroupEntry 5 }

  bwDXSCallParkGroupNumRetrieveFailures OBJECT-TYPE
    SYNTAX      Counter32
    MAX-ACCESS  read-write
    STATUS      current
    DESCRIPTION 
        "This counter reflects the number of times an attempt to retrieve a parked call fails by a group"
    ::= { bwDXSCallParkGroupEntry 6 }

  bwDXSCallPickupNumAttempts OBJECT-TYPE
    SYNTAX      Counter32
    MAX-ACCESS  read-write
    STATUS      current
    DESCRIPTION 
        "This counter reflects the number of user attempts to pick up an incoming call"
    ::= { callPickup 1 }

  bwDXSCallPickupNumFailures OBJECT-TYPE
    SYNTAX      Counter32
    MAX-ACCESS  read-write
    STATUS      current
    DESCRIPTION 
        "This counter reflects the number of failed attempts to pick up an incoming call"
    ::= { callPickup 2 }

  bwDXSCallPickupSPTable OBJECT-TYPE
    SYNTAX      SEQUENCE OF BwCallPickupSPEntry
    MAX-ACCESS  not-accessible
    STATUS      current
    DESCRIPTION 
        "This table contains the counters for Call Pickup service measurements for service providers"
    ::= { callPickup 3 }

  bwDXSCallPickupSPEntry OBJECT-TYPE
    SYNTAX      BwCallPickupSPEntry
    MAX-ACCESS  not-accessible
    STATUS      current
    DESCRIPTION 
        "This row contains the counters for Call Pickup service measurements for a service provider"
    INDEX       { bwDXSCallPickupSPIndex }
    ::= { bwDXSCallPickupSPTable 1 }

  BwCallPickupSPEntry ::= SEQUENCE {
    bwDXSCallPickupSPIndex         Unsigned32,
    bwDXSCallPickupSPID            DisplayString,
    bwDXSCallPickupSPNumAttempts   Counter32,
    bwDXSCallPickupSPNumFailures   Counter32
  }

  bwDXSCallPickupSPIndex OBJECT-TYPE
    SYNTAX      Unsigned32
    MAX-ACCESS  read-only
    STATUS      current
    DESCRIPTION 
        "This integer represents the a service provider index in the system"
    ::= { bwDXSCallPickupSPEntry 1 }

  bwDXSCallPickupSPID OBJECT-TYPE
    SYNTAX      DisplayString
    MAX-ACCESS  read-only
    STATUS      current
    DESCRIPTION 
        "This string represents a service provider ID"
    ::= { bwDXSCallPickupSPEntry 2 }

  bwDXSCallPickupSPNumAttempts OBJECT-TYPE
    SYNTAX      Counter32
    MAX-ACCESS  read-write
    STATUS      current
    DESCRIPTION 
        "This counter reflects the number of user attempts to pick up an incoming call by a service provider"
    ::= { bwDXSCallPickupSPEntry 3 }

  bwDXSCallPickupSPNumFailures OBJECT-TYPE
    SYNTAX      Counter32
    MAX-ACCESS  read-write
    STATUS      current
    DESCRIPTION 
        "This counter reflects the number of failed attempts to pick up an incoming call by a service provider"
    ::= { bwDXSCallPickupSPEntry 4 }

  bwDXSCallPickupGroupTable OBJECT-TYPE
    SYNTAX      SEQUENCE OF BwCallPickupGroupEntry
    MAX-ACCESS  not-accessible
    STATUS      current
    DESCRIPTION 
        "This table contains the counters for Call Pickup service measurements for groups"
    ::= { callPickup 4 }

  bwDXSCallPickupGroupEntry OBJECT-TYPE
    SYNTAX      BwCallPickupGroupEntry
    MAX-ACCESS  not-accessible
    STATUS      current
    DESCRIPTION 
        "This row contains the counters for Call Pickup service measurements for a group"
    INDEX       { bwDXSCallPickupGroupIndex }
    ::= { bwDXSCallPickupGroupTable 1 }

  BwCallPickupGroupEntry ::= SEQUENCE {
    bwDXSCallPickupGroupIndex          Unsigned32,
    bwDXSCallPickupGroupID             DisplayString,
    bwDXSCallPickupGroupNumAttempts    Counter32,
    bwDXSCallPickupGroupNumFailures    Counter32
  }

  bwDXSCallPickupGroupIndex OBJECT-TYPE
    SYNTAX      Unsigned32
    MAX-ACCESS  read-only
    STATUS      current
    DESCRIPTION 
        "This integer represents the a Group index in the system"
    ::= { bwDXSCallPickupGroupEntry 1 }

  bwDXSCallPickupGroupID OBJECT-TYPE
    SYNTAX      DisplayString
    MAX-ACCESS  read-only
    STATUS      current
    DESCRIPTION 
        "This string represents a Group ID"
    ::= { bwDXSCallPickupGroupEntry 2 }

  bwDXSCallPickupGroupNumAttempts OBJECT-TYPE
    SYNTAX      Counter32
    MAX-ACCESS  read-write
    STATUS      current
    DESCRIPTION 
        "This counter reflects the number of user attempts to pick up an incoming call by a Group"
    ::= { bwDXSCallPickupGroupEntry 3 }

  bwDXSCallPickupGroupNumFailures OBJECT-TYPE
    SYNTAX      Counter32
    MAX-ACCESS  read-write
    STATUS      current
    DESCRIPTION 
        "This counter reflects the number of failed attempts to pick up an incoming call by a Group"
    ::= { bwDXSCallPickupGroupEntry 4 }

  bwDXSCallReturnNumReturns OBJECT-TYPE
    SYNTAX      Counter32
    MAX-ACCESS  read-write
    STATUS      current
    DESCRIPTION 
        "This counter reflects the number of times this service is executed"
    ::= { callReturn 1 }

  bwDXSCallReturnSPTable OBJECT-TYPE
    SYNTAX      SEQUENCE OF BwCallReturnSPEntry
    MAX-ACCESS  not-accessible
    STATUS      current
    DESCRIPTION 
        "This table contains the counters for Call Return service measurements for service providers"
    ::= { callReturn 2 }

  bwDXSCallReturnSPEntry OBJECT-TYPE
    SYNTAX      BwCallReturnSPEntry
    MAX-ACCESS  not-accessible
    STATUS      current
    DESCRIPTION 
        "This row contains the counters for Call Return service measurements for a service provider"
    INDEX       { bwDXSCallReturnSPIndex }
    ::= { bwDXSCallReturnSPTable 1 }

  BwCallReturnSPEntry ::= SEQUENCE {
    bwDXSCallReturnSPIndex         Unsigned32,
    bwDXSCallReturnSPID            DisplayString,
    bwDXSCallReturnSPNumReturns    Counter32
  }

  bwDXSCallReturnSPIndex OBJECT-TYPE
    SYNTAX      Unsigned32
    MAX-ACCESS  read-only
    STATUS      current
    DESCRIPTION 
        "This integer represents the a service provider index in the system"
    ::= { bwDXSCallReturnSPEntry 1 }

  bwDXSCallReturnSPID OBJECT-TYPE
    SYNTAX      DisplayString
    MAX-ACCESS  read-only
    STATUS      current
    DESCRIPTION 
        "This string represents a service provider ID"
    ::= { bwDXSCallReturnSPEntry 2 }

  bwDXSCallReturnSPNumReturns OBJECT-TYPE
    SYNTAX      Counter32
    MAX-ACCESS  read-write
    STATUS      current
    DESCRIPTION 
        "This counter reflects the number of times this service is executed by a service provider"
    ::= { bwDXSCallReturnSPEntry 3 }

  bwDXSCallReturnGroupTable OBJECT-TYPE
    SYNTAX      SEQUENCE OF BwCallReturnGroupEntry
    MAX-ACCESS  not-accessible
    STATUS      current
    DESCRIPTION 
        "This table contains the counters for Call Return service measurements for groups"
    ::= { callReturn 3 }

  bwDXSCallReturnGroupEntry OBJECT-TYPE
    SYNTAX      BwCallReturnGroupEntry
    MAX-ACCESS  not-accessible
    STATUS      current
    DESCRIPTION 
        "This row contains the counters for Call Return service measurements for a group"
    INDEX       { bwDXSCallReturnGroupIndex }
    ::= { bwDXSCallReturnGroupTable 1 }

  BwCallReturnGroupEntry ::= SEQUENCE {
    bwDXSCallReturnGroupIndex          Unsigned32,
    bwDXSCallReturnGroupID             DisplayString,
    bwDXSCallReturnGroupNumReturns     Counter32
  }

  bwDXSCallReturnGroupIndex OBJECT-TYPE
    SYNTAX      Unsigned32
    MAX-ACCESS  read-only
    STATUS      current
    DESCRIPTION 
        "This integer represents the a group index in the system"
    ::= { bwDXSCallReturnGroupEntry 1 }

  bwDXSCallReturnGroupID OBJECT-TYPE
    SYNTAX      DisplayString
    MAX-ACCESS  read-only
    STATUS      current
    DESCRIPTION 
        "This string represents a group ID"
    ::= { bwDXSCallReturnGroupEntry 2 }

  bwDXSCallReturnGroupNumReturns OBJECT-TYPE
    SYNTAX      Counter32
    MAX-ACCESS  read-write
    STATUS      current
    DESCRIPTION 
        "This counter reflects the number of times this service is executed by a group"
    ::= { bwDXSCallReturnGroupEntry 3 }

  bwDXSCommPilotCallMgrNumDial OBJECT-TYPE
    SYNTAX      Counter32
    MAX-ACCESS  read-write
    STATUS      current
    DESCRIPTION 
        "This counter reflects the number of dial requests from a CommPilot Call Mgr that
         results in an outgoing call"
    ::= { commPilotCallManager 1 }

  bwDXSCommPilotCallMgrNumAnswer OBJECT-TYPE
    SYNTAX      Counter32
    MAX-ACCESS  read-write
    STATUS      current
    DESCRIPTION 
        "This counter reflects the number of times an incoming call being answered from the
         CommPilot Call Mgr results in that call being answered"
    ::= { commPilotCallManager 2 }

  bwDXSCommPilotCallMgrNumRelease OBJECT-TYPE
    SYNTAX      Counter32
    MAX-ACCESS  read-write
    STATUS      current
    DESCRIPTION 
        "This counter reflects the number of times a Release request from the CommPilot Call
         Mgr results in the call being released"
    ::= { commPilotCallManager 3 }

  bwDXSCommPilotCallMgrNumHold OBJECT-TYPE
    SYNTAX      Counter32
    MAX-ACCESS  read-write
    STATUS      current
    DESCRIPTION 
        "This counter reflects the number of times a Hold request from the CommPilot Call Mgr
         results in the call being held"
    ::= { commPilotCallManager 4 }

  bwDXSCommPilotCallMgrNumTransfer OBJECT-TYPE
    SYNTAX      Counter32
    MAX-ACCESS  read-write
    STATUS      current
    DESCRIPTION 
        "This counter reflects the number of times a Transfer request from the CommPilot Call
         Mgr results in the call being transferred"
    ::= { commPilotCallManager 5 }

  bwDXSCommPilotCallMgrNumConference OBJECT-TYPE
    SYNTAX      Counter32
    MAX-ACCESS  read-write
    STATUS      current
    DESCRIPTION 
        "This counter reflects the number of times a Conference request from the CommPilot
         Call Mgr results in two calls being conferenced"
    ::= { commPilotCallManager 6 }

  bwDXSCommPilotCallMgrNumTransferVM OBJECT-TYPE
    SYNTAX      Counter32
    MAX-ACCESS  read-write
    STATUS      current
    DESCRIPTION 
        "This counter reflects the number of times a user attempts to send a call to voicemail"
    ::= { commPilotCallManager 7 }

  bwDXSCommPilotCallManagerSPTable OBJECT-TYPE
    SYNTAX      SEQUENCE OF BwCommPilotCallManagerSPEntry
    MAX-ACCESS  not-accessible
    STATUS      current
    DESCRIPTION 
        "This table contains the counters for CommPilot Call Manager service measurements for service providers"
    ::= { commPilotCallManager 8 }

  bwDXSCommPilotCallManagerSPEntry OBJECT-TYPE
    SYNTAX      BwCommPilotCallManagerSPEntry
    MAX-ACCESS  not-accessible
    STATUS      current
    DESCRIPTION 
        "This row contains the counters for CommPilot Call Manager service measurements for a service provider"
    INDEX       { bwDXSCommPilotCallManagerSPIndex }
    ::= { bwDXSCommPilotCallManagerSPTable 1 }

  BwCommPilotCallManagerSPEntry ::= SEQUENCE {
    bwDXSCommPilotCallManagerSPIndex               Unsigned32,
    bwDXSCommPilotCallManagerSPID                  DisplayString,
    bwDXSCommPilotCallMgrSPNumDial                 Counter32,
    bwDXSCommPilotCallMgrSPNumAnswer               Counter32,
    bwDXSCommPilotCallMgrSPNumRelease              Counter32,
    bwDXSCommPilotCallMgrSPNumHold                 Counter32,
    bwDXSCommPilotCallMgrSPNumTransfer             Counter32,
    bwDXSCommPilotCallMgrSPNumConference           Counter32,
    bwDXSCommPilotCallMgrSPNumTransferVM           Counter32,
    bwDXSCommPilotCallMgrSPNumConferenceAnswer     Counter32,
    bwDXSCommPilotCallMgrSPNumConferenceHold       Counter32,
    bwDXSCommPilotCallMgrSPNumConferenceRelease    Counter32,
    bwDXSCommPilotCallMgrSPNumTransferCC           Counter32,
    bwDXSCommPilotCallMgrSPNumConferenceAdd        Counter32,
    bwDXSCommPilotCallMgrSPNumCallPark             Counter32,
    bwDXSCommPilotCallMgrSPNumGroupCallPark        Counter32,
    bwDXSCommPilotCallMgrSPNumCallParkRetrieve     Counter32
  }

  bwDXSCommPilotCallManagerSPIndex OBJECT-TYPE
    SYNTAX      Unsigned32
    MAX-ACCESS  read-only
    STATUS      current
    DESCRIPTION 
        "This integer represents the a service provider index in the system"
    ::= { bwDXSCommPilotCallManagerSPEntry 1 }

  bwDXSCommPilotCallManagerSPID OBJECT-TYPE
    SYNTAX      DisplayString
    MAX-ACCESS  read-only
    STATUS      current
    DESCRIPTION 
        "This string represents a service provider ID"
    ::= { bwDXSCommPilotCallManagerSPEntry 2 }

  bwDXSCommPilotCallMgrSPNumDial OBJECT-TYPE
    SYNTAX      Counter32
    MAX-ACCESS  read-write
    STATUS      current
    DESCRIPTION 
        "This counter reflects the number of dial requests from a CommPilot Call Mgr that results in an outgoing call by a service provider"
    ::= { bwDXSCommPilotCallManagerSPEntry 3 }

  bwDXSCommPilotCallMgrSPNumAnswer OBJECT-TYPE
    SYNTAX      Counter32
    MAX-ACCESS  read-write
    STATUS      current
    DESCRIPTION 
        "This counter reflects the number of times an incoming call being answered from the CommPilot Call Mgr results in that call being answered by a service provider"
    ::= { bwDXSCommPilotCallManagerSPEntry 4 }

  bwDXSCommPilotCallMgrSPNumRelease OBJECT-TYPE
    SYNTAX      Counter32
    MAX-ACCESS  read-write
    STATUS      current
    DESCRIPTION 
        "This counter reflects the number of times a Release request from the CommPilot Call Mgr results in the call being released by a service provider"
    ::= { bwDXSCommPilotCallManagerSPEntry 5 }

  bwDXSCommPilotCallMgrSPNumHold OBJECT-TYPE
    SYNTAX      Counter32
    MAX-ACCESS  read-write
    STATUS      current
    DESCRIPTION 
        "This counter reflects the number of times a Hold request from the CommPilot Call Mgr results in the call being held by a service provider"
    ::= { bwDXSCommPilotCallManagerSPEntry 6 }

  bwDXSCommPilotCallMgrSPNumTransfer OBJECT-TYPE
    SYNTAX      Counter32
    MAX-ACCESS  read-write
    STATUS      current
    DESCRIPTION 
        "This counter reflects the number of times a Transfer request from the CommPilot Call Mgr results in the call being transferred by a service provider"
    ::= { bwDXSCommPilotCallManagerSPEntry 7 }

  bwDXSCommPilotCallMgrSPNumConference OBJECT-TYPE
    SYNTAX      Counter32
    MAX-ACCESS  read-write
    STATUS      current
    DESCRIPTION 
        "This counter reflects the number of times a Conference request from the CommPilot Call Mgr results in two calls being conferenced by a service provider"
    ::= { bwDXSCommPilotCallManagerSPEntry 8 }

  bwDXSCommPilotCallMgrSPNumTransferVM OBJECT-TYPE
    SYNTAX      Counter32
    MAX-ACCESS  read-write
    STATUS      current
    DESCRIPTION 
        "This counter reflects the number of times a user attempts to send a call to voicemail by a service provider"
    ::= { bwDXSCommPilotCallManagerSPEntry 9 }

  bwDXSCommPilotCallMgrSPNumConferenceAnswer OBJECT-TYPE
    SYNTAX      Counter32
    MAX-ACCESS  read-write
    STATUS      current
    DESCRIPTION 
        "This counter reflects the number of times a held conference has been answered/retrieved from the CommPilot Call Mgr by a service provider"
    ::= { bwDXSCommPilotCallManagerSPEntry 10 }

  bwDXSCommPilotCallMgrSPNumConferenceHold OBJECT-TYPE
    SYNTAX      Counter32
    MAX-ACCESS  read-write
    STATUS      current
    DESCRIPTION 
        "This counter reflects the number of times a Conference has been held from the CommPilot Call Mgr by a service provider by the service provider"
    ::= { bwDXSCommPilotCallManagerSPEntry 11 }

  bwDXSCommPilotCallMgrSPNumConferenceRelease OBJECT-TYPE
    SYNTAX      Counter32
    MAX-ACCESS  read-write
    STATUS      current
    DESCRIPTION 
        "This counter reflects the number of times a Conference has been released from the CommPilot Call Mgr by a service provider by the service provider"
    ::= { bwDXSCommPilotCallManagerSPEntry 12 }

  bwDXSCommPilotCallMgrSPNumTransferCC OBJECT-TYPE
    SYNTAX      Counter32
    MAX-ACCESS  read-write
    STATUS      current
    DESCRIPTION 
        "This counter reflects the number of CAP callActions with actionType of xferCC which are received by the system per service provider"
    ::= { bwDXSCommPilotCallManagerSPEntry 13 }

  bwDXSCommPilotCallMgrSPNumConferenceAdd OBJECT-TYPE
    SYNTAX      Counter32
    MAX-ACCESS  read-write
    STATUS      current
    DESCRIPTION 
        "This counter reflects the number of CAP callActions with actionType of ConfAdd which are received by the system per service provider"
    ::= { bwDXSCommPilotCallManagerSPEntry 14 }

  bwDXSCommPilotCallMgrSPNumCallPark OBJECT-TYPE
    SYNTAX      Counter32
    MAX-ACCESS  read-write
    STATUS      current
    DESCRIPTION 
        "Number of CallPark call actions that have been received for a user under the service provider."
    ::= { bwDXSCommPilotCallManagerSPEntry 15 }

  bwDXSCommPilotCallMgrSPNumGroupCallPark OBJECT-TYPE
    SYNTAX      Counter32
    MAX-ACCESS  read-write
    STATUS      current
    DESCRIPTION 
        "Number of GroupCallPark call actions that have been received for a user under the service provider."
    ::= { bwDXSCommPilotCallManagerSPEntry 16 }

  bwDXSCommPilotCallMgrSPNumCallParkRetrieve OBJECT-TYPE
    SYNTAX      Counter32
    MAX-ACCESS  read-write
    STATUS      current
    DESCRIPTION 
        "Number of CallParkRetrieve call actions that have been received for a user under the service provider."
    ::= { bwDXSCommPilotCallManagerSPEntry 17 }

  bwDXSCommPilotCallMgrNumConferenceAnswer OBJECT-TYPE
    SYNTAX      Counter32
    MAX-ACCESS  read-write
    STATUS      current
    DESCRIPTION 
        "This counter reflects the number of times a held Conference has been answered/retrieved from the CommPilot Call Mgr"
    ::= { commPilotCallManager 9 }

  bwDXSCommPilotCallMgrNumConferenceHold OBJECT-TYPE
    SYNTAX      Counter32
    MAX-ACCESS  read-write
    STATUS      current
    DESCRIPTION 
        "This counter reflects the number of times a Conference has been held from the CommPilot Call Mgr"
    ::= { commPilotCallManager 10 }

  bwDXSCommPilotCallMgrNumConferenceRelease OBJECT-TYPE
    SYNTAX      Counter32
    MAX-ACCESS  read-write
    STATUS      current
    DESCRIPTION 
        "This counter reflects the number of times a Conference has been released from the CommPilot Call Mgr"
    ::= { commPilotCallManager 11 }

  bwDXSCommPilotCallManagerGroupTable OBJECT-TYPE
    SYNTAX      SEQUENCE OF BwCommPilotCallManagerGroupEntry
    MAX-ACCESS  not-accessible
    STATUS      current
    DESCRIPTION 
        "This table contains the counters for CommPilot Call Manager service measurements for service providers"
    ::= { commPilotCallManager 12 }

  bwDXSCommPilotCallManagerGroupEntry OBJECT-TYPE
    SYNTAX      BwCommPilotCallManagerGroupEntry
    MAX-ACCESS  not-accessible
    STATUS      current
    DESCRIPTION 
        "This row contains the counters for CommPilot Call Manager service measurements for a group"
    INDEX       { bwDXSCommPilotCallManagerGroupIndex }
    ::= { bwDXSCommPilotCallManagerGroupTable 1 }

  BwCommPilotCallManagerGroupEntry ::= SEQUENCE {
    bwDXSCommPilotCallManagerGroupIndex                Unsigned32,
    bwDXSCommPilotCallManagerGroupID                   DisplayString,
    bwDXSCommPilotCallMgrGroupNumDial                  Counter32,
    bwDXSCommPilotCallMgrGroupNumAnswer                Counter32,
    bwDXSCommPilotCallMgrGroupNumRelease               Counter32,
    bwDXSCommPilotCallMgrGroupNumHold                  Counter32,
    bwDXSCommPilotCallMgrGroupNumTransfer              Counter32,
    bwDXSCommPilotCallMgrGroupNumConference            Counter32,
    bwDXSCommPilotCallMgrGroupNumTransferVM            Counter32,
    bwDXSCommPilotCallMgrGroupNumConferenceAnswer      Counter32,
    bwDXSCommPilotCallMgrGroupNumConferenceHold        Counter32,
    bwDXSCommPilotCallMgrGroupNumConferenceRelease     Counter32,
    bwDXSCommPilotCallMgrGroupNumTransferCC            Counter32,
    bwDXSCommPilotCallMgrGroupNumConferenceAdd         Counter32,
    bwDXSCommPilotCallMgrGroupNumCallPark              Counter32,
    bwDXSCommPilotCallMgrGroupNumGroupCallPark         Counter32,
    bwDXSCommPilotCallMgrGroupNumCallParkRetrieve      Counter32
  }

  bwDXSCommPilotCallManagerGroupIndex OBJECT-TYPE
    SYNTAX      Unsigned32
    MAX-ACCESS  read-only
    STATUS      current
    DESCRIPTION 
        "This integer represents the a group index in the system"
    ::= { bwDXSCommPilotCallManagerGroupEntry 1 }

  bwDXSCommPilotCallManagerGroupID OBJECT-TYPE
    SYNTAX      DisplayString
    MAX-ACCESS  read-only
    STATUS      current
    DESCRIPTION 
        "This string represents a group ID"
    ::= { bwDXSCommPilotCallManagerGroupEntry 2 }

  bwDXSCommPilotCallMgrGroupNumDial OBJECT-TYPE
    SYNTAX      Counter32
    MAX-ACCESS  read-write
    STATUS      current
    DESCRIPTION 
        "This counter reflects the number of dial requests from a CommPilot Call Mgr that results in an outgoing call by a group"
    ::= { bwDXSCommPilotCallManagerGroupEntry 3 }

  bwDXSCommPilotCallMgrGroupNumAnswer OBJECT-TYPE
    SYNTAX      Counter32
    MAX-ACCESS  read-write
    STATUS      current
    DESCRIPTION 
        "This counter reflects the number of times an incoming call being answered from the CommPilot Call Mgr results in that call being answered by a group"
    ::= { bwDXSCommPilotCallManagerGroupEntry 4 }

  bwDXSCommPilotCallMgrGroupNumRelease OBJECT-TYPE
    SYNTAX      Counter32
    MAX-ACCESS  read-write
    STATUS      current
    DESCRIPTION 
        "This counter reflects the number of times a Release request from the CommPilot Call Mgr results in the call being released by a group"
    ::= { bwDXSCommPilotCallManagerGroupEntry 5 }

  bwDXSCommPilotCallMgrGroupNumHold OBJECT-TYPE
    SYNTAX      Counter32
    MAX-ACCESS  read-write
    STATUS      current
    DESCRIPTION 
        "This counter reflects the number of times a Hold request from the CommPilot Call Mgr results in the call being held by a group"
    ::= { bwDXSCommPilotCallManagerGroupEntry 6 }

  bwDXSCommPilotCallMgrGroupNumTransfer OBJECT-TYPE
    SYNTAX      Counter32
    MAX-ACCESS  read-write
    STATUS      current
    DESCRIPTION 
        "This counter reflects the number of times a Transfer request from the CommPilot Call Mgr results in the call being transferred by a group"
    ::= { bwDXSCommPilotCallManagerGroupEntry 7 }

  bwDXSCommPilotCallMgrGroupNumConference OBJECT-TYPE
    SYNTAX      Counter32
    MAX-ACCESS  read-write
    STATUS      current
    DESCRIPTION 
        "This counter reflects the number of times a Conference request from the CommPilot Call Mgr results in two calls being conferenced by a group"
    ::= { bwDXSCommPilotCallManagerGroupEntry 8 }

  bwDXSCommPilotCallMgrGroupNumTransferVM OBJECT-TYPE
    SYNTAX      Counter32
    MAX-ACCESS  read-write
    STATUS      current
    DESCRIPTION 
        "This counter reflects the number of times a user attempts to send a call to voicemail by a group"
    ::= { bwDXSCommPilotCallManagerGroupEntry 9 }

  bwDXSCommPilotCallMgrGroupNumConferenceAnswer OBJECT-TYPE
    SYNTAX      Counter32
    MAX-ACCESS  read-write
    STATUS      current
    DESCRIPTION 
        "This counter reflects the number of times a held conference has been answered/retrieved from the CommPilot Call Mgr by a group"
    ::= { bwDXSCommPilotCallManagerGroupEntry 10 }

  bwDXSCommPilotCallMgrGroupNumConferenceHold OBJECT-TYPE
    SYNTAX      Counter32
    MAX-ACCESS  read-write
    STATUS      current
    DESCRIPTION 
        "This counter reflects the number of times a Conference has been held from the CommPilot Call Mgr by a group"
    ::= { bwDXSCommPilotCallManagerGroupEntry 11 }

  bwDXSCommPilotCallMgrGroupNumConferenceRelease OBJECT-TYPE
    SYNTAX      Counter32
    MAX-ACCESS  read-write
    STATUS      current
    DESCRIPTION 
        "This counter reflects the number of times a Conference has been released from the CommPilot Call Mgr by a group"
    ::= { bwDXSCommPilotCallManagerGroupEntry 12 }

  bwDXSCommPilotCallMgrGroupNumTransferCC OBJECT-TYPE
    SYNTAX      Counter32
    MAX-ACCESS  read-write
    STATUS      current
    DESCRIPTION 
        "This counter reflects the number of CAP callActions with actionType of xferCC which are received by the system per group"
    ::= { bwDXSCommPilotCallManagerGroupEntry 13 }

  bwDXSCommPilotCallMgrGroupNumConferenceAdd OBJECT-TYPE
    SYNTAX      Counter32
    MAX-ACCESS  read-write
    STATUS      current
    DESCRIPTION 
        "This counter reflects the number of CAP callActions with actionType of ConfAdd which are received by the system per group"
    ::= { bwDXSCommPilotCallManagerGroupEntry 14 }

  bwDXSCommPilotCallMgrGroupNumCallPark OBJECT-TYPE
    SYNTAX      Counter32
    MAX-ACCESS  read-write
    STATUS      current
    DESCRIPTION 
        "Number of CallPark call actions that have been received for a user in the group."
    ::= { bwDXSCommPilotCallManagerGroupEntry 15 }

  bwDXSCommPilotCallMgrGroupNumGroupCallPark OBJECT-TYPE
    SYNTAX      Counter32
    MAX-ACCESS  read-write
    STATUS      current
    DESCRIPTION 
        "Number of GroupCallPark call actions that have been received for a user in the group."
    ::= { bwDXSCommPilotCallManagerGroupEntry 16 }

  bwDXSCommPilotCallMgrGroupNumCallParkRetrieve OBJECT-TYPE
    SYNTAX      Counter32
    MAX-ACCESS  read-write
    STATUS      current
    DESCRIPTION 
        "Number of CallParkRetrieve call actions that have been received for a user in the group."
    ::= { bwDXSCommPilotCallManagerGroupEntry 17 }

  bwDXSCommPilotCallMgrNumTransferCC OBJECT-TYPE
    SYNTAX      Counter32
    MAX-ACCESS  read-write
    STATUS      current
    DESCRIPTION 
        "This counter reflects the number of CAP callActions with actionType of xferCC which are received by the system"
    ::= { commPilotCallManager 13 }

  bwDXSCommPilotCallMgrNumConferenceAdd OBJECT-TYPE
    SYNTAX      Counter32
    MAX-ACCESS  read-write
    STATUS      current
    DESCRIPTION 
        "This counter reflects the number of CAP callActions with actionType of ConfAdd which are received by the system"
    ::= { commPilotCallManager 14 }

  bwDXSCommPilotCallMgrNumCallPark OBJECT-TYPE
    SYNTAX      Counter32
    MAX-ACCESS  read-write
    STATUS      current
    DESCRIPTION 
        "Number of CallPark call actions that have been received."
    ::= { commPilotCallManager 15 }

  bwDXSCommPilotCallMgrNumGroupCallPark OBJECT-TYPE
    SYNTAX      Counter32
    MAX-ACCESS  read-write
    STATUS      current
    DESCRIPTION 
        "Number of GroupCallPark call actions that have been received."
    ::= { commPilotCallManager 16 }

  bwDXSCommPilotCallMgrNumCallParkRetrieve OBJECT-TYPE
    SYNTAX      Counter32
    MAX-ACCESS  read-write
    STATUS      current
    DESCRIPTION 
        "Number of CallParkRetrieve call actions that have been received."
    ::= { commPilotCallManager 17 }

  bwDXSDoNotDisturbNumInvoked OBJECT-TYPE
    SYNTAX      Counter32
    MAX-ACCESS  read-write
    STATUS      current
    DESCRIPTION 
        "This counter reflects the number of times this service is triggered"
    ::= { doNotDisturb 1 }

  bwDXSDoNotDisturbSPTable OBJECT-TYPE
    SYNTAX      SEQUENCE OF BwDoNotDisturbSPEntry
    MAX-ACCESS  not-accessible
    STATUS      current
    DESCRIPTION 
        "This table contains the counters for Do Not Disturb service measurements for service providers"
    ::= { doNotDisturb 2 }

  bwDXSDoNotDisturbSPEntry OBJECT-TYPE
    SYNTAX      BwDoNotDisturbSPEntry
    MAX-ACCESS  not-accessible
    STATUS      current
    DESCRIPTION 
        "This row contains the counters for Do Not Disturb service measurements for a service provider"
    INDEX       { bwDXSDoNotDisturbSPIndex }
    ::= { bwDXSDoNotDisturbSPTable 1 }

  BwDoNotDisturbSPEntry ::= SEQUENCE {
    bwDXSDoNotDisturbSPIndex           Unsigned32,
    bwDXSDoNotDisturbSPID              DisplayString,
    bwDXSDoNotDisturbSPNumInvoked      Counter32,
    bwDXSDNDSPNumPhoneActivations      Counter32,
    bwDXSDNDSPNumPhoneDeactivations    Counter32
  }

  bwDXSDoNotDisturbSPIndex OBJECT-TYPE
    SYNTAX      Unsigned32
    MAX-ACCESS  read-only
    STATUS      current
    DESCRIPTION 
        "This integer represents the a service provider index in the system"
    ::= { bwDXSDoNotDisturbSPEntry 1 }

  bwDXSDoNotDisturbSPID OBJECT-TYPE
    SYNTAX      DisplayString
    MAX-ACCESS  read-only
    STATUS      current
    DESCRIPTION 
        "This string represents a service provider ID"
    ::= { bwDXSDoNotDisturbSPEntry 2 }

  bwDXSDoNotDisturbSPNumInvoked OBJECT-TYPE
    SYNTAX      Counter32
    MAX-ACCESS  read-write
    STATUS      current
    DESCRIPTION 
        "This counter reflects the number of times this service is triggered by a service provider"
    ::= { bwDXSDoNotDisturbSPEntry 3 }

  bwDXSDNDSPNumPhoneActivations OBJECT-TYPE
    SYNTAX      Counter32
    MAX-ACCESS  read-write
    STATUS      current
    DESCRIPTION 
        "Number of times DND has been activated via FAC for users in a given service provider"
    ::= { bwDXSDoNotDisturbSPEntry 4 }

  bwDXSDNDSPNumPhoneDeactivations OBJECT-TYPE
    SYNTAX      Counter32
    MAX-ACCESS  read-write
    STATUS      current
    DESCRIPTION 
        "Number of times DND has been deactivated via FAC for users in a given service provider"
    ::= { bwDXSDoNotDisturbSPEntry 5 }

  bwDXSDndPhoneActivations OBJECT-TYPE
    SYNTAX      Counter32
    MAX-ACCESS  read-write
    STATUS      current
    DESCRIPTION 
        "Total number of times DND has been activated via FAC"
    ::= { doNotDisturb 3 }

  bwDXSDndPhoneDeactivations OBJECT-TYPE
    SYNTAX      Counter32
    MAX-ACCESS  read-write
    STATUS      current
    DESCRIPTION 
        "Total number of times DND has been deactivated via FAC"
    ::= { doNotDisturb 4 }

  bwDXSDoNotDisturbGroupTable OBJECT-TYPE
    SYNTAX      SEQUENCE OF BwDoNotDisturbGroupEntry
    MAX-ACCESS  not-accessible
    STATUS      current
    DESCRIPTION 
        "This table contains the counters for Do Not Disturb service measurements for groups"
    ::= { doNotDisturb 5 }

  bwDXSDoNotDisturbGroupEntry OBJECT-TYPE
    SYNTAX      BwDoNotDisturbGroupEntry
    MAX-ACCESS  not-accessible
    STATUS      current
    DESCRIPTION 
        "This row contains the counters for Do Not Disturb service measurements for a group"
    INDEX       { bwDXSDoNotDisturbGroupIndex }
    ::= { bwDXSDoNotDisturbGroupTable 1 }

  BwDoNotDisturbGroupEntry ::= SEQUENCE {
    bwDXSDoNotDisturbGroupIndex            Unsigned32,
    bwDXSDoNotDisturbGroupID               DisplayString,
    bwDXSDoNotDisturbGroupNumInvoked       Counter32,
    bwDXSDNDGroupNumPhoneActivations       Counter32,
    bwDXSDNDGroupNumPhoneDeactivations     Counter32
  }

  bwDXSDoNotDisturbGroupIndex OBJECT-TYPE
    SYNTAX      Unsigned32
    MAX-ACCESS  read-only
    STATUS      current
    DESCRIPTION 
        "This integer represents the a group index in the system"
    ::= { bwDXSDoNotDisturbGroupEntry 1 }

  bwDXSDoNotDisturbGroupID OBJECT-TYPE
    SYNTAX      DisplayString
    MAX-ACCESS  read-only
    STATUS      current
    DESCRIPTION 
        "This string represents a group ID"
    ::= { bwDXSDoNotDisturbGroupEntry 2 }

  bwDXSDoNotDisturbGroupNumInvoked OBJECT-TYPE
    SYNTAX      Counter32
    MAX-ACCESS  read-write
    STATUS      current
    DESCRIPTION 
        "This counter reflects the number of times this service is triggered by a group"
    ::= { bwDXSDoNotDisturbGroupEntry 3 }

  bwDXSDNDGroupNumPhoneActivations OBJECT-TYPE
    SYNTAX      Counter32
    MAX-ACCESS  read-write
    STATUS      current
    DESCRIPTION 
        "Number of times DND has been activated via FAC for users in a given group"
    ::= { bwDXSDoNotDisturbGroupEntry 4 }

  bwDXSDNDGroupNumPhoneDeactivations OBJECT-TYPE
    SYNTAX      Counter32
    MAX-ACCESS  read-write
    STATUS      current
    DESCRIPTION 
        "Number of times DND has been deactivated via FAC for users in a given group"
    ::= { bwDXSDoNotDisturbGroupEntry 5 }

  bwDXSFlashCallTransferNumTransfers OBJECT-TYPE
    SYNTAX      Counter32
    MAX-ACCESS  read-write
    STATUS      current
    DESCRIPTION 
        "This counter reflects the number of times the flash code and destination number
         are used to effect a transfer"
    ::= { flashCallTransfer 1 }

  bwDXSFlashCallTransferSPTable OBJECT-TYPE
    SYNTAX      SEQUENCE OF BwFlashCallTransferSPEntry
    MAX-ACCESS  not-accessible
    STATUS      current
    DESCRIPTION 
        "This table contains the counters for Flash Call Transfer service measurements for service providers"
    ::= { flashCallTransfer 2 }

  bwDXSFlashCallTransferSPEntry OBJECT-TYPE
    SYNTAX      BwFlashCallTransferSPEntry
    MAX-ACCESS  not-accessible
    STATUS      current
    DESCRIPTION 
        "This row contains the counters for Flash Call Transfer service measurements for a service provider"
    INDEX       { bwDXSFlashCallTransferSPIndex }
    ::= { bwDXSFlashCallTransferSPTable 1 }

  BwFlashCallTransferSPEntry ::= SEQUENCE {
    bwDXSFlashCallTransferSPIndex          Unsigned32,
    bwDXSFlashCallTransferSPID             DisplayString,
    bwDXSFlashCallTransferSPNumTransfers   Counter32
  }

  bwDXSFlashCallTransferSPIndex OBJECT-TYPE
    SYNTAX      Unsigned32
    MAX-ACCESS  read-only
    STATUS      current
    DESCRIPTION 
        "This integer represents the a service provider index in the system"
    ::= { bwDXSFlashCallTransferSPEntry 1 }

  bwDXSFlashCallTransferSPID OBJECT-TYPE
    SYNTAX      DisplayString
    MAX-ACCESS  read-only
    STATUS      current
    DESCRIPTION 
        "This string represents a service provider ID"
    ::= { bwDXSFlashCallTransferSPEntry 2 }

  bwDXSFlashCallTransferSPNumTransfers OBJECT-TYPE
    SYNTAX      Counter32
    MAX-ACCESS  read-write
    STATUS      current
    DESCRIPTION 
        "This counter reflects the number of times the flash code and destination number are used to effect a transfer by a service provider"
    ::= { bwDXSFlashCallTransferSPEntry 3 }

  bwDXSFlashCallTransferGroupTable OBJECT-TYPE
    SYNTAX      SEQUENCE OF BwFlashCallTransferGroupEntry
    MAX-ACCESS  not-accessible
    STATUS      current
    DESCRIPTION 
        "This table contains the counters for Flash Call Transfer service measurements for groups"
    ::= { flashCallTransfer 3 }

  bwDXSFlashCallTransferGroupEntry OBJECT-TYPE
    SYNTAX      BwFlashCallTransferGroupEntry
    MAX-ACCESS  not-accessible
    STATUS      current
    DESCRIPTION 
        "This row contains the counters for Flash Call Transfer service measurements for a group"
    INDEX       { bwDXSFlashCallTransferGroupIndex }
    ::= { bwDXSFlashCallTransferGroupTable 1 }

  BwFlashCallTransferGroupEntry ::= SEQUENCE {
    bwDXSFlashCallTransferGroupIndex           Unsigned32,
    bwDXSFlashCallTransferGroupID              DisplayString,
    bwDXSFlashCallTransferGroupNumTransfers    Counter32
  }

  bwDXSFlashCallTransferGroupIndex OBJECT-TYPE
    SYNTAX      Unsigned32
    MAX-ACCESS  read-only
    STATUS      current
    DESCRIPTION 
        "This integer represents the a group index in the system"
    ::= { bwDXSFlashCallTransferGroupEntry 1 }

  bwDXSFlashCallTransferGroupID OBJECT-TYPE
    SYNTAX      DisplayString
    MAX-ACCESS  read-only
    STATUS      current
    DESCRIPTION 
        "This string represents a group ID"
    ::= { bwDXSFlashCallTransferGroupEntry 2 }

  bwDXSFlashCallTransferGroupNumTransfers OBJECT-TYPE
    SYNTAX      Counter32
    MAX-ACCESS  read-write
    STATUS      current
    DESCRIPTION 
        "This counter reflects the number of times the flash code and destination number are used to effect a transfer by a group"
    ::= { bwDXSFlashCallTransferGroupEntry 3 }

  bwDXSFlashCallWaitingNumAnswers OBJECT-TYPE
    SYNTAX      Counter32
    MAX-ACCESS  read-write
    STATUS      current
    DESCRIPTION 
        "This counter reflects the number of times the flash code results in the waiting call
         getting answered"
    ::= { flashCallWaiting 1 }

  bwDXSFlashCallWaitingSPTable OBJECT-TYPE
    SYNTAX      SEQUENCE OF BwFlashCallWaitingSPEntry
    MAX-ACCESS  not-accessible
    STATUS      current
    DESCRIPTION 
        "This table contains the counters for Flash Call Waiting service measurements for service providers"
    ::= { flashCallWaiting 2 }

  bwDXSFlashCallWaitingSPEntry OBJECT-TYPE
    SYNTAX      BwFlashCallWaitingSPEntry
    MAX-ACCESS  not-accessible
    STATUS      current
    DESCRIPTION 
        "This row contains the counters for Flash Call Waiting service measurements for a service provider"
    INDEX       { bwDXSFlashCallWaitingSPIndex }
    ::= { bwDXSFlashCallWaitingSPTable 1 }

  BwFlashCallWaitingSPEntry ::= SEQUENCE {
    bwDXSFlashCallWaitingSPIndex       Unsigned32,
    bwDXSFlashCallWaitingSPID          DisplayString,
    bwDXSFlashCallWaitingSPNumAnswers  Counter32
  }

  bwDXSFlashCallWaitingSPIndex OBJECT-TYPE
    SYNTAX      Unsigned32
    MAX-ACCESS  read-only
    STATUS      current
    DESCRIPTION 
        "This integer represents the a service provider index in the system"
    ::= { bwDXSFlashCallWaitingSPEntry 1 }

  bwDXSFlashCallWaitingSPID OBJECT-TYPE
    SYNTAX      DisplayString
    MAX-ACCESS  read-only
    STATUS      current
    DESCRIPTION 
        "This string represents a service provider ID"
    ::= { bwDXSFlashCallWaitingSPEntry 2 }

  bwDXSFlashCallWaitingSPNumAnswers OBJECT-TYPE
    SYNTAX      Counter32
    MAX-ACCESS  read-write
    STATUS      current
    DESCRIPTION 
        "This counter reflects the number of times the flash code results in the waiting call getting answered by a service provider"
    ::= { bwDXSFlashCallWaitingSPEntry 3 }

  bwDXSFlashCallWaitingGroupTable OBJECT-TYPE
    SYNTAX      SEQUENCE OF BwFlashCallWaitingGroupEntry
    MAX-ACCESS  not-accessible
    STATUS      current
    DESCRIPTION 
        "This table contains the counters for Flash Call Waiting service measurements for groups"
    ::= { flashCallWaiting 3 }

  bwDXSFlashCallWaitingGroupEntry OBJECT-TYPE
    SYNTAX      BwFlashCallWaitingGroupEntry
    MAX-ACCESS  not-accessible
    STATUS      current
    DESCRIPTION 
        "This row contains the counters for Flash Call Waiting service measurements for a group"
    INDEX       { bwDXSFlashCallWaitingGroupIndex }
    ::= { bwDXSFlashCallWaitingGroupTable 1 }

  BwFlashCallWaitingGroupEntry ::= SEQUENCE {
    bwDXSFlashCallWaitingGroupIndex        Unsigned32,
    bwDXSFlashCallWaitingGroupID           DisplayString,
    bwDXSFlashCallWaitingGroupNumAnswers   Counter32
  }

  bwDXSFlashCallWaitingGroupIndex OBJECT-TYPE
    SYNTAX      Unsigned32
    MAX-ACCESS  read-only
    STATUS      current
    DESCRIPTION 
        "This integer represents the a group index in the system"
    ::= { bwDXSFlashCallWaitingGroupEntry 1 }

  bwDXSFlashCallWaitingGroupID OBJECT-TYPE
    SYNTAX      DisplayString
    MAX-ACCESS  read-only
    STATUS      current
    DESCRIPTION 
        "This string represents a group ID"
    ::= { bwDXSFlashCallWaitingGroupEntry 2 }

  bwDXSFlashCallWaitingGroupNumAnswers OBJECT-TYPE
    SYNTAX      Counter32
    MAX-ACCESS  read-write
    STATUS      current
    DESCRIPTION 
        "This counter reflects the number of times the flash code results in the waiting call getting answered by a group"
    ::= { bwDXSFlashCallWaitingGroupEntry 3 }

  bwDXSFlashConsultationNumCalls OBJECT-TYPE
    SYNTAX      Counter32
    MAX-ACCESS  read-write
    STATUS      current
    DESCRIPTION 
        "This counter reflects the number of times a counsultation is attempted using the flash
         code and destination number"
    ::= { flashConsultation 1 }

  bwDXSFlashConsultationSPTable OBJECT-TYPE
    SYNTAX      SEQUENCE OF BwFlashConsultationSPEntry
    MAX-ACCESS  not-accessible
    STATUS      current
    DESCRIPTION 
        "This table contains the counters for Flash Consultation service measurements for service providers"
    ::= { flashConsultation 2 }

  bwDXSFlashConsultationSPEntry OBJECT-TYPE
    SYNTAX      BwFlashConsultationSPEntry
    MAX-ACCESS  not-accessible
    STATUS      current
    DESCRIPTION 
        "This row contains the counters for Flash Consultation service measurements for a service provider"
    INDEX       { bwDXSFlashConsultationSPIndex }
    ::= { bwDXSFlashConsultationSPTable 1 }

  BwFlashConsultationSPEntry ::= SEQUENCE {
    bwDXSFlashConsultationSPIndex      Unsigned32,
    bwDXSFlashConsultationSPID         DisplayString,
    bwDXSFlashConsultationSPNumCalls   Counter32
  }

  bwDXSFlashConsultationSPIndex OBJECT-TYPE
    SYNTAX      Unsigned32
    MAX-ACCESS  read-only
    STATUS      current
    DESCRIPTION 
        "This integer represents the a service provider index in the system"
    ::= { bwDXSFlashConsultationSPEntry 1 }

  bwDXSFlashConsultationSPID OBJECT-TYPE
    SYNTAX      DisplayString
    MAX-ACCESS  read-only
    STATUS      current
    DESCRIPTION 
        "This string represents a service provider ID"
    ::= { bwDXSFlashConsultationSPEntry 2 }

  bwDXSFlashConsultationSPNumCalls OBJECT-TYPE
    SYNTAX      Counter32
    MAX-ACCESS  read-write
    STATUS      current
    DESCRIPTION 
        "This counter reflects the number of times a counsultation is attempted using the flash code and destination number by a service provider"
    ::= { bwDXSFlashConsultationSPEntry 3 }

  bwDXSFlashConsultationGroupTable OBJECT-TYPE
    SYNTAX      SEQUENCE OF BwFlashConsultationGroupEntry
    MAX-ACCESS  not-accessible
    STATUS      current
    DESCRIPTION 
        "This table contains the counters for Flash Consultation service measurements for groups"
    ::= { flashConsultation 3 }

  bwDXSFlashConsultationGroupEntry OBJECT-TYPE
    SYNTAX      BwFlashConsultationGroupEntry
    MAX-ACCESS  not-accessible
    STATUS      current
    DESCRIPTION 
        "This row contains the counters for Flash Consultation service measurements for a group"
    INDEX       { bwDXSFlashConsultationGroupIndex }
    ::= { bwDXSFlashConsultationGroupTable 1 }

  BwFlashConsultationGroupEntry ::= SEQUENCE {
    bwDXSFlashConsultationGroupIndex       Unsigned32,
    bwDXSFlashConsultationGroupID          DisplayString,
    bwDXSFlashConsultationGroupNumCalls    Counter32
  }

  bwDXSFlashConsultationGroupIndex OBJECT-TYPE
    SYNTAX      Unsigned32
    MAX-ACCESS  read-only
    STATUS      current
    DESCRIPTION 
        "This integer represents the a group index in the system"
    ::= { bwDXSFlashConsultationGroupEntry 1 }

  bwDXSFlashConsultationGroupID OBJECT-TYPE
    SYNTAX      DisplayString
    MAX-ACCESS  read-only
    STATUS      current
    DESCRIPTION 
        "This string represents a group ID"
    ::= { bwDXSFlashConsultationGroupEntry 2 }

  bwDXSFlashConsultationGroupNumCalls OBJECT-TYPE
    SYNTAX      Counter32
    MAX-ACCESS  read-write
    STATUS      current
    DESCRIPTION 
        "This counter reflects the number of times a counsultation is attempted using the flash code and destination number by a group"
    ::= { bwDXSFlashConsultationGroupEntry 3 }

  bwDXSFlashThreeWayCallNum3WC OBJECT-TYPE
    SYNTAX      Counter32
    MAX-ACCESS  read-write
    STATUS      current
    DESCRIPTION 
        "This counter reflects the number of times the flash results in two calls being joined
         into a conference"
    ::= { flashThreeWayCall 1 }

  bwDXSFlashThreeWayCallSPTable OBJECT-TYPE
    SYNTAX      SEQUENCE OF BwFlashThreeWayCallSPEntry
    MAX-ACCESS  not-accessible
    STATUS      current
    DESCRIPTION 
        "This table contains the counters for Flash Three-Way Call service measurements for service providers"
    ::= { flashThreeWayCall 2 }

  bwDXSFlashThreeWayCallSPEntry OBJECT-TYPE
    SYNTAX      BwFlashThreeWayCallSPEntry
    MAX-ACCESS  not-accessible
    STATUS      current
    DESCRIPTION 
        "This row contains the counters for Flash Three-Way Call service measurements for a service provider"
    INDEX       { bwDXSFlashThreeWayCallSPIndex }
    ::= { bwDXSFlashThreeWayCallSPTable 1 }

  BwFlashThreeWayCallSPEntry ::= SEQUENCE {
    bwDXSFlashThreeWayCallSPIndex      Unsigned32,
    bwDXSFlashThreeWayCallSPID         DisplayString,
    bwDXSFlashThreeWayCallSPNum3WC     Counter32
  }

  bwDXSFlashThreeWayCallSPIndex OBJECT-TYPE
    SYNTAX      Unsigned32
    MAX-ACCESS  read-only
    STATUS      current
    DESCRIPTION 
        "This integer represents the a service provider index in the system"
    ::= { bwDXSFlashThreeWayCallSPEntry 1 }

  bwDXSFlashThreeWayCallSPID OBJECT-TYPE
    SYNTAX      DisplayString
    MAX-ACCESS  read-only
    STATUS      current
    DESCRIPTION 
        "This string represents a service provider ID"
    ::= { bwDXSFlashThreeWayCallSPEntry 2 }

  bwDXSFlashThreeWayCallSPNum3WC OBJECT-TYPE
    SYNTAX      Counter32
    MAX-ACCESS  read-write
    STATUS      current
    DESCRIPTION 
        "This counter reflects the number of times the flash results in two calls being joined into a conference by a service provider"
    ::= { bwDXSFlashThreeWayCallSPEntry 3 }

  bwDXSFlashThreeWayCallGroupTable OBJECT-TYPE
    SYNTAX      SEQUENCE OF BwFlashThreeWayCallGroupEntry
    MAX-ACCESS  not-accessible
    STATUS      current
    DESCRIPTION 
        "This table contains the counters for Flash Three-Way Call service measurements for groups"
    ::= { flashThreeWayCall 3 }

  bwDXSFlashThreeWayCallGroupEntry OBJECT-TYPE
    SYNTAX      BwFlashThreeWayCallGroupEntry
    MAX-ACCESS  not-accessible
    STATUS      current
    DESCRIPTION 
        "This row contains the counters for Flash Three-Way Call service measurements for a group"
    INDEX       { bwDXSFlashThreeWayCallGroupIndex }
    ::= { bwDXSFlashThreeWayCallGroupTable 1 }

  BwFlashThreeWayCallGroupEntry ::= SEQUENCE {
    bwDXSFlashThreeWayCallGroupIndex   Unsigned32,
    bwDXSFlashThreeWayCallGroupID      DisplayString,
    bwDXSFlashThreeWayCallGroupNum3WC  Counter32
  }

  bwDXSFlashThreeWayCallGroupIndex OBJECT-TYPE
    SYNTAX      Unsigned32
    MAX-ACCESS  read-only
    STATUS      current
    DESCRIPTION 
        "This integer represents the a group index in the system"
    ::= { bwDXSFlashThreeWayCallGroupEntry 1 }

  bwDXSFlashThreeWayCallGroupID OBJECT-TYPE
    SYNTAX      DisplayString
    MAX-ACCESS  read-only
    STATUS      current
    DESCRIPTION 
        "This string represents a group ID"
    ::= { bwDXSFlashThreeWayCallGroupEntry 2 }

  bwDXSFlashThreeWayCallGroupNum3WC OBJECT-TYPE
    SYNTAX      Counter32
    MAX-ACCESS  read-write
    STATUS      current
    DESCRIPTION 
        "This counter reflects the number of times the flash results in two calls being joined into a conference by a group"
    ::= { bwDXSFlashThreeWayCallGroupEntry 3 }

  bwDXSHuntGroupNumAttempts OBJECT-TYPE
    SYNTAX      Counter32
    MAX-ACCESS  read-write
    STATUS      current
    DESCRIPTION 
        "This is the number of incoming calls to a Hunt Group."
    ::= { huntGroups 1 }

  bwDXSHuntGroupNumBusy OBJECT-TYPE
    SYNTAX      Counter32
    MAX-ACCESS  read-write
    STATUS      current
    DESCRIPTION 
        "This is the number of calls to a Hunt Group where no agent is available and the originator receives Busy Treatment."
    ::= { huntGroups 2 }

  bwDXSHuntGroupsSPTable OBJECT-TYPE
    SYNTAX      SEQUENCE OF BwHuntGroupsSPEntry
    MAX-ACCESS  not-accessible
    STATUS      current
    DESCRIPTION 
        "This table contains the counters for Hunt Group service measurements for service providers"
    ::= { huntGroups 3 }

  bwDXSHuntGroupsSPEntry OBJECT-TYPE
    SYNTAX      BwHuntGroupsSPEntry
    MAX-ACCESS  not-accessible
    STATUS      current
    DESCRIPTION 
        "This row contains the counters for Hunt Group service measurements for a service provider"
    INDEX       { bwDXSHuntGroupsSPIndex }
    ::= { bwDXSHuntGroupsSPTable 1 }

  BwHuntGroupsSPEntry ::= SEQUENCE {
    bwDXSHuntGroupsSPIndex             Unsigned32,
    bwDXSHuntGroupsSPID                DisplayString,
    bwDXSHuntGroupSPNumAttempts        Counter32,
    bwDXSHuntGroupSPNumBusy            Counter32
  }

  bwDXSHuntGroupsSPIndex OBJECT-TYPE
    SYNTAX      Unsigned32
    MAX-ACCESS  read-only
    STATUS      current
    DESCRIPTION 
        "This integer represents the a service provider index in the system"
    ::= { bwDXSHuntGroupsSPEntry 1 }

  bwDXSHuntGroupsSPID OBJECT-TYPE
    SYNTAX      DisplayString
    MAX-ACCESS  read-only
    STATUS      current
    DESCRIPTION 
        "This string represents a service provider ID"
    ::= { bwDXSHuntGroupsSPEntry 2 }

  bwDXSHuntGroupSPNumAttempts OBJECT-TYPE
    SYNTAX      Counter32
    MAX-ACCESS  read-write
    STATUS      current
    DESCRIPTION 
        "This is the number of incoming calls to a Hunt Group.  There is one instance of this counter for each service provider defined in the system."
    ::= { bwDXSHuntGroupsSPEntry 3 }

  bwDXSHuntGroupSPNumBusy OBJECT-TYPE
    SYNTAX      Counter32
    MAX-ACCESS  read-write
    STATUS      current
    DESCRIPTION 
        "This is the number of calls to a Hunt Group where no agent is available and the originator receives Busy Treatment.  There is one instance of this counter for each service provider defined in the system."
    ::= { bwDXSHuntGroupsSPEntry 4 }

  bwDXSHuntGroupsGroupTable OBJECT-TYPE
    SYNTAX      SEQUENCE OF BwHuntGroupsGroupEntry
    MAX-ACCESS  not-accessible
    STATUS      current
    DESCRIPTION 
        "This table contains the counters for Hunt Group service measurements for groups"
    ::= { huntGroups 4 }

  bwDXSHuntGroupsGroupEntry OBJECT-TYPE
    SYNTAX      BwHuntGroupsGroupEntry
    MAX-ACCESS  not-accessible
    STATUS      current
    DESCRIPTION 
        "This row contains the counters for Hunt Group service measurements for a group"
    INDEX       { bwDXSHuntGroupsGroupIndex }
    ::= { bwDXSHuntGroupsGroupTable 1 }

  BwHuntGroupsGroupEntry ::= SEQUENCE {
    bwDXSHuntGroupsGroupIndex              Unsigned32,
    bwDXSHuntGroupsGroupID                 DisplayString,
    bwDXSHuntGroupsGroupNumAttempts        Counter32,
    bwDXSHuntGroupsGroupNumBusy            Counter32
  }

  bwDXSHuntGroupsGroupIndex OBJECT-TYPE
    SYNTAX      Unsigned32
    MAX-ACCESS  read-only
    STATUS      current
    DESCRIPTION 
        "This integer represents the a Group index in the system"
    ::= { bwDXSHuntGroupsGroupEntry 1 }

  bwDXSHuntGroupsGroupID OBJECT-TYPE
    SYNTAX      DisplayString
    MAX-ACCESS  read-only
    STATUS      current
    DESCRIPTION 
        "This string represents a Group ID"
    ::= { bwDXSHuntGroupsGroupEntry 2 }

  bwDXSHuntGroupsGroupNumAttempts OBJECT-TYPE
    SYNTAX      Counter32
    MAX-ACCESS  read-write
    STATUS      current
    DESCRIPTION 
        "This is the number of incoming calls to a Hunt Group.  There is one instance of this counter for each group defined in the system."
    ::= { bwDXSHuntGroupsGroupEntry 3 }

  bwDXSHuntGroupsGroupNumBusy OBJECT-TYPE
    SYNTAX      Counter32
    MAX-ACCESS  read-write
    STATUS      current
    DESCRIPTION 
        "This is the number of calls to a Hunt Group where no agent is available and the originator receives Busy Treatment.  There is one instance of this counter for each group defined in the system."
    ::= { bwDXSHuntGroupsGroupEntry 4 }

  bwDXSICPNumInterGroupBlocks OBJECT-TYPE
    SYNTAX      Counter32
    MAX-ACCESS  read-write
    STATUS      current
    DESCRIPTION 
        "This counter reflects the number of times this service denies a direct call from outside the group"
    ::= { incomingCallingPlan 1 }

  bwDXSIncomingCallingPlanSPTable OBJECT-TYPE
    SYNTAX      SEQUENCE OF BwIncomingCallingPlanSPEntry
    MAX-ACCESS  not-accessible
    STATUS      current
    DESCRIPTION 
        "This table contains the counters for Incoming Calling Plan service measurements for service providers"
    ::= { incomingCallingPlan 2 }

  bwDXSIncomingCallingPlanSPEntry OBJECT-TYPE
    SYNTAX      BwIncomingCallingPlanSPEntry
    MAX-ACCESS  not-accessible
    STATUS      current
    DESCRIPTION 
        "This row contains the counters for Incoming Calling Plan service measurements for a service provider"
    INDEX       { bwDXSIncomingCallingPlanSPIndex }
    ::= { bwDXSIncomingCallingPlanSPTable 1 }

  BwIncomingCallingPlanSPEntry ::= SEQUENCE {
    bwDXSIncomingCallingPlanSPIndex    Unsigned32,
    bwDXSIncomingCallingPlanSPID       DisplayString,
    bwDXSICPSPNumInterGroupBlocks      Counter32,
    bwDXSICPSPNumCollectCallBlocks     Counter32,
    bwDXSICPSPNumIntraGroupBlocks      Counter32,
    bwDXSICPSPNumOutsideCallerBlocks   Counter32
  }

  bwDXSIncomingCallingPlanSPIndex OBJECT-TYPE
    SYNTAX      Unsigned32
    MAX-ACCESS  read-only
    STATUS      current
    DESCRIPTION 
        "This integer represents the a service provider index in the system"
    ::= { bwDXSIncomingCallingPlanSPEntry 1 }

  bwDXSIncomingCallingPlanSPID OBJECT-TYPE
    SYNTAX      DisplayString
    MAX-ACCESS  read-only
    STATUS      current
    DESCRIPTION 
        "Column Description This string represents a service provider ID"
    ::= { bwDXSIncomingCallingPlanSPEntry 2 }

  bwDXSICPSPNumInterGroupBlocks OBJECT-TYPE
    SYNTAX      Counter32
    MAX-ACCESS  read-write
    STATUS      current
    DESCRIPTION 
        "This counter reflects the number of times this service denies a direct call from outside the group for a service provider"
    ::= { bwDXSIncomingCallingPlanSPEntry 3 }

  bwDXSICPSPNumCollectCallBlocks OBJECT-TYPE
    SYNTAX      Counter32
    MAX-ACCESS  read-write
    STATUS      current
    DESCRIPTION 
        "This counter is incremented whenever the service denies a collect call for a service provider"
    ::= { bwDXSIncomingCallingPlanSPEntry 4 }

  bwDXSICPSPNumIntraGroupBlocks OBJECT-TYPE
    SYNTAX      Counter32
    MAX-ACCESS  read-write
    STATUS      current
    DESCRIPTION 
        "This counter is incremented whenever the service denies an intra-group call for a service provider"
    ::= { bwDXSIncomingCallingPlanSPEntry 5 }

  bwDXSICPSPNumOutsideCallerBlocks OBJECT-TYPE
    SYNTAX      Counter32
    MAX-ACCESS  read-write
    STATUS      current
    DESCRIPTION 
        "This counter reflects the number of times this service denies a call forwarded/transferred by a group member where the other party is outside the group for a service provider"
    ::= { bwDXSIncomingCallingPlanSPEntry 6 }

  bwDXSIncomingCallingPlanGroupTable OBJECT-TYPE
    SYNTAX      SEQUENCE OF BwIncomingCallingPlanGroupEntry
    MAX-ACCESS  not-accessible
    STATUS      current
    DESCRIPTION 
        "This table contains the counters for Incoming Calling Plan service measurements for groups"
    ::= { incomingCallingPlan 3 }

  bwDXSIncomingCallingPlanGroupEntry OBJECT-TYPE
    SYNTAX      BwIncomingCallingPlanGroupEntry
    MAX-ACCESS  not-accessible
    STATUS      current
    DESCRIPTION 
        "This row contains the counters for Incoming Calling Plan service measurements for a group"
    INDEX       { bwDXSIncomingCallingPlanGroupIndex }
    ::= { bwDXSIncomingCallingPlanGroupTable 1 }

  BwIncomingCallingPlanGroupEntry ::= SEQUENCE {
    bwDXSIncomingCallingPlanGroupIndex     Unsigned32,
    bwDXSIncomingCallingPlanGroupID        DisplayString,
    bwDXSICPGroupNumInterGroupBlocks       Counter32,
    bwDXSICPGroupNumCollectCallBlocks      Counter32,
    bwDXSICPGroupNumIntraGroupBlocks       Counter32,
    bwDXSICPGroupNumOutsideCallerBlocks    Counter32
  }

  bwDXSIncomingCallingPlanGroupIndex OBJECT-TYPE
    SYNTAX      Unsigned32
    MAX-ACCESS  read-only
    STATUS      current
    DESCRIPTION 
        "This integer represents the a group index in the system"
    ::= { bwDXSIncomingCallingPlanGroupEntry 1 }

  bwDXSIncomingCallingPlanGroupID OBJECT-TYPE
    SYNTAX      DisplayString
    MAX-ACCESS  read-only
    STATUS      current
    DESCRIPTION 
        "Column Description This string represents a group ID"
    ::= { bwDXSIncomingCallingPlanGroupEntry 2 }

  bwDXSICPGroupNumInterGroupBlocks OBJECT-TYPE
    SYNTAX      Counter32
    MAX-ACCESS  read-write
    STATUS      current
    DESCRIPTION 
        "This counter reflects the number of times this service denies a direct call from outside the group for a group"
    ::= { bwDXSIncomingCallingPlanGroupEntry 3 }

  bwDXSICPGroupNumCollectCallBlocks OBJECT-TYPE
    SYNTAX      Counter32
    MAX-ACCESS  read-write
    STATUS      current
    DESCRIPTION 
        "This counter is incremented whenever the service denies a collect call for a group"
    ::= { bwDXSIncomingCallingPlanGroupEntry 4 }

  bwDXSICPGroupNumIntraGroupBlocks OBJECT-TYPE
    SYNTAX      Counter32
    MAX-ACCESS  read-write
    STATUS      current
    DESCRIPTION 
        "This counter is incremented whenever the service denies an intra-group call for a group"
    ::= { bwDXSIncomingCallingPlanGroupEntry 5 }

  bwDXSICPGroupNumOutsideCallerBlocks OBJECT-TYPE
    SYNTAX      Counter32
    MAX-ACCESS  read-write
    STATUS      current
    DESCRIPTION 
        "This counter reflects the number of times this service denies a call forwarded/transferred by a group member where the other party is outside the group for a group"
    ::= { bwDXSIncomingCallingPlanGroupEntry 6 }

  bwDXSICPNumCollectCallBlocks OBJECT-TYPE
    SYNTAX      Counter32
    MAX-ACCESS  read-write
    STATUS      current
    DESCRIPTION 
        "This counter is incremented whenever the service denies a collect call"
    ::= { incomingCallingPlan 4 }

  bwDXSICPNumIntraGroupBlocks OBJECT-TYPE
    SYNTAX      Counter32
    MAX-ACCESS  read-write
    STATUS      current
    DESCRIPTION 
        "This counter is incremented whenever the service denies an intra-group call"
    ::= { incomingCallingPlan 5 }

  bwDXSICPNumOutsideCallerBlocks OBJECT-TYPE
    SYNTAX      Counter32
    MAX-ACCESS  read-write
    STATUS      current
    DESCRIPTION 
        "This counter reflects the number of times this service denies a call forwarded/transferred by a group member where the other party is outside the group"
    ::= { incomingCallingPlan 6 }

  bwDXSIPPhoneNumForwards OBJECT-TYPE
    SYNTAX      Counter32
    MAX-ACCESS  read-write
    STATUS      current
    DESCRIPTION 
        "This counter reflects the number of times this service redirects a call on a request from
         an IP Phone"
    ::= { ipPhone 1 }

  bwDXSIPPhoneSPTable OBJECT-TYPE
    SYNTAX      SEQUENCE OF BwIPPhoneSPEntry
    MAX-ACCESS  not-accessible
    STATUS      current
    DESCRIPTION 
        "This table contains the counters for IP Phone service measurements for service providers"
    ::= { ipPhone 2 }

  bwDXSIPPhoneSPEntry OBJECT-TYPE
    SYNTAX      BwIPPhoneSPEntry
    MAX-ACCESS  not-accessible
    STATUS      current
    DESCRIPTION 
        "This row contains the counters for IP Phone service measurements for a service provider"
    INDEX       { bwDXSIPPhoneSPIndex }
    ::= { bwDXSIPPhoneSPTable 1 }

  BwIPPhoneSPEntry ::= SEQUENCE {
    bwDXSIPPhoneSPIndex        Unsigned32,
    bwDXSIPPhoneSPID           DisplayString,
    bwDXSIPPhoneSPNumForwards  Counter32
  }

  bwDXSIPPhoneSPIndex OBJECT-TYPE
    SYNTAX      Unsigned32
    MAX-ACCESS  read-only
    STATUS      current
    DESCRIPTION 
        "This integer represents the a service provider index in the system"
    ::= { bwDXSIPPhoneSPEntry 1 }

  bwDXSIPPhoneSPID OBJECT-TYPE
    SYNTAX      DisplayString
    MAX-ACCESS  read-only
    STATUS      current
    DESCRIPTION 
        "This string represents a service provider ID"
    ::= { bwDXSIPPhoneSPEntry 2 }

  bwDXSIPPhoneSPNumForwards OBJECT-TYPE
    SYNTAX      Counter32
    MAX-ACCESS  read-write
    STATUS      current
    DESCRIPTION 
        "This counter reflects the number of times this service redirects a call on a request from an IP Phone by a service provider"
    ::= { bwDXSIPPhoneSPEntry 3 }

  bwDXSIPPhoneGroupTable OBJECT-TYPE
    SYNTAX      SEQUENCE OF BwIPPhoneGroupEntry
    MAX-ACCESS  not-accessible
    STATUS      current
    DESCRIPTION 
        "This table contains the counters for IP Phone service measurements for groups"
    ::= { ipPhone 3 }

  bwDXSIPPhoneGroupEntry OBJECT-TYPE
    SYNTAX      BwIPPhoneGroupEntry
    MAX-ACCESS  not-accessible
    STATUS      current
    DESCRIPTION 
        "This row contains the counters for IP Phone service measurements for a group"
    INDEX       { bwDXSIPPhoneGroupIndex }
    ::= { bwDXSIPPhoneGroupTable 1 }

  BwIPPhoneGroupEntry ::= SEQUENCE {
    bwDXSIPPhoneGroupIndex         Unsigned32,
    bwDXSIPPhoneGroupID            DisplayString,
    bwDXSIPPhoneGroupNumForwards   Counter32
  }

  bwDXSIPPhoneGroupIndex OBJECT-TYPE
    SYNTAX      Unsigned32
    MAX-ACCESS  read-only
    STATUS      current
    DESCRIPTION 
        "This integer represents the a group index in the system"
    ::= { bwDXSIPPhoneGroupEntry 1 }

  bwDXSIPPhoneGroupID OBJECT-TYPE
    SYNTAX      DisplayString
    MAX-ACCESS  read-only
    STATUS      current
    DESCRIPTION 
        "This string represents a group ID"
    ::= { bwDXSIPPhoneGroupEntry 2 }

  bwDXSIPPhoneGroupNumForwards OBJECT-TYPE
    SYNTAX      Counter32
    MAX-ACCESS  read-write
    STATUS      current
    DESCRIPTION 
        "This counter reflects the number of times this service redirects a call on a request from an IP Phone by a group"
    ::= { bwDXSIPPhoneGroupEntry 3 }

  bwDXSLNRNumRedials OBJECT-TYPE
    SYNTAX      Counter32
    MAX-ACCESS  read-write
    STATUS      current
    DESCRIPTION 
        "This counter reflects the number of times the flash code results in this service
         attempting to dial the last number called"
    ::= { lastNumberRedial 1 }

  bwDXSLastNumberRedialSPTable OBJECT-TYPE
    SYNTAX      SEQUENCE OF BwLastNumberRedialSPEntry
    MAX-ACCESS  not-accessible
    STATUS      current
    DESCRIPTION 
        "This table contains the counters for Last Number Redial service measurements for service providers"
    ::= { lastNumberRedial 2 }

  bwDXSLastNumberRedialSPEntry OBJECT-TYPE
    SYNTAX      BwLastNumberRedialSPEntry
    MAX-ACCESS  not-accessible
    STATUS      current
    DESCRIPTION 
        "This row contains the counters for Last Number Redial service measurements for a service provider"
    INDEX       { bwDXSLastNumberRedialSPIndex }
    ::= { bwDXSLastNumberRedialSPTable 1 }

  BwLastNumberRedialSPEntry ::= SEQUENCE {
    bwDXSLastNumberRedialSPIndex   Unsigned32,
    bwDXSLastNumberRedialSPID      DisplayString,
    bwDXSLNRSPNumRedials           Counter32
  }

  bwDXSLastNumberRedialSPIndex OBJECT-TYPE
    SYNTAX      Unsigned32
    MAX-ACCESS  read-only
    STATUS      current
    DESCRIPTION 
        "This integer represents the a service provider index in the system"
    ::= { bwDXSLastNumberRedialSPEntry 1 }

  bwDXSLastNumberRedialSPID OBJECT-TYPE
    SYNTAX      DisplayString
    MAX-ACCESS  read-only
    STATUS      current
    DESCRIPTION 
        "This string represents a service provider ID"
    ::= { bwDXSLastNumberRedialSPEntry 2 }

  bwDXSLNRSPNumRedials OBJECT-TYPE
    SYNTAX      Counter32
    MAX-ACCESS  read-write
    STATUS      current
    DESCRIPTION 
        "This counter reflects the number of times the flash code results in this service attempting to dial the last number called by a service provider"
    ::= { bwDXSLastNumberRedialSPEntry 3 }

  bwDXSLastNumberRedialGroupTable OBJECT-TYPE
    SYNTAX      SEQUENCE OF BwLastNumberRedialGroupEntry
    MAX-ACCESS  not-accessible
    STATUS      current
    DESCRIPTION 
        "This table contains the counters for Last Number Redial service measurements for groups"
    ::= { lastNumberRedial 3 }

  bwDXSLastNumberRedialGroupEntry OBJECT-TYPE
    SYNTAX      BwLastNumberRedialGroupEntry
    MAX-ACCESS  not-accessible
    STATUS      current
    DESCRIPTION 
        "This row contains the counters for Last Number Redial service measurements for a group"
    INDEX       { bwDXSLastNumberRedialGroupIndex }
    ::= { bwDXSLastNumberRedialGroupTable 1 }

  BwLastNumberRedialGroupEntry ::= SEQUENCE {
    bwDXSLastNumberRedialGroupIndex    Unsigned32,
    bwDXSLastNumberRedialGroupID       DisplayString,
    bwDXSLNRGroupNumRedials            Counter32
  }

  bwDXSLastNumberRedialGroupIndex OBJECT-TYPE
    SYNTAX      Unsigned32
    MAX-ACCESS  read-only
    STATUS      current
    DESCRIPTION 
        "This integer represents the a group index in the system"
    ::= { bwDXSLastNumberRedialGroupEntry 1 }

  bwDXSLastNumberRedialGroupID OBJECT-TYPE
    SYNTAX      DisplayString
    MAX-ACCESS  read-only
    STATUS      current
    DESCRIPTION 
        "This string represents a group ID"
    ::= { bwDXSLastNumberRedialGroupEntry 2 }

  bwDXSLNRGroupNumRedials OBJECT-TYPE
    SYNTAX      Counter32
    MAX-ACCESS  read-write
    STATUS      current
    DESCRIPTION 
        "This counter reflects the number of times the flash code results in this service attempting to dial the last number called by a group"
    ::= { bwDXSLastNumberRedialGroupEntry 3 }

  bwDXSOCPNumGroupCallsBlocked OBJECT-TYPE
    SYNTAX      Counter32
    MAX-ACCESS  read-write
    STATUS      current
    DESCRIPTION 
        "This counter reflects the number of times an intra-group call is blocked"
    ::= { outgoingCallingPlan 1 }

  bwDXSOCPNumLocalCallsBlocked OBJECT-TYPE
    SYNTAX      Counter32
    MAX-ACCESS  read-write
    STATUS      current
    DESCRIPTION 
        "This counter reflects the number of times a local call is blocked"
    ::= { outgoingCallingPlan 2 }

  bwDXSOCPNumTollFreeCallsBlocked OBJECT-TYPE
    SYNTAX      Counter32
    MAX-ACCESS  read-write
    STATUS      current
    DESCRIPTION 
        "This counter reflects the number of times a toll free call is blocked"
    ::= { outgoingCallingPlan 3 }

  bwDXSOCPNumTollCallsBlocked OBJECT-TYPE
    SYNTAX      Counter32
    MAX-ACCESS  read-write
    STATUS      current
    DESCRIPTION 
        "This counter reflects the number of times a toll call is blocked"
    ::= { outgoingCallingPlan 4 }

  bwDXSOCPNumIntlCallsBlocked OBJECT-TYPE
    SYNTAX      Counter32
    MAX-ACCESS  read-write
    STATUS      current
    DESCRIPTION 
        "This counter reflects the number of times an international call is blocked"
    ::= { outgoingCallingPlan 5 }

  bwDXSOCPNumOperatorAssistedCallsBlocked OBJECT-TYPE
    SYNTAX      Counter32
    MAX-ACCESS  read-write
    STATUS      current
    DESCRIPTION 
        "This counter reflects the number of times an operator assisted call is blocked"
    ::= { outgoingCallingPlan 6 }

  bwDXSOCPNumChargeableDirAssistCallsBlocked OBJECT-TYPE
    SYNTAX      Counter32
    MAX-ACCESS  read-write
    STATUS      current
    DESCRIPTION 
        "This counter reflects the number of times a chargeable directory assistance call is
         blocked"
    ::= { outgoingCallingPlan 7 }

  bwDXSOCPNumSpecialServices1CallsBlocked OBJECT-TYPE
    SYNTAX      Counter32
    MAX-ACCESS  read-write
    STATUS      current
    DESCRIPTION 
        "This counter reflects the number of times a special services call is blocked"
    ::= { outgoingCallingPlan 8 }

  bwDXSOCPNumSpecialServices2CallsBlocked OBJECT-TYPE
    SYNTAX      Counter32
    MAX-ACCESS  read-write
    STATUS      current
    DESCRIPTION 
        "This counter reflects the number of times a special services call is blocked"
    ::= { outgoingCallingPlan 9 }

  bwDXSOCPNumPremiumServices1CallsBlocked OBJECT-TYPE
    SYNTAX      Counter32
    MAX-ACCESS  read-write
    STATUS      current
    DESCRIPTION 
        "This counter reflects the number of times a premium services call is blocked"
    ::= { outgoingCallingPlan 10 }

  bwDXSOCPNumPremiumServices2CallsBlocked OBJECT-TYPE
    SYNTAX      Counter32
    MAX-ACCESS  read-write
    STATUS      current
    DESCRIPTION 
        "This counter reflects the number of times a premium services call is blocked"
    ::= { outgoingCallingPlan 11 }

  bwDXSOCPNumCasualCallsBlocked OBJECT-TYPE
    SYNTAX      Counter32
    MAX-ACCESS  read-write
    STATUS      current
    DESCRIPTION 
        "This counter reflects the number of times a casual equal access call is blocked"
    ::= { outgoingCallingPlan 12 }

  bwDXSOCPNumURLDialingCallsBlocked OBJECT-TYPE
    SYNTAX      Counter32
    MAX-ACCESS  read-write
    STATUS      current
    DESCRIPTION 
        "This counter reflects the number of times a URL dialed call is blocked"
    ::= { outgoingCallingPlan 13 }

  bwDXSOCPNumUnknownCallsBlocked OBJECT-TYPE
    SYNTAX      Counter32
    MAX-ACCESS  read-write
    STATUS      current
    DESCRIPTION 
        "This counter reflects the number of times an unknown call type is blocked"
    ::= { outgoingCallingPlan 14 }

  bwDXSOutgoingCallingPlanSPTable OBJECT-TYPE
    SYNTAX      SEQUENCE OF BwOutgoingCallingPlanSPEntry
    MAX-ACCESS  not-accessible
    STATUS      current
    DESCRIPTION 
        "This table contains the counters for Outgoing Calling Plan service measurements for service providers"
    ::= { outgoingCallingPlan 15 }

  bwDXSOutgoingCallingPlanSPEntry OBJECT-TYPE
    SYNTAX      BwOutgoingCallingPlanSPEntry
    MAX-ACCESS  not-accessible
    STATUS      current
    DESCRIPTION 
        "This row contains the counters for Outgoing Calling Plan service measurements for a service provider"
    INDEX       { bwDXSOutgoingCallingPlanSPIndex }
    ::= { bwDXSOutgoingCallingPlanSPTable 1 }

  BwOutgoingCallingPlanSPEntry ::= SEQUENCE {
    bwDXSOutgoingCallingPlanSPIndex                Unsigned32,
    bwDXSOutgoingCallingPlanSPID                   DisplayString,
    bwDXSOCPSPNumGroupCallsBlocked                 Counter32,
    bwDXSOCPSPNumLocalCallsBlocked                 Counter32,
    bwDXSOCPSPNumTollFreeCallsBlocked              Counter32,
    bwDXSOCPSPNumTollCallsBlocked                  Counter32,
    bwDXSOCPSPNumIntlCallsBlocked                  Counter32,
    bwDXSOCPSPNumOperatorAssistedCallsBlocked      Counter32,
    bwDXSOCPSPNumChargeableDirAssistCallsBlocked   Counter32,
    bwDXSOCPSPNumSpecialServices1CallsBlocked      Counter32,
    bwDXSOCPSPNumSpecialServices2CallsBlocked      Counter32,
    bwDXSOCPSPNumPremiumServices1CallsBlocked      Counter32,
    bwDXSOCPSPNumPremiumServices2CallsBlocked      Counter32,
    bwDXSOCPSPNumCasualCallsBlocked                Counter32,
    bwDXSOCPSPNumURLDialingCallsBlocked            Counter32,
    bwDXSOCPSPNumUnknownCallsBlocked               Counter32,
    bwDXSOCPSPNumSuccessfulAuthorizations          Counter32,
    bwDXSOCPSPNumUnsuccessfulAuthorizations        Counter32,
    bwDXSOCPSPNumTransfers                         Counter32,
    bwDXSOCPSACSPNumSuccessfulLock                 Counter32,
    bwDXSOCPSACSPNumSuccessfulUnlock               Counter32,
    bwDXSOCPSACSPNumUnsuccessfulLock               Counter32,
    bwDXSOCPSACSPNumUnsuccessfulUnlock             Counter32,
    bwDXSOCPSACSPNumUnsuccessfulCodeUsage          Counter32,
    bwDXSOCPSPNumOutsideGroupTransferBlocks        Counter32
  }

  bwDXSOutgoingCallingPlanSPIndex OBJECT-TYPE
    SYNTAX      Unsigned32
    MAX-ACCESS  read-only
    STATUS      current
    DESCRIPTION 
        "This integer represents the a service provider index in the system"
    ::= { bwDXSOutgoingCallingPlanSPEntry 1 }

  bwDXSOutgoingCallingPlanSPID OBJECT-TYPE
    SYNTAX      DisplayString
    MAX-ACCESS  read-only
    STATUS      current
    DESCRIPTION 
        "This string represents a service provider ID"
    ::= { bwDXSOutgoingCallingPlanSPEntry 2 }

  bwDXSOCPSPNumGroupCallsBlocked OBJECT-TYPE
    SYNTAX      Counter32
    MAX-ACCESS  read-write
    STATUS      current
    DESCRIPTION 
        "This counter reflects the number of times an intra-group call is blocked by a service provider"
    ::= { bwDXSOutgoingCallingPlanSPEntry 3 }

  bwDXSOCPSPNumLocalCallsBlocked OBJECT-TYPE
    SYNTAX      Counter32
    MAX-ACCESS  read-write
    STATUS      current
    DESCRIPTION 
        "This counter reflects the number of times a local call is blocked by a service provider"
    ::= { bwDXSOutgoingCallingPlanSPEntry 4 }

  bwDXSOCPSPNumTollFreeCallsBlocked OBJECT-TYPE
    SYNTAX      Counter32
    MAX-ACCESS  read-write
    STATUS      current
    DESCRIPTION 
        "This counter reflects the number of times a toll free call is blocked by a service provider"
    ::= { bwDXSOutgoingCallingPlanSPEntry 5 }

  bwDXSOCPSPNumTollCallsBlocked OBJECT-TYPE
    SYNTAX      Counter32
    MAX-ACCESS  read-write
    STATUS      current
    DESCRIPTION 
        "This counter reflects the number of times a toll call is blocked by a service provider"
    ::= { bwDXSOutgoingCallingPlanSPEntry 6 }

  bwDXSOCPSPNumIntlCallsBlocked OBJECT-TYPE
    SYNTAX      Counter32
    MAX-ACCESS  read-write
    STATUS      current
    DESCRIPTION 
        "This counter reflects the number of times an international call is blocked by a service provider"
    ::= { bwDXSOutgoingCallingPlanSPEntry 7 }

  bwDXSOCPSPNumOperatorAssistedCallsBlocked OBJECT-TYPE
    SYNTAX      Counter32
    MAX-ACCESS  read-write
    STATUS      current
    DESCRIPTION 
        "This counter reflects the number of times an operator assisted call is blocked by a service provider"
    ::= { bwDXSOutgoingCallingPlanSPEntry 8 }

  bwDXSOCPSPNumChargeableDirAssistCallsBlocked OBJECT-TYPE
    SYNTAX      Counter32
    MAX-ACCESS  read-write
    STATUS      current
    DESCRIPTION 
        "This counter reflects the number of times a chargeable directory assistance call is blocked by a service provider"
    ::= { bwDXSOutgoingCallingPlanSPEntry 9 }

  bwDXSOCPSPNumSpecialServices1CallsBlocked OBJECT-TYPE
    SYNTAX      Counter32
    MAX-ACCESS  read-write
    STATUS      current
    DESCRIPTION 
        "This counter reflects the number of times a special services call is blocked by a service provider"
    ::= { bwDXSOutgoingCallingPlanSPEntry 10 }

  bwDXSOCPSPNumSpecialServices2CallsBlocked OBJECT-TYPE
    SYNTAX      Counter32
    MAX-ACCESS  read-write
    STATUS      current
    DESCRIPTION 
        "This counter reflects the number of times a special services call is blocked by a service provider"
    ::= { bwDXSOutgoingCallingPlanSPEntry 11 }

  bwDXSOCPSPNumPremiumServices1CallsBlocked OBJECT-TYPE
    SYNTAX      Counter32
    MAX-ACCESS  read-write
    STATUS      current
    DESCRIPTION 
        "This counter reflects the number of times a premium services call is blocked by a service provider"
    ::= { bwDXSOutgoingCallingPlanSPEntry 12 }

  bwDXSOCPSPNumPremiumServices2CallsBlocked OBJECT-TYPE
    SYNTAX      Counter32
    MAX-ACCESS  read-write
    STATUS      current
    DESCRIPTION 
        "This counter reflects the number of times a premium services call is blocked by a service provider"
    ::= { bwDXSOutgoingCallingPlanSPEntry 13 }

  bwDXSOCPSPNumCasualCallsBlocked OBJECT-TYPE
    SYNTAX      Counter32
    MAX-ACCESS  read-write
    STATUS      current
    DESCRIPTION 
        "This counter reflects the number of times a casual equal access call is blocked by a service provider"
    ::= { bwDXSOutgoingCallingPlanSPEntry 14 }

  bwDXSOCPSPNumURLDialingCallsBlocked OBJECT-TYPE
    SYNTAX      Counter32
    MAX-ACCESS  read-write
    STATUS      current
    DESCRIPTION 
        "This counter reflects the number of times a URL dialed call is blocked by a service provider"
    ::= { bwDXSOutgoingCallingPlanSPEntry 15 }

  bwDXSOCPSPNumUnknownCallsBlocked OBJECT-TYPE
    SYNTAX      Counter32
    MAX-ACCESS  read-write
    STATUS      current
    DESCRIPTION 
        "This counter reflects the number of times an unknown call type is blocked by a service provider"
    ::= { bwDXSOutgoingCallingPlanSPEntry 16 }

  bwDXSOCPSPNumSuccessfulAuthorizations OBJECT-TYPE
    SYNTAX      Counter32
    MAX-ACCESS  read-write
    STATUS      current
    DESCRIPTION 
        "This counter reflects the number of times a caller enters a valid authorization code in order to establish a call for a given service provider."
    ::= { bwDXSOutgoingCallingPlanSPEntry 17 }

  bwDXSOCPSPNumUnsuccessfulAuthorizations OBJECT-TYPE
    SYNTAX      Counter32
    MAX-ACCESS  read-write
    STATUS      current
    DESCRIPTION 
        "This counter reflects the number of times a caller enters an invalid authorization code in order to establish a call for a given service provider."
    ::= { bwDXSOutgoingCallingPlanSPEntry 18 }

  bwDXSOCPSPNumTransfers OBJECT-TYPE
    SYNTAX      Counter32
    MAX-ACCESS  read-write
    STATUS      current
    DESCRIPTION 
        "This counter reflects the number of times OCP transfers the caller to a number where the caller's request will be handled for a given service provider."
    ::= { bwDXSOutgoingCallingPlanSPEntry 19 }

  bwDXSOCPSACSPNumSuccessfulLock OBJECT-TYPE
    SYNTAX      Counter32
    MAX-ACCESS  read-write
    STATUS      current
    DESCRIPTION 
        "This counter reflects the number of times the SAC lock feature access code is used successfully in order to lock calls for a given service provider"
    ::= { bwDXSOutgoingCallingPlanSPEntry 20 }

  bwDXSOCPSACSPNumSuccessfulUnlock OBJECT-TYPE
    SYNTAX      Counter32
    MAX-ACCESS  read-write
    STATUS      current
    DESCRIPTION 
        "This counter reflects the number of times the SAC unlock feature access code is used successfully in order to unlock calls for a given service provider"
    ::= { bwDXSOutgoingCallingPlanSPEntry 21 }

  bwDXSOCPSACSPNumUnsuccessfulLock OBJECT-TYPE
    SYNTAX      Counter32
    MAX-ACCESS  read-write
    STATUS      current
    DESCRIPTION 
        "This counter reflects the number of times the SAC lock feature access code is used unsuccessfully for a given service provider"
    ::= { bwDXSOutgoingCallingPlanSPEntry 22 }

  bwDXSOCPSACSPNumUnsuccessfulUnlock OBJECT-TYPE
    SYNTAX      Counter32
    MAX-ACCESS  read-write
    STATUS      current
    DESCRIPTION 
        "This counter reflects the number of times the SAC unlock feature access code is used unsuccessfully for a given service provider"
    ::= { bwDXSOutgoingCallingPlanSPEntry 23 }

  bwDXSOCPSACSPNumUnsuccessfulCodeUsage OBJECT-TYPE
    SYNTAX      Counter32
    MAX-ACCESS  read-write
    STATUS      current
    DESCRIPTION 
        "This counter reflects the number of times a stored SAC code is erased from the database because it fails to pass EOCP screening following a change in the EOCP plan that makes the stored SAC code obsolete for a given service provider"
    ::= { bwDXSOutgoingCallingPlanSPEntry 24 }

  bwDXSOCPSPNumOutsideGroupTransferBlocks OBJECT-TYPE
    SYNTAX      Counter32
    MAX-ACCESS  read-write
    STATUS      current
    DESCRIPTION 
        "This counter reflects the number of times this service denies call forwarding or transfer to a party outside of the group for a given service provider."
    ::= { bwDXSOutgoingCallingPlanSPEntry 25 }

  bwDXSOutgoingCallingPlanGroupTable OBJECT-TYPE
    SYNTAX      SEQUENCE OF BwOutgoingCallingPlanGroupEntry
    MAX-ACCESS  not-accessible
    STATUS      current
    DESCRIPTION 
        "This table contains the counters for Outgoing Calling Plan service measurements for groups"
    ::= { outgoingCallingPlan 16 }

  bwDXSOutgoingCallingPlanGroupEntry OBJECT-TYPE
    SYNTAX      BwOutgoingCallingPlanGroupEntry
    MAX-ACCESS  not-accessible
    STATUS      current
    DESCRIPTION 
        "This row contains the counters for Outgoing Calling Plan service measurements for a group"
    INDEX       { bwDXSOutgoingCallingPlanGroupIndex }
    ::= { bwDXSOutgoingCallingPlanGroupTable 1 }

  BwOutgoingCallingPlanGroupEntry ::= SEQUENCE {
    bwDXSOutgoingCallingPlanGroupIndex                 Unsigned32,
    bwDXSOutgoingCallingPlanGroupID                    DisplayString,
    bwDXSOCPGroupNumGroupCallsBlocked                  Counter32,
    bwDXSOCPGroupNumLocalCallsBlocked                  Counter32,
    bwDXSOCPGroupNumTollFreeCallsBlocked               Counter32,
    bwDXSOCPGroupNumTollCallsBlocked                   Counter32,
    bwDXSOCPGroupNumIntlCallsBlocked                   Counter32,
    bwDXSOCPGroupNumOperatorAssistedCallsBlocked       Counter32,
    bwDXSOCPGroupNumChargeableDirAssistCallsBlocked    Counter32,
    bwDXSOCPGroupNumSpecialServices1CallsBlocked       Counter32,
    bwDXSOCPGroupNumSpecialServices2CallsBlocked       Counter32,
    bwDXSOCPGroupNumPremiumServices1CallsBlocked       Counter32,
    bwDXSOCPGroupNumPremiumServices2CallsBlocked       Counter32,
    bwDXSOCPGroupNumCasualCallsBlocked                 Counter32,
    bwDXSOCPGroupNumURLDialingCallsBlocked             Counter32,
    bwDXSOCPGroupNumUnknownCallsBlocked                Counter32,
    bwDXSOCPGroupNumSuccessfulAuthorizations           Counter32,
    bwDXSOCPGroupNumUnsuccessfulAuthorizations         Counter32,
    bwDXSOCPGroupNumTransfers                          Counter32,
    bwDXSOCPSACGroupNumSuccessfulLock                  Counter32,
    bwDXSOCPSACGroupNumSuccessfulUnlock                Counter32,
    bwDXSOCPSACGroupNumUnsuccessfulLock                Counter32,
    bwDXSOCPSACGroupNumUnsuccessfulUnlock              Counter32,
    bwDXSOCPSACGroupNumUnsuccessfulCodeUsage           Counter32,
    bwDXSOCPGroupNumOutsideGroupTransferBlocks         Counter32
  }

  bwDXSOutgoingCallingPlanGroupIndex OBJECT-TYPE
    SYNTAX      Unsigned32
    MAX-ACCESS  read-only
    STATUS      current
    DESCRIPTION 
        "This integer represents the a group index in the system"
    ::= { bwDXSOutgoingCallingPlanGroupEntry 1 }

  bwDXSOutgoingCallingPlanGroupID OBJECT-TYPE
    SYNTAX      DisplayString
    MAX-ACCESS  read-only
    STATUS      current
    DESCRIPTION 
        "This string represents a group ID"
    ::= { bwDXSOutgoingCallingPlanGroupEntry 2 }

  bwDXSOCPGroupNumGroupCallsBlocked OBJECT-TYPE
    SYNTAX      Counter32
    MAX-ACCESS  read-write
    STATUS      current
    DESCRIPTION 
        "This counter reflects the number of times an intra-group call is blocked by a group"
    ::= { bwDXSOutgoingCallingPlanGroupEntry 3 }

  bwDXSOCPGroupNumLocalCallsBlocked OBJECT-TYPE
    SYNTAX      Counter32
    MAX-ACCESS  read-write
    STATUS      current
    DESCRIPTION 
        "This counter reflects the number of times a local call is blocked by a group"
    ::= { bwDXSOutgoingCallingPlanGroupEntry 4 }

  bwDXSOCPGroupNumTollFreeCallsBlocked OBJECT-TYPE
    SYNTAX      Counter32
    MAX-ACCESS  read-write
    STATUS      current
    DESCRIPTION 
        "This counter reflects the number of times a toll free call is blocked by a group"
    ::= { bwDXSOutgoingCallingPlanGroupEntry 5 }

  bwDXSOCPGroupNumTollCallsBlocked OBJECT-TYPE
    SYNTAX      Counter32
    MAX-ACCESS  read-write
    STATUS      current
    DESCRIPTION 
        "This counter reflects the number of times a toll call is blocked by a group"
    ::= { bwDXSOutgoingCallingPlanGroupEntry 6 }

  bwDXSOCPGroupNumIntlCallsBlocked OBJECT-TYPE
    SYNTAX      Counter32
    MAX-ACCESS  read-write
    STATUS      current
    DESCRIPTION 
        "This counter reflects the number of times an international call is blocked by a group"
    ::= { bwDXSOutgoingCallingPlanGroupEntry 7 }

  bwDXSOCPGroupNumOperatorAssistedCallsBlocked OBJECT-TYPE
    SYNTAX      Counter32
    MAX-ACCESS  read-write
    STATUS      current
    DESCRIPTION 
        "This counter reflects the number of times an operator assisted call is blocked by a group"
    ::= { bwDXSOutgoingCallingPlanGroupEntry 8 }

  bwDXSOCPGroupNumChargeableDirAssistCallsBlocked OBJECT-TYPE
    SYNTAX      Counter32
    MAX-ACCESS  read-write
    STATUS      current
    DESCRIPTION 
        "This counter reflects the number of times a chargeable directory assistance call is blocked by a group"
    ::= { bwDXSOutgoingCallingPlanGroupEntry 9 }

  bwDXSOCPGroupNumSpecialServices1CallsBlocked OBJECT-TYPE
    SYNTAX      Counter32
    MAX-ACCESS  read-write
    STATUS      current
    DESCRIPTION 
        "This counter reflects the number of times a special services call is blocked by a group"
    ::= { bwDXSOutgoingCallingPlanGroupEntry 10 }

  bwDXSOCPGroupNumSpecialServices2CallsBlocked OBJECT-TYPE
    SYNTAX      Counter32
    MAX-ACCESS  read-write
    STATUS      current
    DESCRIPTION 
        "This counter reflects the number of times a special services call is blocked by a group"
    ::= { bwDXSOutgoingCallingPlanGroupEntry 11 }

  bwDXSOCPGroupNumPremiumServices1CallsBlocked OBJECT-TYPE
    SYNTAX      Counter32
    MAX-ACCESS  read-write
    STATUS      current
    DESCRIPTION 
        "This counter reflects the number of times a premium services call is blocked by a group"
    ::= { bwDXSOutgoingCallingPlanGroupEntry 12 }

  bwDXSOCPGroupNumPremiumServices2CallsBlocked OBJECT-TYPE
    SYNTAX      Counter32
    MAX-ACCESS  read-write
    STATUS      current
    DESCRIPTION 
        "This counter reflects the number of times a premium services call is blocked by a group"
    ::= { bwDXSOutgoingCallingPlanGroupEntry 13 }

  bwDXSOCPGroupNumCasualCallsBlocked OBJECT-TYPE
    SYNTAX      Counter32
    MAX-ACCESS  read-write
    STATUS      current
    DESCRIPTION 
        "This counter reflects the number of times a casual equal access call is blocked by a group"
    ::= { bwDXSOutgoingCallingPlanGroupEntry 14 }

  bwDXSOCPGroupNumURLDialingCallsBlocked OBJECT-TYPE
    SYNTAX      Counter32
    MAX-ACCESS  read-write
    STATUS      current
    DESCRIPTION 
        "This counter reflects the number of times a URL dialed call is blocked by a group"
    ::= { bwDXSOutgoingCallingPlanGroupEntry 15 }

  bwDXSOCPGroupNumUnknownCallsBlocked OBJECT-TYPE
    SYNTAX      Counter32
    MAX-ACCESS  read-write
    STATUS      current
    DESCRIPTION 
        "This counter reflects the number of times an unknown call type is blocked by a group"
    ::= { bwDXSOutgoingCallingPlanGroupEntry 16 }

  bwDXSOCPGroupNumSuccessfulAuthorizations OBJECT-TYPE
    SYNTAX      Counter32
    MAX-ACCESS  read-write
    STATUS      current
    DESCRIPTION 
        "This counter reflects the number of times a caller enters a valid authorization code in order to establish a call for a given group."
    ::= { bwDXSOutgoingCallingPlanGroupEntry 17 }

  bwDXSOCPGroupNumUnsuccessfulAuthorizations OBJECT-TYPE
    SYNTAX      Counter32
    MAX-ACCESS  read-write
    STATUS      current
    DESCRIPTION 
        "This counter reflects the number of times a caller enters an invalid authorization code in order to establish a call for a given group."
    ::= { bwDXSOutgoingCallingPlanGroupEntry 18 }

  bwDXSOCPGroupNumTransfers OBJECT-TYPE
    SYNTAX      Counter32
    MAX-ACCESS  read-write
    STATUS      current
    DESCRIPTION 
        "This counter reflects the number of times OCP transfers the caller to a number where the caller's request will be handled for a given group."
    ::= { bwDXSOutgoingCallingPlanGroupEntry 19 }

  bwDXSOCPSACGroupNumSuccessfulLock OBJECT-TYPE
    SYNTAX      Counter32
    MAX-ACCESS  read-write
    STATUS      current
    DESCRIPTION 
        "This counter reflects the number of times the SAC lock feature access code is used successfully in order to lock calls for a given group"
    ::= { bwDXSOutgoingCallingPlanGroupEntry 20 }

  bwDXSOCPSACGroupNumSuccessfulUnlock OBJECT-TYPE
    SYNTAX      Counter32
    MAX-ACCESS  read-write
    STATUS      current
    DESCRIPTION 
        "This counter reflects the number of times the SAC unlock feature access code is used successfully in order to unlock calls for a given group"
    ::= { bwDXSOutgoingCallingPlanGroupEntry 21 }

  bwDXSOCPSACGroupNumUnsuccessfulLock OBJECT-TYPE
    SYNTAX      Counter32
    MAX-ACCESS  read-write
    STATUS      current
    DESCRIPTION 
        "This counter reflects the number of times the SAC lock feature access code is used unsuccessfully for a given group"
    ::= { bwDXSOutgoingCallingPlanGroupEntry 22 }

  bwDXSOCPSACGroupNumUnsuccessfulUnlock OBJECT-TYPE
    SYNTAX      Counter32
    MAX-ACCESS  read-write
    STATUS      current
    DESCRIPTION 
        "This counter reflects the number of times the SAC unlock feature access code is used unsuccessfully for a given group"
    ::= { bwDXSOutgoingCallingPlanGroupEntry 23 }

  bwDXSOCPSACGroupNumUnsuccessfulCodeUsage OBJECT-TYPE
    SYNTAX      Counter32
    MAX-ACCESS  read-write
    STATUS      current
    DESCRIPTION 
        "This counter reflects the number of times a stored SAC code is erased from the database because it fails to pass EOCP screening following a change in the EOCP plan that makes the stored SAC code obsolete for a given group"
    ::= { bwDXSOutgoingCallingPlanGroupEntry 24 }

  bwDXSOCPGroupNumOutsideGroupTransferBlocks OBJECT-TYPE
    SYNTAX      Counter32
    MAX-ACCESS  read-write
    STATUS      current
    DESCRIPTION 
        "This counter reflects the number of times this service denies call forwarding or transfer to a party outside of the group for a given group."
    ::= { bwDXSOutgoingCallingPlanGroupEntry 25 }

  bwDXSOCPNumSuccessfulAuthorizations OBJECT-TYPE
    SYNTAX      Counter32
    MAX-ACCESS  read-write
    STATUS      current
    DESCRIPTION 
        "This counter reflects the number of times a caller enters a valid authorization code in order to establish a call."
    ::= { outgoingCallingPlan 17 }

  bwDXSOCPNumUnsuccessfulAuthorizations OBJECT-TYPE
    SYNTAX      Counter32
    MAX-ACCESS  read-write
    STATUS      current
    DESCRIPTION 
        "This counter reflects the number of times a caller enters an invalid authorization code in order to establish a call."
    ::= { outgoingCallingPlan 18 }

  bwDXSOCPNumTransfers OBJECT-TYPE
    SYNTAX      Counter32
    MAX-ACCESS  read-write
    STATUS      current
    DESCRIPTION 
        "This counter reflects the number of times OCP transfers the caller to a number where the caller's request will be handled."
    ::= { outgoingCallingPlan 19 }

  bwDXSOCPSACNumSuccessfulLock OBJECT-TYPE
    SYNTAX      Counter32
    MAX-ACCESS  read-write
    STATUS      current
    DESCRIPTION 
        "This counter reflects the number of times the SAC lock feature access code is used successfully in order to lock calls"
    ::= { outgoingCallingPlan 20 }

  bwDXSOCPSACNumSuccessfulUnlock OBJECT-TYPE
    SYNTAX      Counter32
    MAX-ACCESS  read-write
    STATUS      current
    DESCRIPTION 
        "This counter reflects the number of times the SAC unlock feature access code is used successfully in order to unlock calls"
    ::= { outgoingCallingPlan 21 }

  bwDXSOCPSACNumUnsuccessfulLock OBJECT-TYPE
    SYNTAX      Counter32
    MAX-ACCESS  read-write
    STATUS      current
    DESCRIPTION 
        "This counter reflects the number of times the SAC lock feature access code is used unsuccessfully"
    ::= { outgoingCallingPlan 22 }

  bwDXSOCPSACNumUnsuccessfulUnlock OBJECT-TYPE
    SYNTAX      Counter32
    MAX-ACCESS  read-write
    STATUS      current
    DESCRIPTION 
        "This counter reflects the number of times the SAC unlock feature access code is used unsuccessfully"
    ::= { outgoingCallingPlan 23 }

  bwDXSOCPSACNumUnsuccessfulCodeUsage OBJECT-TYPE
    SYNTAX      Counter32
    MAX-ACCESS  read-write
    STATUS      current
    DESCRIPTION 
        "This counter reflects the number of times a stored SAC code is erased from the database because it fails to pass EOCP screening following a change in the EOCP plan that makes the stored SAC code obsolete"
    ::= { outgoingCallingPlan 24 }

  bwDXSOCPNumOutsideGroupTransferBlocks OBJECT-TYPE
    SYNTAX      Counter32
    MAX-ACCESS  read-write
    STATUS      current
    DESCRIPTION 
        "This counter reflects the number of times this service denies call forwarding or transfer to a party outside of the group."
    ::= { outgoingCallingPlan 25 }

  bwDXSPriorityAlertNumDistinctive OBJECT-TYPE
    SYNTAX      Counter32
    MAX-ACCESS  read-write
    STATUS      current
    DESCRIPTION 
        "This counter reflects the number of times an incoming or waiting call has a priority
         tone applied"
    ::= { priorityAlert 1 }

  bwDXSPriorityAlertSPTable OBJECT-TYPE
    SYNTAX      SEQUENCE OF BwPriorityAlertSPEntry
    MAX-ACCESS  not-accessible
    STATUS      current
    DESCRIPTION 
        "This table contains the counters for Priority Alert service measurements for service providers"
    ::= { priorityAlert 2 }

  bwDXSPriorityAlertSPEntry OBJECT-TYPE
    SYNTAX      BwPriorityAlertSPEntry
    MAX-ACCESS  not-accessible
    STATUS      current
    DESCRIPTION 
        "This row contains the counters for Priority Alert service measurements for a service provider"
    INDEX       { bwDXSPriorityAlertSPIndex }
    ::= { bwDXSPriorityAlertSPTable 1 }

  BwPriorityAlertSPEntry ::= SEQUENCE {
    bwDXSPriorityAlertSPIndex              Unsigned32,
    bwDXSPriorityAlertSPID                 DisplayString,
    bwDXSPriorityAlertSPNumDistinctive     Counter32
  }

  bwDXSPriorityAlertSPIndex OBJECT-TYPE
    SYNTAX      Unsigned32
    MAX-ACCESS  read-only
    STATUS      current
    DESCRIPTION 
        "This integer represents the a service provider index in the system"
    ::= { bwDXSPriorityAlertSPEntry 1 }

  bwDXSPriorityAlertSPID OBJECT-TYPE
    SYNTAX      DisplayString
    MAX-ACCESS  read-only
    STATUS      current
    DESCRIPTION 
        "This string represents a service provider ID"
    ::= { bwDXSPriorityAlertSPEntry 2 }

  bwDXSPriorityAlertSPNumDistinctive OBJECT-TYPE
    SYNTAX      Counter32
    MAX-ACCESS  read-write
    STATUS      current
    DESCRIPTION 
        "This counter reflects the number of times an incoming or waiting call has a priority tone applied by a service provider"
    ::= { bwDXSPriorityAlertSPEntry 3 }

  bwDXSPriorityAlertGroupTable OBJECT-TYPE
    SYNTAX      SEQUENCE OF BwPriorityAlertGroupEntry
    MAX-ACCESS  not-accessible
    STATUS      current
    DESCRIPTION 
        "This table contains the counters for Priority Alert service measurements for groups"
    ::= { priorityAlert 3 }

  bwDXSPriorityAlertGroupEntry OBJECT-TYPE
    SYNTAX      BwPriorityAlertGroupEntry
    MAX-ACCESS  not-accessible
    STATUS      current
    DESCRIPTION 
        "This row contains the counters for Priority Alert service measurements for a group"
    INDEX       { bwDXSPriorityAlertGroupIndex }
    ::= { bwDXSPriorityAlertGroupTable 1 }

  BwPriorityAlertGroupEntry ::= SEQUENCE {
    bwDXSPriorityAlertGroupIndex           Unsigned32,
    bwDXSPriorityAlertGroupID              DisplayString,
    bwDXSPriorityAlertGroupNumDistinctive  Counter32
  }

  bwDXSPriorityAlertGroupIndex OBJECT-TYPE
    SYNTAX      Unsigned32
    MAX-ACCESS  read-only
    STATUS      current
    DESCRIPTION 
        "This integer represents the a group index in the system"
    ::= { bwDXSPriorityAlertGroupEntry 1 }

  bwDXSPriorityAlertGroupID OBJECT-TYPE
    SYNTAX      DisplayString
    MAX-ACCESS  read-only
    STATUS      current
    DESCRIPTION 
        "This string represents a group ID"
    ::= { bwDXSPriorityAlertGroupEntry 2 }

  bwDXSPriorityAlertGroupNumDistinctive OBJECT-TYPE
    SYNTAX      Counter32
    MAX-ACCESS  read-write
    STATUS      current
    DESCRIPTION 
        "This counter reflects the number of times an incoming or waiting call has a priority tone applied by a group"
    ::= { bwDXSPriorityAlertGroupEntry 3 }

  bwDXSSCANumAcceptances OBJECT-TYPE
    SYNTAX      Counter32
    MAX-ACCESS  read-write
    STATUS      current
    DESCRIPTION 
        "This counter reflects the number of times an incoming call meets a criteria for this
         service"
    ::= { selectiveCallAcceptance 1 }

  bwDXSSelectiveCallAcceptanceSPTable OBJECT-TYPE
    SYNTAX      SEQUENCE OF BwSelectiveCallAcceptanceSPEntry
    MAX-ACCESS  not-accessible
    STATUS      current
    DESCRIPTION 
        "This table contains the counters for Selective Call Acceptance service measurements for service providers"
    ::= { selectiveCallAcceptance 2 }

  bwDXSSelectiveCallAcceptanceSPEntry OBJECT-TYPE
    SYNTAX      BwSelectiveCallAcceptanceSPEntry
    MAX-ACCESS  not-accessible
    STATUS      current
    DESCRIPTION 
        "This row contains the counters for Selective Call Acceptance service measurements for a service provider"
    INDEX       { bwDXSSelectiveCallAcceptanceSPIndex }
    ::= { bwDXSSelectiveCallAcceptanceSPTable 1 }

  BwSelectiveCallAcceptanceSPEntry ::= SEQUENCE {
    bwDXSSelectiveCallAcceptanceSPIndex    Unsigned32,
    bwDXSSelectiveCallAcceptanceSPID       DisplayString,
    bwDXSSCASPNumAcceptances               Counter32
  }

  bwDXSSelectiveCallAcceptanceSPIndex OBJECT-TYPE
    SYNTAX      Unsigned32
    MAX-ACCESS  read-only
    STATUS      current
    DESCRIPTION 
        "This integer represents the a service provider index in the system"
    ::= { bwDXSSelectiveCallAcceptanceSPEntry 1 }

  bwDXSSelectiveCallAcceptanceSPID OBJECT-TYPE
    SYNTAX      DisplayString
    MAX-ACCESS  read-only
    STATUS      current
    DESCRIPTION 
        "This string represents a service provider ID"
    ::= { bwDXSSelectiveCallAcceptanceSPEntry 2 }

  bwDXSSCASPNumAcceptances OBJECT-TYPE
    SYNTAX      Counter32
    MAX-ACCESS  read-write
    STATUS      current
    DESCRIPTION 
        "This counter reflects the number of times an incoming call meets a criteria for this service by a service provider"
    ::= { bwDXSSelectiveCallAcceptanceSPEntry 3 }

  bwDXSSelectiveCallAcceptanceGroupTable OBJECT-TYPE
    SYNTAX      SEQUENCE OF BwSelectiveCallAcceptanceGroupEntry
    MAX-ACCESS  not-accessible
    STATUS      current
    DESCRIPTION 
        "This table contains the counters for Selective Call Acceptance service measurements for groups"
    ::= { selectiveCallAcceptance 3 }

  bwDXSSelectiveCallAcceptanceGroupEntry OBJECT-TYPE
    SYNTAX      BwSelectiveCallAcceptanceGroupEntry
    MAX-ACCESS  not-accessible
    STATUS      current
    DESCRIPTION 
        "This row contains the counters for Selective Call Acceptance service measurements for a group"
    INDEX       { bwDXSSelectiveCallAcceptanceGroupIndex }
    ::= { bwDXSSelectiveCallAcceptanceGroupTable 1 }

  BwSelectiveCallAcceptanceGroupEntry ::= SEQUENCE {
    bwDXSSelectiveCallAcceptanceGroupIndex     Unsigned32,
    bwDXSSelectiveCallAcceptanceGroupID        DisplayString,
    bwDXSSCAGroupNumAcceptances                Counter32
  }

  bwDXSSelectiveCallAcceptanceGroupIndex OBJECT-TYPE
    SYNTAX      Unsigned32
    MAX-ACCESS  read-only
    STATUS      current
    DESCRIPTION 
        "This integer represents the a group index in the system"
    ::= { bwDXSSelectiveCallAcceptanceGroupEntry 1 }

  bwDXSSelectiveCallAcceptanceGroupID OBJECT-TYPE
    SYNTAX      DisplayString
    MAX-ACCESS  read-only
    STATUS      current
    DESCRIPTION 
        "This string represents a group ID"
    ::= { bwDXSSelectiveCallAcceptanceGroupEntry 2 }

  bwDXSSCAGroupNumAcceptances OBJECT-TYPE
    SYNTAX      Counter32
    MAX-ACCESS  read-write
    STATUS      current
    DESCRIPTION 
        "This counter reflects the number of times an incoming call meets a criteria for this service by a group"
    ::= { bwDXSSelectiveCallAcceptanceGroupEntry 3 }

  bwDXSSCFNumForwards OBJECT-TYPE
    SYNTAX      Counter32
    MAX-ACCESS  read-write
    STATUS      current
    DESCRIPTION 
        "This counter reflects the number of times a criteria is met for this service"
    ::= { selectiveCallForward 1 }

  bwDXSSelectiveCallForwardSPTable OBJECT-TYPE
    SYNTAX      SEQUENCE OF BwSelectiveCallForwardSPEntry
    MAX-ACCESS  not-accessible
    STATUS      current
    DESCRIPTION 
        "This table contains the counters for Call Forwarding Selective service measurements for service providers"
    ::= { selectiveCallForward 2 }

  bwDXSSelectiveCallForwardSPEntry OBJECT-TYPE
    SYNTAX      BwSelectiveCallForwardSPEntry
    MAX-ACCESS  not-accessible
    STATUS      current
    DESCRIPTION 
        "This row contains the counters for Call Forwarding Selective service measurements for a service provider"
    INDEX       { bwDXSSelectiveCallForwardSPIndex }
    ::= { bwDXSSelectiveCallForwardSPTable 1 }

  BwSelectiveCallForwardSPEntry ::= SEQUENCE {
    bwDXSSelectiveCallForwardSPIndex   Unsigned32,
    bwDXSSelectiveCallForwardSPID      DisplayString,
    bwDXSSCFSPNumForwards              Counter32,
    bwDXSSCFSPNumPhoneActivations      Counter32,
    bwDXSSCFSPNumPhoneDeactivations    Counter32
  }

  bwDXSSelectiveCallForwardSPIndex OBJECT-TYPE
    SYNTAX      Unsigned32
    MAX-ACCESS  read-only
    STATUS      current
    DESCRIPTION 
        "This integer represents the a service provider index in the system"
    ::= { bwDXSSelectiveCallForwardSPEntry 1 }

  bwDXSSelectiveCallForwardSPID OBJECT-TYPE
    SYNTAX      DisplayString
    MAX-ACCESS  read-only
    STATUS      current
    DESCRIPTION 
        "This string represents a service provider ID"
    ::= { bwDXSSelectiveCallForwardSPEntry 2 }

  bwDXSSCFSPNumForwards OBJECT-TYPE
    SYNTAX      Counter32
    MAX-ACCESS  read-write
    STATUS      current
    DESCRIPTION 
        "This counter reflects the number of times a criteria is met for this service by a service provider"
    ::= { bwDXSSelectiveCallForwardSPEntry 3 }

  bwDXSSCFSPNumPhoneActivations OBJECT-TYPE
    SYNTAX      Counter32
    MAX-ACCESS  read-write
    STATUS      current
    DESCRIPTION 
        "This is the number of times SCF has been activated via FAC for users in a given service provider."
    ::= { bwDXSSelectiveCallForwardSPEntry 4 }

  bwDXSSCFSPNumPhoneDeactivations OBJECT-TYPE
    SYNTAX      Counter32
    MAX-ACCESS  read-write
    STATUS      current
    DESCRIPTION 
        "This is the number of times SCF has been deactivated via FAC for users in a given service provider."
    ::= { bwDXSSelectiveCallForwardSPEntry 5 }

  bwDXSSelectiveCallForwardGroupTable OBJECT-TYPE
    SYNTAX      SEQUENCE OF BwSelectiveCallForwardGroupEntry
    MAX-ACCESS  not-accessible
    STATUS      current
    DESCRIPTION 
        "This table contains the counters for Call Forwarding Selective service measurements for groups"
    ::= { selectiveCallForward 3 }

  bwDXSSelectiveCallForwardGroupEntry OBJECT-TYPE
    SYNTAX      BwSelectiveCallForwardGroupEntry
    MAX-ACCESS  not-accessible
    STATUS      current
    DESCRIPTION 
        "This row contains the counters for Call Forwarding Selective service measurements for a group"
    INDEX       { bwDXSSelectiveCallForwardGroupIndex }
    ::= { bwDXSSelectiveCallForwardGroupTable 1 }

  BwSelectiveCallForwardGroupEntry ::= SEQUENCE {
    bwDXSSelectiveCallForwardGroupIndex    Unsigned32,
    bwDXSSelectiveCallForwardGroupID       DisplayString,
    bwDXSSCFGroupNumForwards               Counter32,
    bwDXSSCFGroupNumPhoneActivations       Counter32,
    bwDXSSCFGroupNumPhoneDeactivations     Counter32
  }

  bwDXSSelectiveCallForwardGroupIndex OBJECT-TYPE
    SYNTAX      Unsigned32
    MAX-ACCESS  read-only
    STATUS      current
    DESCRIPTION 
        "This integer represents the a group index in the system"
    ::= { bwDXSSelectiveCallForwardGroupEntry 1 }

  bwDXSSelectiveCallForwardGroupID OBJECT-TYPE
    SYNTAX      DisplayString
    MAX-ACCESS  read-only
    STATUS      current
    DESCRIPTION 
        "This string represents a group ID"
    ::= { bwDXSSelectiveCallForwardGroupEntry 2 }

  bwDXSSCFGroupNumForwards OBJECT-TYPE
    SYNTAX      Counter32
    MAX-ACCESS  read-write
    STATUS      current
    DESCRIPTION 
        "This counter reflects the number of times a criteria is met for this service by a group"
    ::= { bwDXSSelectiveCallForwardGroupEntry 3 }

  bwDXSSCFGroupNumPhoneActivations OBJECT-TYPE
    SYNTAX      Counter32
    MAX-ACCESS  read-write
    STATUS      current
    DESCRIPTION 
        "TThis is the number of times SCF has been activated via FAC for users in a given group."
    ::= { bwDXSSelectiveCallForwardGroupEntry 4 }

  bwDXSSCFGroupNumPhoneDeactivations OBJECT-TYPE
    SYNTAX      Counter32
    MAX-ACCESS  read-write
    STATUS      current
    DESCRIPTION 
        "This is the number of times SCF has been deactivated via FAC for users in a given group."
    ::= { bwDXSSelectiveCallForwardGroupEntry 5 }

  bwDXSSCFNumPhoneActivations OBJECT-TYPE
    SYNTAX      Counter32
    MAX-ACCESS  read-write
    STATUS      current
    DESCRIPTION 
        "This is the number of times SCF has been activated via FAC."
    ::= { selectiveCallForward 4 }

  bwDXSSCFNumPhoneDeactivations OBJECT-TYPE
    SYNTAX      Counter32
    MAX-ACCESS  read-write
    STATUS      current
    DESCRIPTION 
        "This is the number of times SCF has been deactivated via FAC."
    ::= { selectiveCallForward 5 }

  bwDXSSCRNumRejects OBJECT-TYPE
    SYNTAX      Counter32
    MAX-ACCESS  read-write
    STATUS      current
    DESCRIPTION 
        "This counter reflects the number of times an incoming call meets a criteria for this
         service"
    ::= { selectiveCallRejection 1 }

  bwDXSSelectiveCallRejectionSPTable OBJECT-TYPE
    SYNTAX      SEQUENCE OF BwSelectiveCallRejectionSPEntry
    MAX-ACCESS  not-accessible
    STATUS      current
    DESCRIPTION 
        "This table contains the counters for Selective Call Rejection service measurements for service providers"
    ::= { selectiveCallRejection 2 }

  bwDXSSelectiveCallRejectionSPEntry OBJECT-TYPE
    SYNTAX      BwSelectiveCallRejectionSPEntry
    MAX-ACCESS  not-accessible
    STATUS      current
    DESCRIPTION 
        "This row contains the counters for Selective Call Rejection service measurements for a service provider"
    INDEX       { bwDXSSelectiveCallRejectionSPIndex }
    ::= { bwDXSSelectiveCallRejectionSPTable 1 }

  BwSelectiveCallRejectionSPEntry ::= SEQUENCE {
    bwDXSSelectiveCallRejectionSPIndex     Unsigned32,
    bwDXSSelectiveCallRejectionSPID        DisplayString,
    bwDXSSCRSPNumRejects                   Counter32
  }

  bwDXSSelectiveCallRejectionSPIndex OBJECT-TYPE
    SYNTAX      Unsigned32
    MAX-ACCESS  read-only
    STATUS      current
    DESCRIPTION 
        "This integer represents the a service provider index in the system"
    ::= { bwDXSSelectiveCallRejectionSPEntry 1 }

  bwDXSSelectiveCallRejectionSPID OBJECT-TYPE
    SYNTAX      DisplayString
    MAX-ACCESS  read-only
    STATUS      current
    DESCRIPTION 
        "This string represents a service provider ID"
    ::= { bwDXSSelectiveCallRejectionSPEntry 2 }

  bwDXSSCRSPNumRejects OBJECT-TYPE
    SYNTAX      Counter32
    MAX-ACCESS  read-write
    STATUS      current
    DESCRIPTION 
        "This counter reflects the number of times an incoming call meets a criteria for this service by a service provider"
    ::= { bwDXSSelectiveCallRejectionSPEntry 3 }

  bwDXSSelectiveCallRejectionGroupTable OBJECT-TYPE
    SYNTAX      SEQUENCE OF BwSelectiveCallRejectionGroupEntry
    MAX-ACCESS  not-accessible
    STATUS      current
    DESCRIPTION 
        "This table contains the counters for Selective Call Rejection service measurements for groups"
    ::= { selectiveCallRejection 3 }

  bwDXSSelectiveCallRejectionGroupEntry OBJECT-TYPE
    SYNTAX      BwSelectiveCallRejectionGroupEntry
    MAX-ACCESS  not-accessible
    STATUS      current
    DESCRIPTION 
        "This row contains the counters for Selective Call Rejection service measurements for a group"
    INDEX       { bwDXSSelectiveCallRejectionGroupIndex }
    ::= { bwDXSSelectiveCallRejectionGroupTable 1 }

  BwSelectiveCallRejectionGroupEntry ::= SEQUENCE {
    bwDXSSelectiveCallRejectionGroupIndex  Unsigned32,
    bwDXSSelectiveCallRejectionGroupID     DisplayString,
    bwDXSSCRGroupNumRejects                Counter32
  }

  bwDXSSelectiveCallRejectionGroupIndex OBJECT-TYPE
    SYNTAX      Unsigned32
    MAX-ACCESS  read-only
    STATUS      current
    DESCRIPTION 
        "This integer represents the a group index in the system"
    ::= { bwDXSSelectiveCallRejectionGroupEntry 1 }

  bwDXSSelectiveCallRejectionGroupID OBJECT-TYPE
    SYNTAX      DisplayString
    MAX-ACCESS  read-only
    STATUS      current
    DESCRIPTION 
        "This string represents a group ID"
    ::= { bwDXSSelectiveCallRejectionGroupEntry 2 }

  bwDXSSCRGroupNumRejects OBJECT-TYPE
    SYNTAX      Counter32
    MAX-ACCESS  read-write
    STATUS      current
    DESCRIPTION 
        "This counter reflects the number of times an incoming call meets a criteria for this service by a group"
    ::= { bwDXSSelectiveCallRejectionGroupEntry 3 }

  bwDXSSimRingPersonalNumAttempts OBJECT-TYPE
    SYNTAX      Counter32
    MAX-ACCESS  read-write
    STATUS      current
    DESCRIPTION 
        "This counter reflects the number of times an incoming call attempt is received"
    ::= { simRingPersonal 1 }

  bwDXSSimRingPersonalNumBusy OBJECT-TYPE
    SYNTAX      Counter32
    MAX-ACCESS  read-write
    STATUS      current
    DESCRIPTION 
        "This counter reflects the number of times that all parties to whom call delivery attempts
         are made, are busy"
    ::= { simRingPersonal 2 }

  bwDXSSimRingPersonalSPTable OBJECT-TYPE
    SYNTAX      SEQUENCE OF BwSimRingPersonalSPEntry
    MAX-ACCESS  not-accessible
    STATUS      current
    DESCRIPTION 
        "This table contains the counters for Simultaneous Ring Personal service measurements for service providers"
    ::= { simRingPersonal 3 }

  bwDXSSimRingPersonalSPEntry OBJECT-TYPE
    SYNTAX      BwSimRingPersonalSPEntry
    MAX-ACCESS  not-accessible
    STATUS      current
    DESCRIPTION 
        "This row contains the counters for Simultaneous Ring Personal service measurements for a service provider"
    INDEX       { bwDXSSimRingPersonalSPIndex }
    ::= { bwDXSSimRingPersonalSPTable 1 }

  BwSimRingPersonalSPEntry ::= SEQUENCE {
    bwDXSSimRingPersonalSPIndex        Unsigned32,
    bwDXSSimRingPersonalSPID           DisplayString,
    bwDXSSimRingPersonalSPNumAttempts  Counter32,
    bwDXSSimRingPersonalSPNumBusy      Counter32
  }

  bwDXSSimRingPersonalSPIndex OBJECT-TYPE
    SYNTAX      Unsigned32
    MAX-ACCESS  read-only
    STATUS      current
    DESCRIPTION 
        "This integer represents the a service provider index in the system"
    ::= { bwDXSSimRingPersonalSPEntry 1 }

  bwDXSSimRingPersonalSPID OBJECT-TYPE
    SYNTAX      DisplayString
    MAX-ACCESS  read-only
    STATUS      current
    DESCRIPTION 
        "This string represents a service provider ID"
    ::= { bwDXSSimRingPersonalSPEntry 2 }

  bwDXSSimRingPersonalSPNumAttempts OBJECT-TYPE
    SYNTAX      Counter32
    MAX-ACCESS  read-write
    STATUS      current
    DESCRIPTION 
        "This counter reflects the number of times an incoming call attempt is received by a service provider"
    ::= { bwDXSSimRingPersonalSPEntry 3 }

  bwDXSSimRingPersonalSPNumBusy OBJECT-TYPE
    SYNTAX      Counter32
    MAX-ACCESS  read-write
    STATUS      current
    DESCRIPTION 
        "This counter reflects the number of times that all parties to whom call delivery attempts are made by a service provider, are busy"
    ::= { bwDXSSimRingPersonalSPEntry 4 }

  bwDXSSimRingPersonalGroupTable OBJECT-TYPE
    SYNTAX      SEQUENCE OF BwSimRingPersonalGroupEntry
    MAX-ACCESS  not-accessible
    STATUS      current
    DESCRIPTION 
        "This table contains the counters for Simultaneous Ring Personal service measurements for groups"
    ::= { simRingPersonal 4 }

  bwDXSSimRingPersonalGroupEntry OBJECT-TYPE
    SYNTAX      BwSimRingPersonalGroupEntry
    MAX-ACCESS  not-accessible
    STATUS      current
    DESCRIPTION 
        "This row contains the counters for Simultaneous Ring Personal service measurements for a group"
    INDEX       { bwDXSSimRingPersonalGroupIndex }
    ::= { bwDXSSimRingPersonalGroupTable 1 }

  BwSimRingPersonalGroupEntry ::= SEQUENCE {
    bwDXSSimRingPersonalGroupIndex         Unsigned32,
    bwDXSSimRingPersonalGroupID            DisplayString,
    bwDXSSimRingPersonalGroupNumAttempts   Counter32,
    bwDXSSimRingPersonalGroupNumBusy       Counter32
  }

  bwDXSSimRingPersonalGroupIndex OBJECT-TYPE
    SYNTAX      Unsigned32
    MAX-ACCESS  read-only
    STATUS      current
    DESCRIPTION 
        "This integer represents the a group index in the system"
    ::= { bwDXSSimRingPersonalGroupEntry 1 }

  bwDXSSimRingPersonalGroupID OBJECT-TYPE
    SYNTAX      DisplayString
    MAX-ACCESS  read-only
    STATUS      current
    DESCRIPTION 
        "This string represents a group ID"
    ::= { bwDXSSimRingPersonalGroupEntry 2 }

  bwDXSSimRingPersonalGroupNumAttempts OBJECT-TYPE
    SYNTAX      Counter32
    MAX-ACCESS  read-write
    STATUS      current
    DESCRIPTION 
        "This counter reflects the number of times an incoming call attempt is received by a group"
    ::= { bwDXSSimRingPersonalGroupEntry 3 }

  bwDXSSimRingPersonalGroupNumBusy OBJECT-TYPE
    SYNTAX      Counter32
    MAX-ACCESS  read-write
    STATUS      current
    DESCRIPTION 
        "This counter reflects the number of times that all parties to whom call delivery attempts are made by a group, are busy"
    ::= { bwDXSSimRingPersonalGroupEntry 4 }

  bwDXSVMNumBusyGreetingsPlayed OBJECT-TYPE
    SYNTAX      Counter32
    MAX-ACCESS  read-write
    STATUS      current
    DESCRIPTION 
        "This counter reflects the number of times a busy greeting is played to a caller"
    ::= { voiceMessaging 1 }

  bwDXSVMNumNoAnswerGreetingsPlayed OBJECT-TYPE
    SYNTAX      Counter32
    MAX-ACCESS  read-write
    STATUS      current
    DESCRIPTION 
        "This counter reflects the number of times a no answer greeting is played"
    ::= { voiceMessaging 2 }

  bwDXSVMNumMessagesLeft OBJECT-TYPE
    SYNTAX      Counter32
    MAX-ACCESS  read-write
    STATUS      current
    DESCRIPTION 
        "This counter reflects the number of times a voice message is recorded"
    ::= { voiceMessaging 3 }

  bwDXSVMRNumBusyGreetingsRecorded OBJECT-TYPE
    SYNTAX      Counter32
    MAX-ACCESS  read-write
    STATUS      current
    DESCRIPTION 
        "This counter reflects the number of times a busy greeting is recorded over the phone"
    ::= { voiceMessaging 4 }

  bwDXSVMRNumNoAnswerGreetingsRecorded OBJECT-TYPE
    SYNTAX      Counter32
    MAX-ACCESS  read-write
    STATUS      current
    DESCRIPTION 
        "This counter reflects the number of times a no answer greeting is recorded over the
         phone"
    ::= { voiceMessaging 5 }

  bwDXSVMRNumPersonalizedNamesRecorded OBJECT-TYPE
    SYNTAX      Counter32
    MAX-ACCESS  read-write
    STATUS      current
    DESCRIPTION 
        "This counter reflects the number of times a personalized name greeting is recorded
         over the phone"
    ::= { voiceMessaging 6 }

  bwDXSVMRNumLoginAttempts OBJECT-TYPE
    SYNTAX      Counter32
    MAX-ACCESS  read-write
    STATUS      current
    DESCRIPTION 
        "This counter reflects the number of times a user attempts a login over the phone"
    ::= { voiceMessaging 7 }

  bwDXSVMRNumLoginFailures OBJECT-TYPE
    SYNTAX      Counter32
    MAX-ACCESS  read-write
    STATUS      current
    DESCRIPTION 
        "This counter reflects the number of times a user login attempt fails"
    ::= { voiceMessaging 8 }

  bwDXSVMRNumComposeSendAttempts OBJECT-TYPE
    SYNTAX      Counter32
    MAX-ACCESS  read-write
    STATUS      current
    DESCRIPTION 
        "This counter reflects the number of times a composed message is sent to a user"
    ::= { voiceMessaging 9 }

  bwDXSVMRNumComposeSendGroupAttempts OBJECT-TYPE
    SYNTAX      Counter32
    MAX-ACCESS  read-write
    STATUS      current
    DESCRIPTION 
        "This counter reflects the number of times a composed message is sent to a group"
    ::= { voiceMessaging 10 }

  bwDXSVMRNumForwardSendAttempts OBJECT-TYPE
    SYNTAX      Counter32
    MAX-ACCESS  read-write
    STATUS      current
    DESCRIPTION 
        "This counter reflects the number of times a forwarded message is sent to a user"
    ::= { voiceMessaging 11 }

  bwDXSVMRNumForwardSendGroupAttempts OBJECT-TYPE
    SYNTAX      Counter32
    MAX-ACCESS  read-write
    STATUS      current
    DESCRIPTION 
        "This counter reflects the number of times a forwarded message is sent to a group"
    ::= { voiceMessaging 12 }

  bwDXSVMRNumReplySendAttempts OBJECT-TYPE
    SYNTAX      Counter32
    MAX-ACCESS  read-write
    STATUS      current
    DESCRIPTION 
        "This counter reflects the number of times a message reply is sent"
    ::= { voiceMessaging 13 }

  bwDXSVMRNumSendFailed OBJECT-TYPE
    SYNTAX      Counter32
    MAX-ACCESS  read-write
    STATUS      current
    DESCRIPTION 
        "This counter reflects the number of times an attempt to send a message to a user failed"
    ::= { voiceMessaging 14 }

  bwDXSVMRNumSendGroupFailed OBJECT-TYPE
    SYNTAX      Counter32
    MAX-ACCESS  read-write
    STATUS      current
    DESCRIPTION 
        "This counter reflects the number of times an attempt to send a message to a group failed"
    ::= { voiceMessaging 15 }

  bwDXSVMRDeleteAllMsgsAttempts OBJECT-TYPE
    SYNTAX      Counter32
    MAX-ACCESS  read-write
    STATUS      current
    DESCRIPTION 
        "This counter reflects the number of times a user attempts to delete all messages"
    ::= { voiceMessaging 16 }

  bwDXSVMRCallBackAttempts OBJECT-TYPE
    SYNTAX      Counter32
    MAX-ACCESS  read-write
    STATUS      current
    DESCRIPTION 
        "This counter reflects the number of times a user attempts to callback the caller"
    ::= { voiceMessaging 17 }

  bwDXSVPNumAABusHoursGreetingRecorded OBJECT-TYPE
    SYNTAX      Counter32
    MAX-ACCESS  read-write
    STATUS      current
    DESCRIPTION 
        "This counter reflects the number of times an AA business hours greeting is recorded over the phone"
    ::= { voiceMessaging 19 }

  bwDXSVPNumAAAfterHoursGreetingRecorded OBJECT-TYPE
    SYNTAX      Counter32
    MAX-ACCESS  read-write
    STATUS      current
    DESCRIPTION 
        "This counter reflects the number of times an AA after hours greeting is recorded over the phone"
    ::= { voiceMessaging 20 }

  bwDXSVPNumCFADestinationChanged OBJECT-TYPE
    SYNTAX      Counter32
    MAX-ACCESS  read-write
    STATUS      current
    DESCRIPTION 
        "This counter reflects the number of times a CFA destination is changed over the phone"
    ::= { voiceMessaging 21 }

  bwDXSVPNumPasscodeChanged OBJECT-TYPE
    SYNTAX      Counter32
    MAX-ACCESS  read-write
    STATUS      current
    DESCRIPTION 
        "This counter reflects the number of times a Voice Portal passcode is changed over the phone"
    ::= { voiceMessaging 22 }

  bwDXSVoiceMessagingSPTable OBJECT-TYPE
    SYNTAX      SEQUENCE OF BwVoiceMessagingSPEntry
    MAX-ACCESS  not-accessible
    STATUS      current
    DESCRIPTION 
        "This table contains the counters for Voice Messaging service measurements for service providers"
    ::= { voiceMessaging 23 }

  bwDXSVoiceMessagingSPEntry OBJECT-TYPE
    SYNTAX      BwVoiceMessagingSPEntry
    MAX-ACCESS  not-accessible
    STATUS      current
    DESCRIPTION 
        "This row contains the counters for Voice Messaging service measurements for a service provider"
    INDEX       { bwDXSVoiceMessagingSPIndex }
    ::= { bwDXSVoiceMessagingSPTable 1 }

  BwVoiceMessagingSPEntry ::= SEQUENCE {
    bwDXSVoiceMessagingSPIndex                     Unsigned32,
    bwDXSVoiceMessagingSPID                        DisplayString,
    bwDXSVMSPNumBusyGreetingsPlayed                Counter32,
    bwDXSVMSPNumNoAnswerGreetingsPlayed            Counter32,
    bwDXSVMSPNumMessagesLeft                       Counter32,
    bwDXSVMRSPNumBusyGreetingsRecorded             Counter32,
    bwDXSVMRSPNumNoAnswerGreetingsRecorded         Counter32,
    bwDXSVMRSPNumPersonalizedNamesRecorded         Counter32,
    bwDXSVMRSPNumLoginAttempts                     Counter32,
    bwDXSVMRSPNumLoginFailures                     Counter32,
    bwDXSVMRSPNumComposeSendAttempts               Counter32,
    bwDXSVMRSPNumComposeSendGroupAttempts          Counter32,
    bwDXSVMRSPNumForwardSendAttempts               Counter32,
    bwDXSVMRSPNumForwardSendGroupAttempts          Counter32,
    bwDXSVMRSPNumReplySendAttempts                 Counter32,
    bwDXSVMRSPNumSendFailed                        Counter32,
    bwDXSVMRSPNumSendGroupFailed                   Counter32,
    bwDXSVMRSPDeleteAllMsgsAttempts                Counter32,
    bwDXSVMRSPCallBackAttempts                     Counter32,
    bwDXSVPSPNumAABusHoursGreetingRecorded         Counter32,
    bwDXSVPSPNumAAAfterHoursGreetingRecorded       Counter32,
    bwDXSVPSPNumCFADestinationChanged              Counter32,
    bwDXSVPSPNumPasscodeChanged                    Counter32,
    bwDXSVMRSPNumComposeSendListAttempts           Counter32,
    bwDXSVMRSPNumForwardSendListAttempts           Counter32,
    bwDXSVMRSPNumSendListFailed                    Counter32,
    bwDXSVPSPGreetingRecorded                      Counter32,
    bwDXSVMSPGreetingRecorded                      Counter32,
    bwDXSVPCSPCall                                 Counter32,
    bwDXSSPMultiMediaMsgDeposit                    Counter32,
    bwDXSVMSPMultiMediaGreetingRecorded            Counter32,
    bwDXSAutoAttendantSPMultiMediaPromptRecorded   Counter32,
    bwDXSMessagingSPQuery                          Counter32,
    bwDXSMessagingSPQueryNoUser                    Counter32,
    bwDXSMessagingSPQueryNoMailbox                 Counter32
  }

  bwDXSVoiceMessagingSPIndex OBJECT-TYPE
    SYNTAX      Unsigned32
    MAX-ACCESS  read-only
    STATUS      current
    DESCRIPTION 
        "This integer represents the a service provider index in the system"
    ::= { bwDXSVoiceMessagingSPEntry 1 }

  bwDXSVoiceMessagingSPID OBJECT-TYPE
    SYNTAX      DisplayString
    MAX-ACCESS  read-only
    STATUS      current
    DESCRIPTION 
        "This string represents a service provider ID"
    ::= { bwDXSVoiceMessagingSPEntry 2 }

  bwDXSVMSPNumBusyGreetingsPlayed OBJECT-TYPE
    SYNTAX      Counter32
    MAX-ACCESS  read-write
    STATUS      current
    DESCRIPTION 
        "This counter reflects the number of times a busy greeting is played to a caller by a service provider"
    ::= { bwDXSVoiceMessagingSPEntry 3 }

  bwDXSVMSPNumNoAnswerGreetingsPlayed OBJECT-TYPE
    SYNTAX      Counter32
    MAX-ACCESS  read-write
    STATUS      current
    DESCRIPTION 
        "This counter reflects the number of times a no answer greeting is played by a service provider"
    ::= { bwDXSVoiceMessagingSPEntry 4 }

  bwDXSVMSPNumMessagesLeft OBJECT-TYPE
    SYNTAX      Counter32
    MAX-ACCESS  read-write
    STATUS      current
    DESCRIPTION 
        "This counter reflects the number of times a voice message is recorded by a service provider"
    ::= { bwDXSVoiceMessagingSPEntry 5 }

  bwDXSVMRSPNumBusyGreetingsRecorded OBJECT-TYPE
    SYNTAX      Counter32
    MAX-ACCESS  read-write
    STATUS      current
    DESCRIPTION 
        "This counter reflects the number of times a busy greeting is recorded over the phone by a service provider"
    ::= { bwDXSVoiceMessagingSPEntry 6 }

  bwDXSVMRSPNumNoAnswerGreetingsRecorded OBJECT-TYPE
    SYNTAX      Counter32
    MAX-ACCESS  read-write
    STATUS      current
    DESCRIPTION 
        "This counter reflects the number of times a no answer greeting is recorded over the phone by a service provider"
    ::= { bwDXSVoiceMessagingSPEntry 7 }

  bwDXSVMRSPNumPersonalizedNamesRecorded OBJECT-TYPE
    SYNTAX      Counter32
    MAX-ACCESS  read-write
    STATUS      current
    DESCRIPTION 
        "This counter reflects the number of times a personalized name greeting is recorded over the phone by a service provider"
    ::= { bwDXSVoiceMessagingSPEntry 8 }

  bwDXSVMRSPNumLoginAttempts OBJECT-TYPE
    SYNTAX      Counter32
    MAX-ACCESS  read-write
    STATUS      current
    DESCRIPTION 
        "This counter reflects the number of times a user attempts a login over the phone by a service provider"
    ::= { bwDXSVoiceMessagingSPEntry 9 }

  bwDXSVMRSPNumLoginFailures OBJECT-TYPE
    SYNTAX      Counter32
    MAX-ACCESS  read-write
    STATUS      current
    DESCRIPTION 
        "This counter reflects the number of times a user login attempt fails by a service provider"
    ::= { bwDXSVoiceMessagingSPEntry 10 }

  bwDXSVMRSPNumComposeSendAttempts OBJECT-TYPE
    SYNTAX      Counter32
    MAX-ACCESS  read-write
    STATUS      current
    DESCRIPTION 
        "This counter reflects the number of times a composed message is sent to a user by a service provider"
    ::= { bwDXSVoiceMessagingSPEntry 11 }

  bwDXSVMRSPNumComposeSendGroupAttempts OBJECT-TYPE
    SYNTAX      Counter32
    MAX-ACCESS  read-write
    STATUS      current
    DESCRIPTION 
        "This counter reflects the number of times a composed message is sent to a group by a service provider"
    ::= { bwDXSVoiceMessagingSPEntry 12 }

  bwDXSVMRSPNumForwardSendAttempts OBJECT-TYPE
    SYNTAX      Counter32
    MAX-ACCESS  read-write
    STATUS      current
    DESCRIPTION 
        "This counter reflects the number of times a forwarded message is sent to a user by a service provider"
    ::= { bwDXSVoiceMessagingSPEntry 13 }

  bwDXSVMRSPNumForwardSendGroupAttempts OBJECT-TYPE
    SYNTAX      Counter32
    MAX-ACCESS  read-write
    STATUS      current
    DESCRIPTION 
        "This counter reflects the number of times a forwarded message is sent to a group by a service provider"
    ::= { bwDXSVoiceMessagingSPEntry 14 }

  bwDXSVMRSPNumReplySendAttempts OBJECT-TYPE
    SYNTAX      Counter32
    MAX-ACCESS  read-write
    STATUS      current
    DESCRIPTION 
        "This counter reflects the number of times a message reply is sent by a service provider"
    ::= { bwDXSVoiceMessagingSPEntry 15 }

  bwDXSVMRSPNumSendFailed OBJECT-TYPE
    SYNTAX      Counter32
    MAX-ACCESS  read-write
    STATUS      current
    DESCRIPTION 
        "This counter reflects the number of times an attempt to send a message to a user failed by a service provider"
    ::= { bwDXSVoiceMessagingSPEntry 16 }

  bwDXSVMRSPNumSendGroupFailed OBJECT-TYPE
    SYNTAX      Counter32
    MAX-ACCESS  read-write
    STATUS      current
    DESCRIPTION 
        "This counter reflects the number of times an attempt to send a message to a group failed by a service provider"
    ::= { bwDXSVoiceMessagingSPEntry 17 }

  bwDXSVMRSPDeleteAllMsgsAttempts OBJECT-TYPE
    SYNTAX      Counter32
    MAX-ACCESS  read-write
    STATUS      current
    DESCRIPTION 
        "This counter reflects the number of times a user attempts to delete all messages by a service provider"
    ::= { bwDXSVoiceMessagingSPEntry 18 }

  bwDXSVMRSPCallBackAttempts OBJECT-TYPE
    SYNTAX      Counter32
    MAX-ACCESS  read-write
    STATUS      current
    DESCRIPTION 
        "This counter reflects the number of times a user attempts to callback the caller by a service provider"
    ::= { bwDXSVoiceMessagingSPEntry 19 }

  bwDXSVPSPNumAABusHoursGreetingRecorded OBJECT-TYPE
    SYNTAX      Counter32
    MAX-ACCESS  read-write
    STATUS      current
    DESCRIPTION 
        "This counter reflects the number of times an AA business hours greeting is recorded over the phone by a service provider"
    ::= { bwDXSVoiceMessagingSPEntry 21 }

  bwDXSVPSPNumAAAfterHoursGreetingRecorded OBJECT-TYPE
    SYNTAX      Counter32
    MAX-ACCESS  read-write
    STATUS      current
    DESCRIPTION 
        "This counter reflects the number of times an AA after hours greeting is recorded over the phone by a service provider"
    ::= { bwDXSVoiceMessagingSPEntry 22 }

  bwDXSVPSPNumCFADestinationChanged OBJECT-TYPE
    SYNTAX      Counter32
    MAX-ACCESS  read-write
    STATUS      current
    DESCRIPTION 
        "This counter reflects the number of times a CFA destination is changed over the phone by a service provider"
    ::= { bwDXSVoiceMessagingSPEntry 23 }

  bwDXSVPSPNumPasscodeChanged OBJECT-TYPE
    SYNTAX      Counter32
    MAX-ACCESS  read-write
    STATUS      current
    DESCRIPTION 
        "This counter reflects the number of times a Voice Portal is changed over the phone by a service provider"
    ::= { bwDXSVoiceMessagingSPEntry 24 }

  bwDXSVMRSPNumComposeSendListAttempts OBJECT-TYPE
    SYNTAX      Counter32
    MAX-ACCESS  read-write
    STATUS      current
    DESCRIPTION 
        "This counter reflects the number of times a composed message is sent to a distribution list by a service provider"
    ::= { bwDXSVoiceMessagingSPEntry 25 }

  bwDXSVMRSPNumForwardSendListAttempts OBJECT-TYPE
    SYNTAX      Counter32
    MAX-ACCESS  read-write
    STATUS      current
    DESCRIPTION 
        "This counter reflects the number of times a forwarded message is sent to a distribution list by a service provider"
    ::= { bwDXSVoiceMessagingSPEntry 26 }

  bwDXSVMRSPNumSendListFailed OBJECT-TYPE
    SYNTAX      Counter32
    MAX-ACCESS  read-write
    STATUS      current
    DESCRIPTION 
        "This counter reflects the number of times an attempt to send a message to a distribution list failed for a service provider (NOT incremented in case of partial failures)"
    ::= { bwDXSVoiceMessagingSPEntry 27 }

  bwDXSVPSPGreetingRecorded OBJECT-TYPE
    SYNTAX      Counter32
    MAX-ACCESS  read-write
    STATUS      current
    DESCRIPTION 
        "Number of times a user recorded a branded Voice Messaging greeting for a given service provider"
    ::= { bwDXSVoiceMessagingSPEntry 28 }

  bwDXSVMSPGreetingRecorded OBJECT-TYPE
    SYNTAX      Counter32
    MAX-ACCESS  read-write
    STATUS      current
    DESCRIPTION 
        "Number of times a user recorded a branded Voice Portal greeting for a given service provider"
    ::= { bwDXSVoiceMessagingSPEntry 29 }

  bwDXSVPCSPCall OBJECT-TYPE
    SYNTAX      Counter32
    MAX-ACCESS  read-write
    STATUS      current
    DESCRIPTION 
        "Number of times a user from a specific service provider initiated a call with Voice Portal Calling"
    ::= { bwDXSVoiceMessagingSPEntry 30 }

  bwDXSSPMultiMediaMsgDeposit OBJECT-TYPE
    SYNTAX      Counter32
    MAX-ACCESS  read-write
    STATUS      current
    DESCRIPTION 
        "Number of times a user has received a multimedia message for a given service provider"
    ::= { bwDXSVoiceMessagingSPEntry 31 }

  bwDXSVMSPMultiMediaGreetingRecorded OBJECT-TYPE
    SYNTAX      Counter32
    MAX-ACCESS  read-write
    STATUS      current
    DESCRIPTION 
        "Number of time a user has recorded a multimedia message via the Voice Portal for a given service provider"
    ::= { bwDXSVoiceMessagingSPEntry 32 }

  bwDXSAutoAttendantSPMultiMediaPromptRecorded OBJECT-TYPE
    SYNTAX      Counter32
    MAX-ACCESS  read-write
    STATUS      current
    DESCRIPTION 
        "Number of times an administrator has recorded an AA prompt via the Voice Portal for a given service provider"
    ::= { bwDXSVoiceMessagingSPEntry 33 }

  bwDXSMessagingSPQuery OBJECT-TYPE
    SYNTAX      Counter32
    MAX-ACCESS  read-write
    STATUS      current
    DESCRIPTION 
        "This counter is incremented whenever a request for remote user mailbox information is sent out for a given service provider."
    ::= { bwDXSVoiceMessagingSPEntry 34 }

  bwDXSMessagingSPQueryNoUser OBJECT-TYPE
    SYNTAX      Counter32
    MAX-ACCESS  read-write
    STATUS      current
    DESCRIPTION 
        "This counter is incremented whenever a request for remote user mailbox information results in a user not found error for a given service provider."
    ::= { bwDXSVoiceMessagingSPEntry 35 }

  bwDXSMessagingSPQueryNoMailbox OBJECT-TYPE
    SYNTAX      Counter32
    MAX-ACCESS  read-write
    STATUS      current
    DESCRIPTION 
        "This counter is incremented whenever a request for remote user mailbox information results in an error because the remote mailbox is disabled, full, or not configured for a given service provider."
    ::= { bwDXSVoiceMessagingSPEntry 36 }

  bwDXSVMRNumComposeSendListAttempts OBJECT-TYPE
    SYNTAX      Counter32
    MAX-ACCESS  read-write
    STATUS      current
    DESCRIPTION 
        "This counter reflects the number of times a composed message is sent to a distribution list"
    ::= { voiceMessaging 24 }

  bwDXSVMRNumForwardSendListAttempts OBJECT-TYPE
    SYNTAX      Counter32
    MAX-ACCESS  read-write
    STATUS      current
    DESCRIPTION 
        "This counter reflects the number of times a forwarded message is sent to a distribution list"
    ::= { voiceMessaging 25 }

  bwDXSVMRNumSendListFailed OBJECT-TYPE
    SYNTAX      Counter32
    MAX-ACCESS  read-write
    STATUS      current
    DESCRIPTION 
        "This counter reflects the number of times an attempt to send a message to a distribution list has failed (NOT incremented in case of partial failures)"
    ::= { voiceMessaging 26 }

  bwDXSVPGreetingRecorded OBJECT-TYPE
    SYNTAX      Counter32
    MAX-ACCESS  read-write
    STATUS      current
    DESCRIPTION 
        "Number of times a user recorded a branded Voice Portal greeting"
    ::= { voiceMessaging 27 }

  bwDXSVMGreetingRecorded OBJECT-TYPE
    SYNTAX      Counter32
    MAX-ACCESS  read-write
    STATUS      current
    DESCRIPTION 
        "Number of times a user recorded a branded Voice Messaging greeting"
    ::= { voiceMessaging 28 }

  bwDXSVoiceMessagingGroupTable OBJECT-TYPE
    SYNTAX      SEQUENCE OF BwVoiceMessagingGroupEntry
    MAX-ACCESS  not-accessible
    STATUS      current
    DESCRIPTION 
        "This table contains the counters for Voice Messaging service measurements for groups"
    ::= { voiceMessaging 29 }

  bwDXSVoiceMessagingGroupEntry OBJECT-TYPE
    SYNTAX      BwVoiceMessagingGroupEntry
    MAX-ACCESS  not-accessible
    STATUS      current
    DESCRIPTION 
        "This row contains the counters for Voice Messaging service measurements for a group"
    INDEX       { bwDXSVoiceMessagingGroupIndex }
    ::= { bwDXSVoiceMessagingGroupTable 1 }

  BwVoiceMessagingGroupEntry ::= SEQUENCE {
    bwDXSVoiceMessagingGroupIndex                      Unsigned32,
    bwDXSVoiceMessagingGroupID                         DisplayString,
    bwDXSVMGroupNumBusyGreetingsPlayed                 Counter32,
    bwDXSVMGroupNumNoAnswerGreetingsPlayed             Counter32,
    bwDXSVMGroupNumMessagesLeft                        Counter32,
    bwDXSVMRGroupNumBusyGreetingsRecorded              Counter32,
    bwDXSVMRGroupNumNoAnswerGreetingsRecorded          Counter32,
    bwDXSVMRGroupNumPersonalizedNamesRecorded          Counter32,
    bwDXSVMRGroupNumLoginAttempts                      Counter32,
    bwDXSVMRGroupNumLoginFailures                      Counter32,
    bwDXSVMRGroupNumComposeSendAttempts                Counter32,
    bwDXSVMRGroupNumComposeSendGroupAttempts           Counter32,
    bwDXSVMRGroupNumForwardSendAttempts                Counter32,
    bwDXSVMRGroupNumForwardSendGroupAttempts           Counter32,
    bwDXSVMRGroupNumReplySendAttempts                  Counter32,
    bwDXSVMRGroupNumSendFailed                         Counter32,
    bwDXSVMRGroupNumSendGroupFailed                    Counter32,
    bwDXSVMRGroupDeleteAllMsgsAttempts                 Counter32,
    bwDXSVMRGroupCallBackAttempts                      Counter32,
    bwDXSVPGroupNumAABusHoursGreetingRecorded          Counter32,
    bwDXSVPGroupNumAAAfterHoursGreetingRecorded        Counter32,
    bwDXSVPGroupNumCFADestinationChanged               Counter32,
    bwDXSVPGroupNumPasscodeChanged                     Counter32,
    bwDXSVMRGroupNumComposeSendListAttempts            Counter32,
    bwDXSVMRGroupNumForwardSendListAttempts            Counter32,
    bwDXSVMRGroupNumSendListFailed                     Counter32,
    bwDXSVPGroupGreetingRecorded                       Counter32,
    bwDXSVMGroupGreetingRecorded                       Counter32,
    bwDXSVPCGroupCall                                  Counter32,
    bwDXSGroupMultiMediaMsgDeposit                     Counter32,
    bwDXSVMGroupMultiMediaGreetingRecorded             Counter32,
    bwDXSAutoAttendantGroupMultiMediaPromptRecorded    Counter32,
    bwDXSMessagingGroupQuery                           Counter32,
    bwDXSMessagingGroupQueryNoUser                     Counter32,
    bwDXSMessagingGroupQueryNoMailbox                  Counter32
  }

  bwDXSVoiceMessagingGroupIndex OBJECT-TYPE
    SYNTAX      Unsigned32
    MAX-ACCESS  read-only
    STATUS      current
    DESCRIPTION 
        "This integer represents the a group index in the system"
    ::= { bwDXSVoiceMessagingGroupEntry 1 }

  bwDXSVoiceMessagingGroupID OBJECT-TYPE
    SYNTAX      DisplayString
    MAX-ACCESS  read-only
    STATUS      current
    DESCRIPTION 
        "This string represents a group ID"
    ::= { bwDXSVoiceMessagingGroupEntry 2 }

  bwDXSVMGroupNumBusyGreetingsPlayed OBJECT-TYPE
    SYNTAX      Counter32
    MAX-ACCESS  read-write
    STATUS      current
    DESCRIPTION 
        "This counter reflects the number of times a busy greeting is played to a caller by a group"
    ::= { bwDXSVoiceMessagingGroupEntry 3 }

  bwDXSVMGroupNumNoAnswerGreetingsPlayed OBJECT-TYPE
    SYNTAX      Counter32
    MAX-ACCESS  read-write
    STATUS      current
    DESCRIPTION 
        "This counter reflects the number of times a no answer greeting is played by a group"
    ::= { bwDXSVoiceMessagingGroupEntry 4 }

  bwDXSVMGroupNumMessagesLeft OBJECT-TYPE
    SYNTAX      Counter32
    MAX-ACCESS  read-write
    STATUS      current
    DESCRIPTION 
        "This counter reflects the number of times a voice message is recorded by a group"
    ::= { bwDXSVoiceMessagingGroupEntry 5 }

  bwDXSVMRGroupNumBusyGreetingsRecorded OBJECT-TYPE
    SYNTAX      Counter32
    MAX-ACCESS  read-write
    STATUS      current
    DESCRIPTION 
        "This counter reflects the number of times a busy greeting is recorded over the phone by a group"
    ::= { bwDXSVoiceMessagingGroupEntry 6 }

  bwDXSVMRGroupNumNoAnswerGreetingsRecorded OBJECT-TYPE
    SYNTAX      Counter32
    MAX-ACCESS  read-write
    STATUS      current
    DESCRIPTION 
        "This counter reflects the number of times a no answer greeting is recorded over the phone by a group"
    ::= { bwDXSVoiceMessagingGroupEntry 7 }

  bwDXSVMRGroupNumPersonalizedNamesRecorded OBJECT-TYPE
    SYNTAX      Counter32
    MAX-ACCESS  read-write
    STATUS      current
    DESCRIPTION 
        "This counter reflects the number of times a personalized name greeting is recorded over the phone by a group"
    ::= { bwDXSVoiceMessagingGroupEntry 8 }

  bwDXSVMRGroupNumLoginAttempts OBJECT-TYPE
    SYNTAX      Counter32
    MAX-ACCESS  read-write
    STATUS      current
    DESCRIPTION 
        "This counter reflects the number of times a user attempts a login over the phone by a group"
    ::= { bwDXSVoiceMessagingGroupEntry 9 }

  bwDXSVMRGroupNumLoginFailures OBJECT-TYPE
    SYNTAX      Counter32
    MAX-ACCESS  read-write
    STATUS      current
    DESCRIPTION 
        "This counter reflects the number of times a user login attempt fails by a group"
    ::= { bwDXSVoiceMessagingGroupEntry 10 }

  bwDXSVMRGroupNumComposeSendAttempts OBJECT-TYPE
    SYNTAX      Counter32
    MAX-ACCESS  read-write
    STATUS      current
    DESCRIPTION 
        "This counter reflects the number of times a composed message is sent to a user by a group"
    ::= { bwDXSVoiceMessagingGroupEntry 11 }

  bwDXSVMRGroupNumComposeSendGroupAttempts OBJECT-TYPE
    SYNTAX      Counter32
    MAX-ACCESS  read-write
    STATUS      current
    DESCRIPTION 
        "This counter reflects the number of times a composed message is sent to a group by a group"
    ::= { bwDXSVoiceMessagingGroupEntry 12 }

  bwDXSVMRGroupNumForwardSendAttempts OBJECT-TYPE
    SYNTAX      Counter32
    MAX-ACCESS  read-write
    STATUS      current
    DESCRIPTION 
        "This counter reflects the number of times a forwarded message is sent to a user by a group"
    ::= { bwDXSVoiceMessagingGroupEntry 13 }

  bwDXSVMRGroupNumForwardSendGroupAttempts OBJECT-TYPE
    SYNTAX      Counter32
    MAX-ACCESS  read-write
    STATUS      current
    DESCRIPTION 
        "This counter reflects the number of times a forwarded message is sent to a group by a group"
    ::= { bwDXSVoiceMessagingGroupEntry 14 }

  bwDXSVMRGroupNumReplySendAttempts OBJECT-TYPE
    SYNTAX      Counter32
    MAX-ACCESS  read-write
    STATUS      current
    DESCRIPTION 
        "This counter reflects the number of times a message reply is sent by a group"
    ::= { bwDXSVoiceMessagingGroupEntry 15 }

  bwDXSVMRGroupNumSendFailed OBJECT-TYPE
    SYNTAX      Counter32
    MAX-ACCESS  read-write
    STATUS      current
    DESCRIPTION 
        "This counter reflects the number of times an attempt to send a message to a user failed by a group"
    ::= { bwDXSVoiceMessagingGroupEntry 16 }

  bwDXSVMRGroupNumSendGroupFailed OBJECT-TYPE
    SYNTAX      Counter32
    MAX-ACCESS  read-write
    STATUS      current
    DESCRIPTION 
        "This counter reflects the number of times an attempt to send a message to a group failed by a group"
    ::= { bwDXSVoiceMessagingGroupEntry 17 }

  bwDXSVMRGroupDeleteAllMsgsAttempts OBJECT-TYPE
    SYNTAX      Counter32
    MAX-ACCESS  read-write
    STATUS      current
    DESCRIPTION 
        "This counter reflects the number of times a user attempts to delete all messages by a group"
    ::= { bwDXSVoiceMessagingGroupEntry 18 }

  bwDXSVMRGroupCallBackAttempts OBJECT-TYPE
    SYNTAX      Counter32
    MAX-ACCESS  read-write
    STATUS      current
    DESCRIPTION 
        "This counter reflects the number of times a user attempts to callback the caller by a group"
    ::= { bwDXSVoiceMessagingGroupEntry 19 }

  bwDXSVPGroupNumAABusHoursGreetingRecorded OBJECT-TYPE
    SYNTAX      Counter32
    MAX-ACCESS  read-write
    STATUS      current
    DESCRIPTION 
        "This counter reflects the number of times an AA business hours greeting is recorded over the phone by a group"
    ::= { bwDXSVoiceMessagingGroupEntry 21 }

  bwDXSVPGroupNumAAAfterHoursGreetingRecorded OBJECT-TYPE
    SYNTAX      Counter32
    MAX-ACCESS  read-write
    STATUS      current
    DESCRIPTION 
        "This counter reflects the number of times an AA after hours greeting is recorded over the phone by a group"
    ::= { bwDXSVoiceMessagingGroupEntry 22 }

  bwDXSVPGroupNumCFADestinationChanged OBJECT-TYPE
    SYNTAX      Counter32
    MAX-ACCESS  read-write
    STATUS      current
    DESCRIPTION 
        "This counter reflects the number of times a CFA destination is changed over the phone by a group"
    ::= { bwDXSVoiceMessagingGroupEntry 23 }

  bwDXSVPGroupNumPasscodeChanged OBJECT-TYPE
    SYNTAX      Counter32
    MAX-ACCESS  read-write
    STATUS      current
    DESCRIPTION 
        "This counter reflects the number of times a Voice Portal is changed over the phone by a group"
    ::= { bwDXSVoiceMessagingGroupEntry 24 }

  bwDXSVMRGroupNumComposeSendListAttempts OBJECT-TYPE
    SYNTAX      Counter32
    MAX-ACCESS  read-write
    STATUS      current
    DESCRIPTION 
        "This counter reflects the number of times a composed message is sent to a distribution list by a group"
    ::= { bwDXSVoiceMessagingGroupEntry 25 }

  bwDXSVMRGroupNumForwardSendListAttempts OBJECT-TYPE
    SYNTAX      Counter32
    MAX-ACCESS  read-write
    STATUS      current
    DESCRIPTION 
        "This counter reflects the number of times a forwarded message is sent to a distribution list by a group"
    ::= { bwDXSVoiceMessagingGroupEntry 26 }

  bwDXSVMRGroupNumSendListFailed OBJECT-TYPE
    SYNTAX      Counter32
    MAX-ACCESS  read-write
    STATUS      current
    DESCRIPTION 
        "This counter reflects the number of times an attempt to send a message to a distribution list failed for a group (NOT incremented in case of partial failures)"
    ::= { bwDXSVoiceMessagingGroupEntry 27 }

  bwDXSVPGroupGreetingRecorded OBJECT-TYPE
    SYNTAX      Counter32
    MAX-ACCESS  read-write
    STATUS      current
    DESCRIPTION 
        "Number of times a user recorded a branded Voice Messaging greeting for a given group"
    ::= { bwDXSVoiceMessagingGroupEntry 28 }

  bwDXSVMGroupGreetingRecorded OBJECT-TYPE
    SYNTAX      Counter32
    MAX-ACCESS  read-write
    STATUS      current
    DESCRIPTION 
        "Number of times a user recorded a branded Voice Portal greeting for a given group"
    ::= { bwDXSVoiceMessagingGroupEntry 29 }

  bwDXSVPCGroupCall OBJECT-TYPE
    SYNTAX      Counter32
    MAX-ACCESS  read-write
    STATUS      current
    DESCRIPTION 
        "Number of times a user from a specific group initiated a call with Voice Portal Calling"
    ::= { bwDXSVoiceMessagingGroupEntry 30 }

  bwDXSGroupMultiMediaMsgDeposit OBJECT-TYPE
    SYNTAX      Counter32
    MAX-ACCESS  read-write
    STATUS      current
    DESCRIPTION 
        "Number of times a user has received a multimedia message for a given group"
    ::= { bwDXSVoiceMessagingGroupEntry 31 }

  bwDXSVMGroupMultiMediaGreetingRecorded OBJECT-TYPE
    SYNTAX      Counter32
    MAX-ACCESS  read-write
    STATUS      current
    DESCRIPTION 
        "Number of time a user has recorded a multimedia message via the Voice Portal for a given group"
    ::= { bwDXSVoiceMessagingGroupEntry 32 }

  bwDXSAutoAttendantGroupMultiMediaPromptRecorded OBJECT-TYPE
    SYNTAX      Counter32
    MAX-ACCESS  read-write
    STATUS      current
    DESCRIPTION 
        "Number of times an administrator has recorded an AA prompt via the Voice Portal for a given group"
    ::= { bwDXSVoiceMessagingGroupEntry 33 }

  bwDXSMessagingGroupQuery OBJECT-TYPE
    SYNTAX      Counter32
    MAX-ACCESS  read-write
    STATUS      current
    DESCRIPTION 
        "This counter is incremented whenever a request for remote user mailbox information is sent out for a given service provider."
    ::= { bwDXSVoiceMessagingGroupEntry 34 }

  bwDXSMessagingGroupQueryNoUser OBJECT-TYPE
    SYNTAX      Counter32
    MAX-ACCESS  read-write
    STATUS      current
    DESCRIPTION 
        "This counter is incremented whenever a request for remote user mailbox information results in a user not found error for a given service provider."
    ::= { bwDXSVoiceMessagingGroupEntry 35 }

  bwDXSMessagingGroupQueryNoMailbox OBJECT-TYPE
    SYNTAX      Counter32
    MAX-ACCESS  read-write
    STATUS      current
    DESCRIPTION 
        "This counter is incremented whenever a request for remote user mailbox information results in an error because the remote mailbox is disabled, full, or not configured for a given service provider."
    ::= { bwDXSVoiceMessagingGroupEntry 36 }

  bwDXSVPCCall OBJECT-TYPE
    SYNTAX      Counter32
    MAX-ACCESS  read-write
    STATUS      current
    DESCRIPTION 
        "Number of times a user initiated a call with Voice Portal Calling"
    ::= { voiceMessaging 30 }

  bwDXSMultiMediaMsgDeposit OBJECT-TYPE
    SYNTAX      Counter32
    MAX-ACCESS  read-write
    STATUS      current
    DESCRIPTION 
        "Number of times a user has received a multimedia message"
    ::= { voiceMessaging 31 }

  bwDXSVMMultiMediaGreetingRecorded OBJECT-TYPE
    SYNTAX      Counter32
    MAX-ACCESS  read-write
    STATUS      current
    DESCRIPTION 
        "Number of time a user has recorded a multimedia message via the Voice Portal"
    ::= { voiceMessaging 32 }

  bwDXSAutoAttendantMultiMediaPromptRecorded OBJECT-TYPE
    SYNTAX      Counter32
    MAX-ACCESS  read-write
    STATUS      current
    DESCRIPTION 
        "Number of times an administrator has recorded an AA prompt via the Voice Portal"
    ::= { voiceMessaging 33 }

  bwDXSMessagingQuery OBJECT-TYPE
    SYNTAX      Counter32
    MAX-ACCESS  read-write
    STATUS      current
    DESCRIPTION 
        "This counter is incremented whenever a request for remote user mailbox information is sent out."
    ::= { voiceMessaging 34 }

  bwDXSMessagingQueryNoUser OBJECT-TYPE
    SYNTAX      Counter32
    MAX-ACCESS  read-write
    STATUS      current
    DESCRIPTION 
        "This counter is incremented whenever a request for remote user mailbox information results in a user not found error."
    ::= { voiceMessaging 35 }

  bwDXSMessagingQueryNoMailbox OBJECT-TYPE
    SYNTAX      Counter32
    MAX-ACCESS  read-write
    STATUS      current
    DESCRIPTION 
        "This counter is incremented whenever a request for remote user mailbox information results in an error because the remote mailbox is disabled, full, or not configured."
    ::= { voiceMessaging 36 }

  bwDXSInterceptUserOriginationInvocations OBJECT-TYPE
    SYNTAX      Counter32
    MAX-ACCESS  read-write
    STATUS      current
    DESCRIPTION 
        "incremented whenever the intercept user service blocks an originating call"
    ::= { intercept 1 }

  bwDXSInterceptGroupOriginationInvocations OBJECT-TYPE
    SYNTAX      Counter32
    MAX-ACCESS  read-write
    STATUS      current
    DESCRIPTION 
        "incremented whenever the intercept group service blocks an originating call"
    ::= { intercept 2 }

  bwDXSInterceptUserTerminationInvocations OBJECT-TYPE
    SYNTAX      Counter32
    MAX-ACCESS  read-write
    STATUS      current
    DESCRIPTION 
        "incremented whenever the intercept user service blocks a terminating call"
    ::= { intercept 3 }

  bwDXSInterceptGroupTerminationInvocations OBJECT-TYPE
    SYNTAX      Counter32
    MAX-ACCESS  read-write
    STATUS      current
    DESCRIPTION 
        "incremented whenever the intercept group service blocks a terminating call"
    ::= { intercept 4 }

  bwDXSInterceptTransfers OBJECT-TYPE
    SYNTAX      Counter32
    MAX-ACCESS  read-write
    STATUS      current
    DESCRIPTION 
        "incremented whenever the intercept service transfers a call"
    ::= { intercept 5 }

  bwDXSInterceptSPTable OBJECT-TYPE
    SYNTAX      SEQUENCE OF BwInterceptSPEntry
    MAX-ACCESS  not-accessible
    STATUS      current
    DESCRIPTION 
        "This table contains the counters for Intercept service measurements for service providers"
    ::= { intercept 6 }

  bwDXSInterceptSPEntry OBJECT-TYPE
    SYNTAX      BwInterceptSPEntry
    MAX-ACCESS  not-accessible
    STATUS      current
    DESCRIPTION 
        "This row contains the counters for Intercept service measurements for a service provider"
    INDEX       { bwDXSInterceptSPIndex }
    ::= { bwDXSInterceptSPTable 1 }

  BwInterceptSPEntry ::= SEQUENCE {
    bwDXSInterceptSPIndex                          Unsigned32,
    bwDXSInterceptSPID                             DisplayString,
    bwDXSInterceptSPUserOriginationInvocations     Counter32,
    bwDXSInterceptSPGroupOriginationInvocations    Counter32,
    bwDXSInterceptSPUserTerminationInvocations     Counter32,
    bwDXSInterceptSPGroupTerminationInvocations    Counter32,
    bwDXSInterceptSPTransfers                      Counter32
  }

  bwDXSInterceptSPIndex OBJECT-TYPE
    SYNTAX      Unsigned32
    MAX-ACCESS  read-only
    STATUS      current
    DESCRIPTION 
        "This integer represents the a service provider index in the system"
    ::= { bwDXSInterceptSPEntry 1 }

  bwDXSInterceptSPID OBJECT-TYPE
    SYNTAX      DisplayString
    MAX-ACCESS  read-only
    STATUS      current
    DESCRIPTION 
        "This string represents a service provider ID"
    ::= { bwDXSInterceptSPEntry 2 }

  bwDXSInterceptSPUserOriginationInvocations OBJECT-TYPE
    SYNTAX      Counter32
    MAX-ACCESS  read-write
    STATUS      current
    DESCRIPTION 
        "This counter reflects the number of times the intercept user service blocks an originating call by a service provider"
    ::= { bwDXSInterceptSPEntry 3 }

  bwDXSInterceptSPGroupOriginationInvocations OBJECT-TYPE
    SYNTAX      Counter32
    MAX-ACCESS  read-write
    STATUS      current
    DESCRIPTION 
        "This counter reflects the number of times the intercept group service blocks an originating call by a service provider"
    ::= { bwDXSInterceptSPEntry 4 }

  bwDXSInterceptSPUserTerminationInvocations OBJECT-TYPE
    SYNTAX      Counter32
    MAX-ACCESS  read-write
    STATUS      current
    DESCRIPTION 
        "This counter reflects the number of times the intercept user service blocks a terminating call by a service provider"
    ::= { bwDXSInterceptSPEntry 5 }

  bwDXSInterceptSPGroupTerminationInvocations OBJECT-TYPE
    SYNTAX      Counter32
    MAX-ACCESS  read-write
    STATUS      current
    DESCRIPTION 
        "This counter reflects the number of times the intercept group service blocks a terminating call by a service provider"
    ::= { bwDXSInterceptSPEntry 6 }

  bwDXSInterceptSPTransfers OBJECT-TYPE
    SYNTAX      Counter32
    MAX-ACCESS  read-write
    STATUS      current
    DESCRIPTION 
        "This counter reflects the number of times the intercept service transfers a call by a service provider"
    ::= { bwDXSInterceptSPEntry 7 }

  bwDXSInterceptGroupTable OBJECT-TYPE
    SYNTAX      SEQUENCE OF BwInterceptGroupEntry
    MAX-ACCESS  not-accessible
    STATUS      current
    DESCRIPTION 
        "This table contains the counters for Intercept service measurements for groups"
    ::= { intercept 7 }

  bwDXSInterceptGroupEntry OBJECT-TYPE
    SYNTAX      BwInterceptGroupEntry
    MAX-ACCESS  not-accessible
    STATUS      current
    DESCRIPTION 
        "This row contains the counters for Intercept service measurements for a service provider"
    INDEX       { bwDXSInterceptGroupIndex }
    ::= { bwDXSInterceptGroupTable 1 }

  BwInterceptGroupEntry ::= SEQUENCE {
    bwDXSInterceptGroupIndex                           Unsigned32,
    bwDXSInterceptGroupID                              DisplayString,
    bwDXSInterceptGroupUserOriginationInvocations      Counter32,
    bwDXSInterceptGroupGroupOriginationInvocations     Counter32,
    bwDXSInterceptGroupUserTerminationInvocations      Counter32,
    bwDXSInterceptGroupGroupTerminationInvocations     Counter32,
    bwDXSInterceptGroupTransfers                       Counter32
  }

  bwDXSInterceptGroupIndex OBJECT-TYPE
    SYNTAX      Unsigned32
    MAX-ACCESS  read-only
    STATUS      current
    DESCRIPTION 
        "This integer represents the a service provider index in the system"
    ::= { bwDXSInterceptGroupEntry 1 }

  bwDXSInterceptGroupID OBJECT-TYPE
    SYNTAX      DisplayString
    MAX-ACCESS  read-only
    STATUS      current
    DESCRIPTION 
        "This string represents a service provider ID"
    ::= { bwDXSInterceptGroupEntry 2 }

  bwDXSInterceptGroupUserOriginationInvocations OBJECT-TYPE
    SYNTAX      Counter32
    MAX-ACCESS  read-write
    STATUS      current
    DESCRIPTION 
        "This counter reflects the number of times the intercept user service blocks an originating call by a service provider"
    ::= { bwDXSInterceptGroupEntry 3 }

  bwDXSInterceptGroupGroupOriginationInvocations OBJECT-TYPE
    SYNTAX      Counter32
    MAX-ACCESS  read-write
    STATUS      current
    DESCRIPTION 
        "This counter reflects the number of times the intercept group service blocks an originating call by a service provider"
    ::= { bwDXSInterceptGroupEntry 4 }

  bwDXSInterceptGroupUserTerminationInvocations OBJECT-TYPE
    SYNTAX      Counter32
    MAX-ACCESS  read-write
    STATUS      current
    DESCRIPTION 
        "This counter reflects the number of times the intercept user service blocks a terminating call by a service provider"
    ::= { bwDXSInterceptGroupEntry 5 }

  bwDXSInterceptGroupGroupTerminationInvocations OBJECT-TYPE
    SYNTAX      Counter32
    MAX-ACCESS  read-write
    STATUS      current
    DESCRIPTION 
        "This counter reflects the number of times the intercept group service blocks a terminating call by a service provider"
    ::= { bwDXSInterceptGroupEntry 6 }

  bwDXSInterceptGroupTransfers OBJECT-TYPE
    SYNTAX      Counter32
    MAX-ACCESS  read-write
    STATUS      current
    DESCRIPTION 
        "This counter reflects the number of times the intercept service transfers a call by a service provider"
    ::= { bwDXSInterceptGroupEntry 7 }

  bwDXSCallingLineIDDeliveryBlockPerCallBlocks OBJECT-TYPE
    SYNTAX      Counter32
    MAX-ACCESS  read-write
    STATUS      current
    DESCRIPTION 
        "This counter reflects the number of times the per call calling line ID delivery block service is invoked."
    ::= { callingLineIDDeliveryBlock 1 }

  bwDXSCallingLineIDDeliveryBlockSPTable OBJECT-TYPE
    SYNTAX      SEQUENCE OF BwCallingLineIDDeliveryBlockSPEntry
    MAX-ACCESS  not-accessible
    STATUS      current
    DESCRIPTION 
        "Table used to report the calling line id blocking statistics per service providers"
    ::= { callingLineIDDeliveryBlock 2 }

  bwDXSCallingLineIDDeliveryBlockSPEntry OBJECT-TYPE
    SYNTAX      BwCallingLineIDDeliveryBlockSPEntry
    MAX-ACCESS  not-accessible
    STATUS      current
    DESCRIPTION 
        "This row contains the counters for the per call calling line ID delivery block service measurements for a service provider."
    INDEX       { bwDXSCallingLineIDDeliveryBlockSPIndex }
    ::= { bwDXSCallingLineIDDeliveryBlockSPTable 1 }

  BwCallingLineIDDeliveryBlockSPEntry ::= SEQUENCE {
    bwDXSCallingLineIDDeliveryBlockSPIndex             Unsigned32,
    bwDXSCallingLineIDDeliveryBlockSPID                DisplayString,
    bwDXSCallingLineIDDeliveryBlockSPPerCallBlocks     Counter32,
    bwDXSCallingLineIDDeliveryPerCallSP                Counter32
  }

  bwDXSCallingLineIDDeliveryBlockSPIndex OBJECT-TYPE
    SYNTAX      Unsigned32
    MAX-ACCESS  read-only
    STATUS      current
    DESCRIPTION 
        "This integer represents the service provider index in the system."
    ::= { bwDXSCallingLineIDDeliveryBlockSPEntry 1 }

  bwDXSCallingLineIDDeliveryBlockSPID OBJECT-TYPE
    SYNTAX      DisplayString
    MAX-ACCESS  read-only
    STATUS      current
    DESCRIPTION 
        "This string represents a service provider ID"
    ::= { bwDXSCallingLineIDDeliveryBlockSPEntry 2 }

  bwDXSCallingLineIDDeliveryBlockSPPerCallBlocks OBJECT-TYPE
    SYNTAX      Counter32
    MAX-ACCESS  read-write
    STATUS      current
    DESCRIPTION 
        "This counter reflects the number of times the per call calling line ID delivery block service is invoked for this service provider."
    ::= { bwDXSCallingLineIDDeliveryBlockSPEntry 3 }

  bwDXSCallingLineIDDeliveryPerCallSP OBJECT-TYPE
    SYNTAX      Counter32
    MAX-ACCESS  read-write
    STATUS      current
    DESCRIPTION 
        "This counter reflects the number of times the calling line ID delivery per call service is invoked for this service provider."
    ::= { bwDXSCallingLineIDDeliveryBlockSPEntry 4 }

  bwDXSCallingLineIDDeliveryBlockGroupTable OBJECT-TYPE
    SYNTAX      SEQUENCE OF BwCallingLineIDDeliveryBlockGroupEntry
    MAX-ACCESS  not-accessible
    STATUS      current
    DESCRIPTION 
        "Table used to report the calling line id blocking statistics per groups"
    ::= { callingLineIDDeliveryBlock 3 }

  bwDXSCallingLineIDDeliveryBlockGroupEntry OBJECT-TYPE
    SYNTAX      BwCallingLineIDDeliveryBlockGroupEntry
    MAX-ACCESS  not-accessible
    STATUS      current
    DESCRIPTION 
        "This row contains the counters for the per call calling line ID delivery block service measurements for a group."
    INDEX       { bwDXSCallingLineIDDeliveryBlockGroupIndex }
    ::= { bwDXSCallingLineIDDeliveryBlockGroupTable 1 }

  BwCallingLineIDDeliveryBlockGroupEntry ::= SEQUENCE {
    bwDXSCallingLineIDDeliveryBlockGroupIndex          Unsigned32,
    bwDXSCallingLineIDDeliveryBlockGroupID             DisplayString,
    bwDXSCallingLineIDDeliveryBlockGroupPerCallBlocks  Counter32,
    bwDXSCallingLineIDDeliveryPerCallGroup             Counter32
  }

  bwDXSCallingLineIDDeliveryBlockGroupIndex OBJECT-TYPE
    SYNTAX      Unsigned32
    MAX-ACCESS  read-only
    STATUS      current
    DESCRIPTION 
        "This integer represents the group index in the system."
    ::= { bwDXSCallingLineIDDeliveryBlockGroupEntry 1 }

  bwDXSCallingLineIDDeliveryBlockGroupID OBJECT-TYPE
    SYNTAX      DisplayString
    MAX-ACCESS  read-only
    STATUS      current
    DESCRIPTION 
        "This string represents a group ID"
    ::= { bwDXSCallingLineIDDeliveryBlockGroupEntry 2 }

  bwDXSCallingLineIDDeliveryBlockGroupPerCallBlocks OBJECT-TYPE
    SYNTAX      Counter32
    MAX-ACCESS  read-write
    STATUS      current
    DESCRIPTION 
        "This counter reflects the number of times the per call calling line ID delivery block service is invoked for this group."
    ::= { bwDXSCallingLineIDDeliveryBlockGroupEntry 3 }

  bwDXSCallingLineIDDeliveryPerCallGroup OBJECT-TYPE
    SYNTAX      Counter32
    MAX-ACCESS  read-write
    STATUS      current
    DESCRIPTION 
        "This counter reflects the number of times the calling line ID delivery per call service is invoked for this group."
    ::= { bwDXSCallingLineIDDeliveryBlockGroupEntry 4 }

  bwDXSCallingLineIDDeliveryPerCall OBJECT-TYPE
    SYNTAX      Counter32
    MAX-ACCESS  read-write
    STATUS      current
    DESCRIPTION 
        "This counter reflects the number of times the per call calling line ID delivery service is invoked."
    ::= { callingLineIDDeliveryBlock 4 }

  bwDXSSessionAuditNumCallsAudited OBJECT-TYPE
    SYNTAX      Counter32
    MAX-ACCESS  read-write
    STATUS      current
    DESCRIPTION 
        "Number of calls that are audited when a Session Audit is invoked."
    ::= { sessionAudit 1 }

  bwDXSSessionAuditNumEndpointsAudited OBJECT-TYPE
    SYNTAX      Counter32
    MAX-ACCESS  read-write
    STATUS      current
    DESCRIPTION 
        "Number of endpoints that are audited when a Session Audit is invoked."
    ::= { sessionAudit 2 }

  bwDXSSessionAuditNumCallsFailedAudit OBJECT-TYPE
    SYNTAX      Counter32
    MAX-ACCESS  read-write
    STATUS      current
    DESCRIPTION 
        "Number of times the SessionAudit service received a failure on a call being audited."
    ::= { sessionAudit 3 }

  bwDXSSessionAuditNumEndpointsFailedAudit OBJECT-TYPE
    SYNTAX      Counter32
    MAX-ACCESS  read-write
    STATUS      current
    DESCRIPTION 
        "Number of times the SessionAudit service received a failure on an endpoint being audited."
    ::= { sessionAudit 4 }

  bwDXSSessionAuditSPTable OBJECT-TYPE
    SYNTAX      SEQUENCE OF BwSessionAuditSPEntry
    MAX-ACCESS  not-accessible
    STATUS      current
    DESCRIPTION 
        "This table contains Session Audit service measurements at a service provider level."
    ::= { sessionAudit 5 }

  bwDXSSessionAuditSPEntry OBJECT-TYPE
    SYNTAX      BwSessionAuditSPEntry
    MAX-ACCESS  not-accessible
    STATUS      current
    DESCRIPTION 
        "Each row contains the service counters for the SessionAudit service for each service provider in the system."
    INDEX       { bwDXSSessionAuditSPIndex }
    ::= { bwDXSSessionAuditSPTable 1 }

  BwSessionAuditSPEntry ::= SEQUENCE {
    bwDXSSessionAuditSPIndex                       Unsigned32,
    bwDXSSessionAuditSPID                          DisplayString,
    bwDXSSessionAuditSPNumCallsAudited             Counter32,
    bwDXSSessionAuditSPNumEndpointsAudited         Counter32,
    bwDXSSessionAuditSPNumCallsFailedAudit         Counter32,
    bwDXSSessionAuditSPNumEndpointsFailedAudit     Counter32
  }

  bwDXSSessionAuditSPIndex OBJECT-TYPE
    SYNTAX      Unsigned32
    MAX-ACCESS  read-only
    STATUS      current
    DESCRIPTION 
        "This column represents the index of the service provider in the system."
    ::= { bwDXSSessionAuditSPEntry 1 }

  bwDXSSessionAuditSPID OBJECT-TYPE
    SYNTAX      DisplayString
    MAX-ACCESS  read-only
    STATUS      current
    DESCRIPTION 
        "This column represents a service provider ID."
    ::= { bwDXSSessionAuditSPEntry 2 }

  bwDXSSessionAuditSPNumCallsAudited OBJECT-TYPE
    SYNTAX      Counter32
    MAX-ACCESS  read-write
    STATUS      current
    DESCRIPTION 
        "Number of calls that are audited when a Session Audit is invoked, per service provider."
    ::= { bwDXSSessionAuditSPEntry 3 }

  bwDXSSessionAuditSPNumEndpointsAudited OBJECT-TYPE
    SYNTAX      Counter32
    MAX-ACCESS  read-write
    STATUS      current
    DESCRIPTION 
        "Number of endpoints that are audited when a Session Audit is invoked, per service provider."
    ::= { bwDXSSessionAuditSPEntry 4 }

  bwDXSSessionAuditSPNumCallsFailedAudit OBJECT-TYPE
    SYNTAX      Counter32
    MAX-ACCESS  read-write
    STATUS      current
    DESCRIPTION 
        "Number of times the SessionAudit service received a failure on a call being audited, per service provider."
    ::= { bwDXSSessionAuditSPEntry 5 }

  bwDXSSessionAuditSPNumEndpointsFailedAudit OBJECT-TYPE
    SYNTAX      Counter32
    MAX-ACCESS  read-write
    STATUS      current
    DESCRIPTION 
        "Number of times the SessionAudit service received a failure on an endpoint being audited, per service provider."
    ::= { bwDXSSessionAuditSPEntry 6 }

  bwDXSSessionAuditGroupTable OBJECT-TYPE
    SYNTAX      SEQUENCE OF BwSessionAuditGroupEntry
    MAX-ACCESS  not-accessible
    STATUS      current
    DESCRIPTION 
        "This table contains Session Audit service measurements at a group level."
    ::= { sessionAudit 6 }

  bwDXSSessionAuditGroupEntry OBJECT-TYPE
    SYNTAX      BwSessionAuditGroupEntry
    MAX-ACCESS  not-accessible
    STATUS      current
    DESCRIPTION 
        "Each row contains the service counters for the SessionAudit service for each group in the system."
    INDEX       { bwDXSSessionAuditGroupIndex }
    ::= { bwDXSSessionAuditGroupTable 1 }

  BwSessionAuditGroupEntry ::= SEQUENCE {
    bwDXSSessionAuditGroupIndex                    Unsigned32,
    bwDXSSessionAuditGroupID                       DisplayString,
    bwDXSSessionAuditGroupNumCallsAudited          Counter32,
    bwDXSSessionAuditGroupNumEndpointsAudited      Counter32,
    bwDXSSessionAuditGroupNumCallsFailedAudit      Counter32,
    bwDXSSessionAuditGroupNumEndpointsFailedAudit  Counter32
  }

  bwDXSSessionAuditGroupIndex OBJECT-TYPE
    SYNTAX      Unsigned32
    MAX-ACCESS  read-only
    STATUS      current
    DESCRIPTION 
        "This column represents the index of the group in the system."
    ::= { bwDXSSessionAuditGroupEntry 1 }

  bwDXSSessionAuditGroupID OBJECT-TYPE
    SYNTAX      DisplayString
    MAX-ACCESS  read-only
    STATUS      current
    DESCRIPTION 
        "This column represents a group ID."
    ::= { bwDXSSessionAuditGroupEntry 2 }

  bwDXSSessionAuditGroupNumCallsAudited OBJECT-TYPE
    SYNTAX      Counter32
    MAX-ACCESS  read-write
    STATUS      current
    DESCRIPTION 
        "Number of calls that are audited when a Session Audit is invoked, per group."
    ::= { bwDXSSessionAuditGroupEntry 3 }

  bwDXSSessionAuditGroupNumEndpointsAudited OBJECT-TYPE
    SYNTAX      Counter32
    MAX-ACCESS  read-write
    STATUS      current
    DESCRIPTION 
        "Number of endpoints that are audited when a Session Audit is invoked, per group."
    ::= { bwDXSSessionAuditGroupEntry 4 }

  bwDXSSessionAuditGroupNumCallsFailedAudit OBJECT-TYPE
    SYNTAX      Counter32
    MAX-ACCESS  read-write
    STATUS      current
    DESCRIPTION 
        "Number of times the SessionAudit service received a failure on a call being audited, per group."
    ::= { bwDXSSessionAuditGroupEntry 5 }

  bwDXSSessionAuditGroupNumEndpointsFailedAudit OBJECT-TYPE
    SYNTAX      Counter32
    MAX-ACCESS  read-write
    STATUS      current
    DESCRIPTION 
        "Number of times the SessionAudit service received a failure on an endpoint being audited, per group."
    ::= { bwDXSSessionAuditGroupEntry 6 }

  bwDXSCallWaitingSPTable OBJECT-TYPE
    SYNTAX      SEQUENCE OF BwCallWaitingSPEntry
    MAX-ACCESS  not-accessible
    STATUS      current
    DESCRIPTION 
        "This counter table will be indexed per service provider."
    ::= { callWaiting 1 }

  bwDXSCallWaitingSPEntry OBJECT-TYPE
    SYNTAX      BwCallWaitingSPEntry
    MAX-ACCESS  not-accessible
    STATUS      current
    DESCRIPTION 
        "Each row contains the service counters for the CallWaiting service for each service provider in the system."
    INDEX       { bwDXSCallWaitingSPIndex }
    ::= { bwDXSCallWaitingSPTable 1 }

  BwCallWaitingSPEntry ::= SEQUENCE {
    bwDXSCallWaitingSPIndex            Unsigned32,
    bwDXSCallWaitingSPID               DisplayString,
    bwDXSCWSPNumPhoneCancellations     Counter32
  }

  bwDXSCallWaitingSPIndex OBJECT-TYPE
    SYNTAX      Unsigned32
    MAX-ACCESS  read-only
    STATUS      current
    DESCRIPTION 
        "This column represents the index of the service provider in the system."
    ::= { bwDXSCallWaitingSPEntry 1 }

  bwDXSCallWaitingSPID OBJECT-TYPE
    SYNTAX      DisplayString
    MAX-ACCESS  read-only
    STATUS      current
    DESCRIPTION 
        "This string represents a service provider ID"
    ::= { bwDXSCallWaitingSPEntry 2 }

  bwDXSCWSPNumPhoneCancellations OBJECT-TYPE
    SYNTAX      Counter32
    MAX-ACCESS  read-write
    STATUS      current
    DESCRIPTION 
        "Number of times CW has been cancelled via FAC for users in a given service provider."
    ::= { bwDXSCallWaitingSPEntry 3 }

  bwDXSCWNumPhoneCancellations OBJECT-TYPE
    SYNTAX      Counter32
    MAX-ACCESS  read-write
    STATUS      current
    DESCRIPTION 
        "Total number of times CW has been cancelled via FAC."
    ::= { callWaiting 2 }

  bwDXSCallWaitingGroupTable OBJECT-TYPE
    SYNTAX      SEQUENCE OF BwCallWaitingGroupEntry
    MAX-ACCESS  not-accessible
    STATUS      current
    DESCRIPTION 
        "This counter table will be indexed per group."
    ::= { callWaiting 3 }

  bwDXSCallWaitingGroupEntry OBJECT-TYPE
    SYNTAX      BwCallWaitingGroupEntry
    MAX-ACCESS  not-accessible
    STATUS      current
    DESCRIPTION 
        "Each row contains the service counters for the CallWaiting service for each group in the system."
    INDEX       { bwDXSCallWaitingGroupIndex }
    ::= { bwDXSCallWaitingGroupTable 1 }

  BwCallWaitingGroupEntry ::= SEQUENCE {
    bwDXSCallWaitingGroupIndex         Unsigned32,
    bwDXSCallWaitingGroupID            DisplayString,
    bwDXSCWGroupNumPhoneCancellations  Counter32
  }

  bwDXSCallWaitingGroupIndex OBJECT-TYPE
    SYNTAX      Unsigned32
    MAX-ACCESS  read-only
    STATUS      current
    DESCRIPTION 
        "This column represents the index of the group in the system."
    ::= { bwDXSCallWaitingGroupEntry 1 }

  bwDXSCallWaitingGroupID OBJECT-TYPE
    SYNTAX      DisplayString
    MAX-ACCESS  read-only
    STATUS      current
    DESCRIPTION 
        "This string represents a group ID"
    ::= { bwDXSCallWaitingGroupEntry 2 }

  bwDXSCWGroupNumPhoneCancellations OBJECT-TYPE
    SYNTAX      Counter32
    MAX-ACCESS  read-write
    STATUS      current
    DESCRIPTION 
        "Number of times CW has been cancelled via FAC for users in a given group."
    ::= { bwDXSCallWaitingGroupEntry 3 }

  bwDXSAlternateNumbersSPTable OBJECT-TYPE
    SYNTAX      SEQUENCE OF BwAlternateNumbersSPEntry
    MAX-ACCESS  not-accessible
    STATUS      current
    DESCRIPTION 
        "This counter table will be indexed per service provider"
    ::= { alternateNumbers 1 }

  bwDXSAlternateNumbersSPEntry OBJECT-TYPE
    SYNTAX      BwAlternateNumbersSPEntry
    MAX-ACCESS  not-accessible
    STATUS      current
    DESCRIPTION 
        "Each row contains the service counters for the Alternate Numbers service for each service provider in the system."
    INDEX       { bwDXSAlternateNumbersSPIndex }
    ::= { bwDXSAlternateNumbersSPTable 1 }

  BwAlternateNumbersSPEntry ::= SEQUENCE {
    bwDXSAlternateNumbersSPIndex   Unsigned32,
    bwDXSAlternateNumbersSPID      DisplayString,
    bwDXSAlternateNumbersSPUsage   Counter32
  }

  bwDXSAlternateNumbersSPIndex OBJECT-TYPE
    SYNTAX      Unsigned32
    MAX-ACCESS  read-only
    STATUS      current
    DESCRIPTION 
        "This column represents the index of the service provider in the system"
    ::= { bwDXSAlternateNumbersSPEntry 1 }

  bwDXSAlternateNumbersSPID OBJECT-TYPE
    SYNTAX      DisplayString
    MAX-ACCESS  read-only
    STATUS      current
    DESCRIPTION 
        "This string represents a service provider ID"
    ::= { bwDXSAlternateNumbersSPEntry 2 }

  bwDXSAlternateNumbersSPUsage OBJECT-TYPE
    SYNTAX      Counter32
    MAX-ACCESS  read-write
    STATUS      current
    DESCRIPTION 
        "Counts all call made to a user's alternate number system per service provider"
    ::= { bwDXSAlternateNumbersSPEntry 3 }

  bwDXSAlternateNumbersUsage OBJECT-TYPE
    SYNTAX      Counter32
    MAX-ACCESS  read-write
    STATUS      current
    DESCRIPTION 
        "Counts all call made to a user's alternate number system"
    ::= { alternateNumbers 2 }

  bwDXSAlternateNumbersGroupTable OBJECT-TYPE
    SYNTAX      SEQUENCE OF BwAlternateNumbersGroupEntry
    MAX-ACCESS  not-accessible
    STATUS      current
    DESCRIPTION 
        "This counter table will be indexed per group"
    ::= { alternateNumbers 3 }

  bwDXSAlternateNumbersGroupEntry OBJECT-TYPE
    SYNTAX      BwAlternateNumbersGroupEntry
    MAX-ACCESS  not-accessible
    STATUS      current
    DESCRIPTION 
        "Each row contains the service counters for the Alternate Numbers service for each group in the system."
    INDEX       { bwDXSAlternateNumbersGroupIndex }
    ::= { bwDXSAlternateNumbersGroupTable 1 }

  BwAlternateNumbersGroupEntry ::= SEQUENCE {
    bwDXSAlternateNumbersGroupIndex    Unsigned32,
    bwDXSAlternateNumbersGroupID       DisplayString,
    bwDXSAlternateNumbersGroupUsage    Counter32
  }

  bwDXSAlternateNumbersGroupIndex OBJECT-TYPE
    SYNTAX      Unsigned32
    MAX-ACCESS  read-only
    STATUS      current
    DESCRIPTION 
        "This column represents the index of the group in the system"
    ::= { bwDXSAlternateNumbersGroupEntry 1 }

  bwDXSAlternateNumbersGroupID OBJECT-TYPE
    SYNTAX      DisplayString
    MAX-ACCESS  read-only
    STATUS      current
    DESCRIPTION 
        "This string represents a group ID"
    ::= { bwDXSAlternateNumbersGroupEntry 2 }

  bwDXSAlternateNumbersGroupUsage OBJECT-TYPE
    SYNTAX      Counter32
    MAX-ACCESS  read-write
    STATUS      current
    DESCRIPTION 
        "Counts all call made to a user's alternate number system per group"
    ::= { bwDXSAlternateNumbersGroupEntry 3 }

  bwDXSCotActivation OBJECT-TYPE
    SYNTAX      Counter32
    MAX-ACCESS  read-write
    STATUS      current
    DESCRIPTION 
        "This is the number of times that an attempt is made to issue a Customer Originated trace."
    ::= { cot 1 }

  bwDXSCotFailureNoId OBJECT-TYPE
    SYNTAX      Counter32
    MAX-ACCESS  read-write
    STATUS      current
    DESCRIPTION 
        "This is the number of times that an attempt to issue a Customer Originated trace failed."
    ::= { cot 2 }

  bwDXSCotSPTable OBJECT-TYPE
    SYNTAX      SEQUENCE OF BwCotSPEntry
    MAX-ACCESS  not-accessible
    STATUS      current
    DESCRIPTION 
        "Counters for customer originated trace service measurements for service providers"
    ::= { cot 3 }

  bwDXSCotSPEntry OBJECT-TYPE
    SYNTAX      BwCotSPEntry
    MAX-ACCESS  not-accessible
    STATUS      current
    DESCRIPTION 
        "Each row contains the service counters for the COT service for each service provider in the system."
    INDEX       { bwDXSCotSPIndex }
    ::= { bwDXSCotSPTable 1 }

  BwCotSPEntry ::= SEQUENCE {
    bwDXSCotSPIndex              Unsigned32,
    bwDXSCotSPID                 DisplayString,
    bwDXSCotSPActivation         Counter32,
    bwDXSCotSPFailureNoId        Counter32,
    bwDXSMidCallCotSPActivation  Counter32,
    bwDXSMidCallCotSPFailureNoId Counter32
  }

  bwDXSCotSPIndex OBJECT-TYPE
    SYNTAX      Unsigned32
    MAX-ACCESS  read-only
    STATUS      current
    DESCRIPTION 
        "This column represents the index of the service provider in the system"
    ::= { bwDXSCotSPEntry 1 }

  bwDXSCotSPID OBJECT-TYPE
    SYNTAX      DisplayString
    MAX-ACCESS  read-only
    STATUS      current
    DESCRIPTION 
        "This string represents a service provider ID"
    ::= { bwDXSCotSPEntry 2 }

  bwDXSCotSPActivation OBJECT-TYPE
    SYNTAX      Counter32
    MAX-ACCESS  read-write
    STATUS      current
    DESCRIPTION 
        "This is the number of times that an attempt is made to issue a Customer Originated trace. There is one instance of this counter for each service provider defined in the system."
    ::= { bwDXSCotSPEntry 3 }

  bwDXSCotSPFailureNoId OBJECT-TYPE
    SYNTAX      Counter32
    MAX-ACCESS  read-write
    STATUS      current
    DESCRIPTION 
        "This is the number of times that an attempt to issue a Customer Originated trace failed. There is one instance of this counter for each service provider defined in the system."
    ::= { bwDXSCotSPEntry 4 }

  bwDXSMidCallCotSPActivation OBJECT-TYPE
    SYNTAX      Counter32
    MAX-ACCESS  read-write
    STATUS      current
    DESCRIPTION 
        "This is the number of times that an attempt is made to issue a mid-call Customer Originated trace. There is one instance of this counter for each service provider defined in the system."
    ::= { bwDXSCotSPEntry 5 }

  bwDXSMidCallCotSPFailureNoId OBJECT-TYPE
    SYNTAX      Counter32
    MAX-ACCESS  read-write
    STATUS      current
    DESCRIPTION 
        "This is the number of times that an attempt to issue a mid-call Customer Originated trace failed. There is one instance of this counter for each service provider defined in the system."
    ::= { bwDXSCotSPEntry 6 }

  bwDXSCotGroupTable OBJECT-TYPE
    SYNTAX      SEQUENCE OF BwCotGroupEntry
    MAX-ACCESS  not-accessible
    STATUS      current
    DESCRIPTION 
        "Counters for customer originated trace service measurements for groups"
    ::= { cot 4 }

  bwDXSCotGroupEntry OBJECT-TYPE
    SYNTAX      BwCotGroupEntry
    MAX-ACCESS  not-accessible
    STATUS      current
    DESCRIPTION 
        "Each row contains the service counters for the COT service for each group in the system."
    INDEX       { bwDXSCotGroupIndex }
    ::= { bwDXSCotGroupTable 1 }

  BwCotGroupEntry ::= SEQUENCE {
    bwDXSCotGroupIndex              Unsigned32,
    bwDXSCotGroupID                 DisplayString,
    bwDXSCotGroupActivation         Counter32,
    bwDXSCotGroupFailureNoId        Counter32,
    bwDXSMidCallCotGroupActivation  Counter32,
    bwDXSMidCallCotGroupFailureNoId Counter32
  }

  bwDXSCotGroupIndex OBJECT-TYPE
    SYNTAX      Unsigned32
    MAX-ACCESS  read-only
    STATUS      current
    DESCRIPTION 
        "This column represents the index of the group in the system"
    ::= { bwDXSCotGroupEntry 1 }

  bwDXSCotGroupID OBJECT-TYPE
    SYNTAX      DisplayString
    MAX-ACCESS  read-only
    STATUS      current
    DESCRIPTION 
        "This string represents a group ID"
    ::= { bwDXSCotGroupEntry 2 }

  bwDXSCotGroupActivation OBJECT-TYPE
    SYNTAX      Counter32
    MAX-ACCESS  read-write
    STATUS      current
    DESCRIPTION 
        "This is the number of times that an attempt is made to issue a Customer Originated trace.There is one instance of this counter for each group defined in the system."
    ::= { bwDXSCotGroupEntry 3 }

  bwDXSCotGroupFailureNoId OBJECT-TYPE
    SYNTAX      Counter32
    MAX-ACCESS  read-write
    STATUS      current
    DESCRIPTION 
        "This is the number of times that an attempt to issue a Customer Originated trace failed. There is one instance of this counter for each group defined in the system."
    ::= { bwDXSCotGroupEntry 4 }

  bwDXSMidCallCotGroupActivation OBJECT-TYPE
    SYNTAX      Counter32
    MAX-ACCESS  read-write
    STATUS      current
    DESCRIPTION 
        "This is the number of times that an attempt is made to issue a mid-call Customer Originated trace.There is one instance of this counter for each group defined in the system."
    ::= { bwDXSCotGroupEntry 5 }

  bwDXSMidCallCotGroupFailureNoId OBJECT-TYPE
    SYNTAX      Counter32
    MAX-ACCESS  read-write
    STATUS      current
    DESCRIPTION 
        "This is the number of times that an attempt to issue a mid-call Customer Originated trace failed. There is one instance of this counter for each group defined in the system."
    ::= { bwDXSCotGroupEntry 6 }

  bwDXSMidCallCotActivation OBJECT-TYPE
    SYNTAX      Counter32
    MAX-ACCESS  read-write
    STATUS      current
    DESCRIPTION 
        "This is the number of times that an attempt is made to issue a mid-call Customer Originated trace."
    ::= { cot 5 }

  bwDXSMidCallCotFailureNoId OBJECT-TYPE
    SYNTAX      Counter32
    MAX-ACCESS  read-write
    STATUS      current
    DESCRIPTION 
        "This is the number of times that an attempt to issue a mid-call Customer Originated trace failed."
    ::= { cot 6 }

  bwDXSSD8NumTimesDialed OBJECT-TYPE
    SYNTAX      Counter32
    MAX-ACCESS  read-write
    STATUS      current
    DESCRIPTION 
        "Total number of times a speed code has been dialed"
    ::= { sd8 1 }

  bwDXSSD8NumTimesProgrammed OBJECT-TYPE
    SYNTAX      Counter32
    MAX-ACCESS  read-write
    STATUS      current
    DESCRIPTION 
        "Total number of times a speed code has been defined by a user via FAC"
    ::= { sd8 2 }

  bwDXSSD8SPTable OBJECT-TYPE
    SYNTAX      SEQUENCE OF BwSD8SPEntry
    MAX-ACCESS  not-accessible
    STATUS      current
    DESCRIPTION 
        "Counters for SD8 service measurements for service providers"
    ::= { sd8 3 }

  bwDXSSD8SPEntry OBJECT-TYPE
    SYNTAX      BwSD8SPEntry
    MAX-ACCESS  not-accessible
    STATUS      current
    DESCRIPTION 
        "Each row contains the service counters for the SD8 service for each service provider in the system."
    INDEX       { bwDXSSD8SPIndex }
    ::= { bwDXSSD8SPTable 1 }

  BwSD8SPEntry ::= SEQUENCE {
    bwDXSSD8SPIndex                Unsigned32,
    bwDXSSD8SPID                   DisplayString,
    bwDXSSD8SPNumTimesDialed       Counter32,
    bwDXSSD8SPNumTimesProgrammed   Counter32
  }

  bwDXSSD8SPIndex OBJECT-TYPE
    SYNTAX      Unsigned32
    MAX-ACCESS  read-only
    STATUS      current
    DESCRIPTION 
        "This column represents the index of the service provider in the system"
    ::= { bwDXSSD8SPEntry 1 }

  bwDXSSD8SPID OBJECT-TYPE
    SYNTAX      DisplayString
    MAX-ACCESS  read-only
    STATUS      current
    DESCRIPTION 
        "This string represents a service provider ID"
    ::= { bwDXSSD8SPEntry 2 }

  bwDXSSD8SPNumTimesDialed OBJECT-TYPE
    SYNTAX      Counter32
    MAX-ACCESS  read-write
    STATUS      current
    DESCRIPTION 
        "Total Number of times a speed code has been dialed by users in a given service provider"
    ::= { bwDXSSD8SPEntry 3 }

  bwDXSSD8SPNumTimesProgrammed OBJECT-TYPE
    SYNTAX      Counter32
    MAX-ACCESS  read-write
    STATUS      current
    DESCRIPTION 
        "Total numberNumber of times a speed code has been defined via FAC by users in a given service provider"
    ::= { bwDXSSD8SPEntry 4 }

  bwDXSSD8GroupTable OBJECT-TYPE
    SYNTAX      SEQUENCE OF BwSD8GroupEntry
    MAX-ACCESS  not-accessible
    STATUS      current
    DESCRIPTION 
        "Counters for SD8 service measurements for groups"
    ::= { sd8 4 }

  bwDXSSD8GroupEntry OBJECT-TYPE
    SYNTAX      BwSD8GroupEntry
    MAX-ACCESS  not-accessible
    STATUS      current
    DESCRIPTION 
        "Each row contains the service counters for the SD8 service for each group in the system."
    INDEX       { bwDXSSD8GroupIndex }
    ::= { bwDXSSD8GroupTable 1 }

  BwSD8GroupEntry ::= SEQUENCE {
    bwDXSSD8GroupIndex                 Unsigned32,
    bwDXSSD8GroupID                    DisplayString,
    bwDXSSD8GroupNumTimesDialed        Counter32,
    bwDXSSD8GroupNumTimesProgrammed    Counter32
  }

  bwDXSSD8GroupIndex OBJECT-TYPE
    SYNTAX      Unsigned32
    MAX-ACCESS  read-only
    STATUS      current
    DESCRIPTION 
        "This column represents the index of the group in the system"
    ::= { bwDXSSD8GroupEntry 1 }

  bwDXSSD8GroupID OBJECT-TYPE
    SYNTAX      DisplayString
    MAX-ACCESS  read-only
    STATUS      current
    DESCRIPTION 
        "This string represents a group ID"
    ::= { bwDXSSD8GroupEntry 2 }

  bwDXSSD8GroupNumTimesDialed OBJECT-TYPE
    SYNTAX      Counter32
    MAX-ACCESS  read-write
    STATUS      current
    DESCRIPTION 
        "Total Number of times a speed code has been dialed by users in a given group"
    ::= { bwDXSSD8GroupEntry 3 }

  bwDXSSD8GroupNumTimesProgrammed OBJECT-TYPE
    SYNTAX      Counter32
    MAX-ACCESS  read-write
    STATUS      current
    DESCRIPTION 
        "Total numberNumber of times a speed code has been defined via FAC by users in a given group"
    ::= { bwDXSSD8GroupEntry 4 }

  bwDXSMusicOnHoldNumUses OBJECT-TYPE
    SYNTAX      Counter32
    MAX-ACCESS  read-write
    STATUS      current
    DESCRIPTION 
        "Total number of times Music On Hold has been used"
    ::= { musicOnHold 1 }

  bwDXSMusicOnHoldSPTable OBJECT-TYPE
    SYNTAX      SEQUENCE OF BwMusicOnHoldSPEntry
    MAX-ACCESS  not-accessible
    STATUS      current
    DESCRIPTION 
        "Counters for Music On Hold service measurements for service providers"
    ::= { musicOnHold 2 }

  bwDXSMusicOnHoldSPEntry OBJECT-TYPE
    SYNTAX      BwMusicOnHoldSPEntry
    MAX-ACCESS  not-accessible
    STATUS      current
    DESCRIPTION 
        "Each row contains the service counters for the Music On Hold service for each service provider in the system."
    INDEX       { bwDXSMusicOnHoldSPIndex }
    ::= { bwDXSMusicOnHoldSPTable 1 }

  BwMusicOnHoldSPEntry ::= SEQUENCE {
    bwDXSMusicOnHoldSPIndex                        Unsigned32,
    bwDXSMusicOnHoldSPID                           DisplayString,
    bwDXSMusicOnHoldSPNumUses                      Counter32,
    bwDXSMusicOnHoldSPExternalSourceNumFailures    Counter32
  }

  bwDXSMusicOnHoldSPIndex OBJECT-TYPE
    SYNTAX      Unsigned32
    MAX-ACCESS  read-only
    STATUS      current
    DESCRIPTION 
        "This column represents the index of the service provider in the system"
    ::= { bwDXSMusicOnHoldSPEntry 1 }

  bwDXSMusicOnHoldSPID OBJECT-TYPE
    SYNTAX      DisplayString
    MAX-ACCESS  read-only
    STATUS      current
    DESCRIPTION 
        "This string represents a service provider ID"
    ::= { bwDXSMusicOnHoldSPEntry 2 }

  bwDXSMusicOnHoldSPNumUses OBJECT-TYPE
    SYNTAX      Counter32
    MAX-ACCESS  read-write
    STATUS      current
    DESCRIPTION 
        "The service provider counter is incremented every a user hears music on hold"
    ::= { bwDXSMusicOnHoldSPEntry 3 }

  bwDXSMusicOnHoldSPExternalSourceNumFailures OBJECT-TYPE
    SYNTAX      Counter32
    MAX-ACCESS  read-write
    STATUS      current
    DESCRIPTION 
        "This is the number of failures to terminate on music-on-hold source."
    ::= { bwDXSMusicOnHoldSPEntry 4 }

  bwDXSMusicOnHoldGroupTable OBJECT-TYPE
    SYNTAX      SEQUENCE OF BwMusicOnHoldGroupEntry
    MAX-ACCESS  not-accessible
    STATUS      current
    DESCRIPTION 
        "Counters for Music On Hold service measurements for groups"
    ::= { musicOnHold 3 }

  bwDXSMusicOnHoldGroupEntry OBJECT-TYPE
    SYNTAX      BwMusicOnHoldGroupEntry
    MAX-ACCESS  not-accessible
    STATUS      current
    DESCRIPTION 
        "Each row contains the service counters for the Music On Hold service for each group in the system."
    INDEX       { bwDXSMusicOnHoldGroupIndex }
    ::= { bwDXSMusicOnHoldGroupTable 1 }

  BwMusicOnHoldGroupEntry ::= SEQUENCE {
    bwDXSMusicOnHoldGroupIndex                         Unsigned32,
    bwDXSMusicOnHoldGroupID                            DisplayString,
    bwDXSMusicOnHoldGroupNumUses                       Counter32,
    bwDXSMusicOnHoldGroupExternalSourceNumFailures     Counter32
  }

  bwDXSMusicOnHoldGroupIndex OBJECT-TYPE
    SYNTAX      Unsigned32
    MAX-ACCESS  read-only
    STATUS      current
    DESCRIPTION 
        "This column represents the index of the group in the system"
    ::= { bwDXSMusicOnHoldGroupEntry 1 }

  bwDXSMusicOnHoldGroupID OBJECT-TYPE
    SYNTAX      DisplayString
    MAX-ACCESS  read-only
    STATUS      current
    DESCRIPTION 
        "This string represents a group ID"
    ::= { bwDXSMusicOnHoldGroupEntry 2 }

  bwDXSMusicOnHoldGroupNumUses OBJECT-TYPE
    SYNTAX      Counter32
    MAX-ACCESS  read-write
    STATUS      current
    DESCRIPTION 
        "The group counter is incremented every a user hears music on hold"
    ::= { bwDXSMusicOnHoldGroupEntry 3 }

  bwDXSMusicOnHoldGroupExternalSourceNumFailures OBJECT-TYPE
    SYNTAX      Counter32
    MAX-ACCESS  read-write
    STATUS      current
    DESCRIPTION 
        "This is the number of failures to terminate on music-on-hold source."
    ::= { bwDXSMusicOnHoldGroupEntry 4 }

  bwDXSMusicOnHoldExternalSourceNumFailures OBJECT-TYPE
    SYNTAX      Counter32
    MAX-ACCESS  read-write
    STATUS      current
    DESCRIPTION 
        "This counter is incremented whenever a caller is put on hold and the music-on-hold source could not be connected to the caller.  This counter is incremented in the context of the Music On Hold and Call Center services."
    ::= { musicOnHold 4 }

  bwDXSThirdPartyMWIControlNotifyIns OBJECT-TYPE
    SYNTAX      Counter32
    MAX-ACCESS  read-write
    STATUS      current
    DESCRIPTION 
        "Number of times a MWI NOTIFY is received."
    ::= { thirdPartyMWIControl 1 }

  bwDXSThirdPartyMWIControlNotifyFailures OBJECT-TYPE
    SYNTAX      Counter32
    MAX-ACCESS  read-write
    STATUS      current
    DESCRIPTION 
        "Number of times a MWI NOTIFY is received for an unknown user, or for a user who is not assigned the service."
    ::= { thirdPartyMWIControl 2 }

  bwDXSCFGNAForward OBJECT-TYPE
    SYNTAX      Counter32
    MAX-ACCESS  read-write
    STATUS      current
    DESCRIPTION 
        "This is the number of times Call Forwarding Group No Answer (CFGNA) has forwarded from one Hunt Group agent to another."
    ::= { callForwardGroupNoAnswer 1 }

  bwDXSCFGNAOverflowForward OBJECT-TYPE
    SYNTAX      Counter32
    MAX-ACCESS  read-write
    STATUS      current
    DESCRIPTION 
        "This is the number of times Call Forwarding Group No Answer rolls over to the first visited Hunt Group agent and the call forwards to the external destination."
    ::= { callForwardGroupNoAnswer 2 }

  bwDXSCFGNAOverflowNoForward OBJECT-TYPE
    SYNTAX      Counter32
    MAX-ACCESS  read-write
    STATUS      current
    DESCRIPTION 
        "This is the number of times Call Forwarding Group No Answer rolls over to the first visited Hunt Group agent and fails to forward the call."
    ::= { callForwardGroupNoAnswer 3 }

  bwDXSCFGNASPTable OBJECT-TYPE
    SYNTAX      SEQUENCE OF BwCFGNASPEntry
    MAX-ACCESS  not-accessible
    STATUS      current
    DESCRIPTION 
        "Counters for Call Center service measurements for service providers"
    ::= { callForwardGroupNoAnswer 4 }

  bwDXSCFGNASPEntry OBJECT-TYPE
    SYNTAX      BwCFGNASPEntry
    MAX-ACCESS  not-accessible
    STATUS      current
    DESCRIPTION 
        "Each row contains the service counters for the Call Forward Group No Answer service for each service provider in the system"
    INDEX       { bwDXSCFGNASPIndex }
    ::= { bwDXSCFGNASPTable 1 }

  BwCFGNASPEntry ::= SEQUENCE {
    bwDXSCFGNASPIndex              Unsigned32,
    bwDXSCFGNASPID                 DisplayString,
    bwDXSCFGNASPForward            Counter32,
    bwDXSCFGNASPOverflowForward    Counter32,
    bwDXSCFGNASPOverflowNoForward  Counter32,
    bwDXSCFGNASPExternalForward    Counter32,
    bwDXSCFGNASPExternalNoForward  Counter32
  }

  bwDXSCFGNASPIndex OBJECT-TYPE
    SYNTAX      Unsigned32
    MAX-ACCESS  read-only
    STATUS      current
    DESCRIPTION 
        "This column represents the index of the service provider in the system"
    ::= { bwDXSCFGNASPEntry 1 }

  bwDXSCFGNASPID OBJECT-TYPE
    SYNTAX      DisplayString
    MAX-ACCESS  read-only
    STATUS      current
    DESCRIPTION 
        "This string represents a service provider ID"
    ::= { bwDXSCFGNASPEntry 2 }

  bwDXSCFGNASPForward OBJECT-TYPE
    SYNTAX      Counter32
    MAX-ACCESS  read-write
    STATUS      current
    DESCRIPTION 
        "This is the number of times Call Forwarding Group No Answer has forwarded from one Hunt Group agent to another."
    ::= { bwDXSCFGNASPEntry 3 }

  bwDXSCFGNASPOverflowForward OBJECT-TYPE
    SYNTAX      Counter32
    MAX-ACCESS  read-write
    STATUS      current
    DESCRIPTION 
        "This is the number of times Call Forwarding Group No Answer rolls over to the first visited Hunt Group agent and the call forwards to the external destination."
    ::= { bwDXSCFGNASPEntry 4 }

  bwDXSCFGNASPOverflowNoForward OBJECT-TYPE
    SYNTAX      Counter32
    MAX-ACCESS  read-write
    STATUS      current
    DESCRIPTION 
        "This is the number of times Call Forwarding Group No Answer rolls over to the first visited Hunt Group agent and fails to forward the call."
    ::= { bwDXSCFGNASPEntry 5 }

  bwDXSCFGNASPExternalForward OBJECT-TYPE
    SYNTAX      Counter32
    MAX-ACCESS  read-write
    STATUS      current
    DESCRIPTION 
        "This is the number of times Call Forwarding Group No Answer External has forwarded a Hunt Group call under the service provider."
    ::= { bwDXSCFGNASPEntry 6 }

  bwDXSCFGNASPExternalNoForward OBJECT-TYPE
    SYNTAX      Counter32
    MAX-ACCESS  read-write
    STATUS      current
    DESCRIPTION 
        "This is the number of times Call Forwarding Group No Answer External fails to forward the call under the service provider."
    ::= { bwDXSCFGNASPEntry 7 }

  bwDXSCFGNAGroupTable OBJECT-TYPE
    SYNTAX      SEQUENCE OF BwCFGNAGroupEntry
    MAX-ACCESS  not-accessible
    STATUS      current
    DESCRIPTION 
        "Counters for Call Center service measurements for groups"
    ::= { callForwardGroupNoAnswer 5 }

  bwDXSCFGNAGroupEntry OBJECT-TYPE
    SYNTAX      BwCFGNAGroupEntry
    MAX-ACCESS  not-accessible
    STATUS      current
    DESCRIPTION 
        "Each row contains the service counters for the Call Forward Group No Answer service for each group in the system"
    INDEX       { bwDXSCFGNAGroupIndex }
    ::= { bwDXSCFGNAGroupTable 1 }

  BwCFGNAGroupEntry ::= SEQUENCE {
    bwDXSCFGNAGroupIndex               Unsigned32,
    bwDXSCFGNAGroupID                  DisplayString,
    bwDXSCFGNAGroupForward             Counter32,
    bwDXSCFGNAGroupOverflowForward     Counter32,
    bwDXSCFGNAGroupOverflowNoForward   Counter32,
    bwDXSCFGNAGroupExternalForward     Counter32,
    bwDXSCFGNAGroupExternalNoForward   Counter32
  }

  bwDXSCFGNAGroupIndex OBJECT-TYPE
    SYNTAX      Unsigned32
    MAX-ACCESS  read-only
    STATUS      current
    DESCRIPTION 
        "This column represents the index of the group in the system"
    ::= { bwDXSCFGNAGroupEntry 1 }

  bwDXSCFGNAGroupID OBJECT-TYPE
    SYNTAX      DisplayString
    MAX-ACCESS  read-only
    STATUS      current
    DESCRIPTION 
        "This string represents a group ID"
    ::= { bwDXSCFGNAGroupEntry 2 }

  bwDXSCFGNAGroupForward OBJECT-TYPE
    SYNTAX      Counter32
    MAX-ACCESS  read-write
    STATUS      current
    DESCRIPTION 
        "This is the number of times Call Forwarding Group No Answer has forwarded from one Hunt Group agent to another."
    ::= { bwDXSCFGNAGroupEntry 3 }

  bwDXSCFGNAGroupOverflowForward OBJECT-TYPE
    SYNTAX      Counter32
    MAX-ACCESS  read-write
    STATUS      current
    DESCRIPTION 
        "This is the number of times Call Forwarding Group No Answer rolls over to the first visited Hunt Group agent and the call forwards to the external destination."
    ::= { bwDXSCFGNAGroupEntry 4 }

  bwDXSCFGNAGroupOverflowNoForward OBJECT-TYPE
    SYNTAX      Counter32
    MAX-ACCESS  read-write
    STATUS      current
    DESCRIPTION 
        "This is the number of times Call Forwarding Group No Answer rolls over to the first visited Hunt Group agent and fails to forward the call."
    ::= { bwDXSCFGNAGroupEntry 5 }

  bwDXSCFGNAGroupExternalForward OBJECT-TYPE
    SYNTAX      Counter32
    MAX-ACCESS  read-write
    STATUS      current
    DESCRIPTION 
        "This is the number of times Call Forwarding Group No Answer External has forwarded a Hunt Group call in the group."
    ::= { bwDXSCFGNAGroupEntry 6 }

  bwDXSCFGNAGroupExternalNoForward OBJECT-TYPE
    SYNTAX      Counter32
    MAX-ACCESS  read-write
    STATUS      current
    DESCRIPTION 
        "This is the number of times Call Forwarding Group No Answer External fails to forward the call in the group."
    ::= { bwDXSCFGNAGroupEntry 7 }

  bwDXSCFGNAExternalForward OBJECT-TYPE
    SYNTAX      Counter32
    MAX-ACCESS  read-write
    STATUS      current
    DESCRIPTION 
        "This is the number of times Call Forwarding Group No Answer External has forwarded a Hunt Group call."
    ::= { callForwardGroupNoAnswer 6 }

  bwDXSCFGNAExternalNoForward OBJECT-TYPE
    SYNTAX      Counter32
    MAX-ACCESS  read-write
    STATUS      current
    DESCRIPTION 
        "This is the number of times Call Forwarding Group No Answer External fails to forward the call."
    ::= { callForwardGroupNoAnswer 7 }

  bwDXSSD100Program OBJECT-TYPE
    SYNTAX      Counter32
    MAX-ACCESS  read-write
    STATUS      current
    DESCRIPTION 
        "This counter is incremented each time a new SD100 call is programmed via FAC method on BroadWorks"
    ::= { sd100 1 }

  bwDXSSD100Call OBJECT-TYPE
    SYNTAX      Counter32
    MAX-ACCESS  read-write
    STATUS      current
    DESCRIPTION 
        "This counter is incremented each time SD100 code is used to originate a call on BroadWorks"
    ::= { sd100 2 }

  bwDXSSD100SPTable OBJECT-TYPE
    SYNTAX      SEQUENCE OF BwSD100SPEntry
    MAX-ACCESS  not-accessible
    STATUS      current
    DESCRIPTION 
        "Counters for sd100 service measurements for service providers"
    ::= { sd100 3 }

  bwDXSSD100SPEntry OBJECT-TYPE
    SYNTAX      BwSD100SPEntry
    MAX-ACCESS  not-accessible
    STATUS      current
    DESCRIPTION 
        "Each row contains the service counters for the sd100 service for each service provider in the system"
    INDEX       { bwDXSSD100SPIndex }
    ::= { bwDXSSD100SPTable 1 }

  BwSD100SPEntry ::= SEQUENCE {
    bwDXSSD100SPIndex      Unsigned32,
    bwDXSSD100SPID         DisplayString,
    bwDXSSD100SPProgram    Counter32,
    bwDXSSD100SPCall       Counter32
  }

  bwDXSSD100SPIndex OBJECT-TYPE
    SYNTAX      Unsigned32
    MAX-ACCESS  read-only
    STATUS      current
    DESCRIPTION 
        "This column represents the index of the service provider in the system"
    ::= { bwDXSSD100SPEntry 1 }

  bwDXSSD100SPID OBJECT-TYPE
    SYNTAX      DisplayString
    MAX-ACCESS  read-only
    STATUS      current
    DESCRIPTION 
        "This string represents a service provider ID"
    ::= { bwDXSSD100SPEntry 2 }

  bwDXSSD100SPProgram OBJECT-TYPE
    SYNTAX      Counter32
    MAX-ACCESS  read-write
    STATUS      current
    DESCRIPTION 
        "This counter is incremented each time a new SD100 call is programmed via the FAC method for a particular service provider"
    ::= { bwDXSSD100SPEntry 3 }

  bwDXSSD100SPCall OBJECT-TYPE
    SYNTAX      Counter32
    MAX-ACCESS  read-write
    STATUS      current
    DESCRIPTION 
        "This counter is incremented each time SD100 code is used to originate a call for a particular service provider"
    ::= { bwDXSSD100SPEntry 4 }

  bwDXSSD100GroupTable OBJECT-TYPE
    SYNTAX      SEQUENCE OF BwSD100GroupEntry
    MAX-ACCESS  not-accessible
    STATUS      current
    DESCRIPTION 
        "Counters for sd100 service measurements for groups"
    ::= { sd100 4 }

  bwDXSSD100GroupEntry OBJECT-TYPE
    SYNTAX      BwSD100GroupEntry
    MAX-ACCESS  not-accessible
    STATUS      current
    DESCRIPTION 
        "Each row contains the service counters for the sd100 service for each group in the system"
    INDEX       { bwDXSSD100GroupIndex }
    ::= { bwDXSSD100GroupTable 1 }

  BwSD100GroupEntry ::= SEQUENCE {
    bwDXSSD100GroupIndex       Unsigned32,
    bwDXSSD100GroupID          DisplayString,
    bwDXSSD100GroupProgram     Counter32,
    bwDXSSD100GroupCall        Counter32
  }

  bwDXSSD100GroupIndex OBJECT-TYPE
    SYNTAX      Unsigned32
    MAX-ACCESS  read-only
    STATUS      current
    DESCRIPTION 
        "This column represents the index of the group in the system"
    ::= { bwDXSSD100GroupEntry 1 }

  bwDXSSD100GroupID OBJECT-TYPE
    SYNTAX      DisplayString
    MAX-ACCESS  read-only
    STATUS      current
    DESCRIPTION 
        "This string represents a group ID"
    ::= { bwDXSSD100GroupEntry 2 }

  bwDXSSD100GroupProgram OBJECT-TYPE
    SYNTAX      Counter32
    MAX-ACCESS  read-write
    STATUS      current
    DESCRIPTION 
        "This counter is incremented each time a new SD100 call is programmed via the FAC method for a particular group"
    ::= { bwDXSSD100GroupEntry 3 }

  bwDXSSD100GroupCall OBJECT-TYPE
    SYNTAX      Counter32
    MAX-ACCESS  read-write
    STATUS      current
    DESCRIPTION 
        "This counter is incremented each time SD100 code is used to originate a call for a particular group"
    ::= { bwDXSSD100GroupEntry 4 }

  bwDXSThirdPartyVoiceMailNbOfCFWBusy OBJECT-TYPE
    SYNTAX      Counter32
    MAX-ACCESS  read-write
    STATUS      current
    DESCRIPTION 
        "Incremented each time a call is forwarded to an external VM (by the Third-Party Voice Mail Support User service) on busy condition"
    ::= { thirdPartyVMail 1 }

  bwDXSThirdPartyVoiceMailNbOfCFWNoAnswer OBJECT-TYPE
    SYNTAX      Counter32
    MAX-ACCESS  read-write
    STATUS      current
    DESCRIPTION 
        "Incremented each time a call is forwarded to an external VM (by the Third-Party Voice Mail Support User service) on no-answer condition, at the group level"
    ::= { thirdPartyVMail 2 }

  bwDXSThirdPartyVMailSPTable OBJECT-TYPE
    SYNTAX      SEQUENCE OF BwThirdPartyVMailSPEntry
    MAX-ACCESS  not-accessible
    STATUS      current
    DESCRIPTION 
        "Counters for the Third Party Voice Mail service measurements for service providers"
    ::= { thirdPartyVMail 3 }

  bwDXSThirdPartyVMailSPEntry OBJECT-TYPE
    SYNTAX      BwThirdPartyVMailSPEntry
    MAX-ACCESS  not-accessible
    STATUS      current
    DESCRIPTION 
        "Each row contains the service counters for the sd100 service for each service provider in the system"
    INDEX       { bwDXSThirdPartyVMailSPIndex }
    ::= { bwDXSThirdPartyVMailSPTable 1 }

  BwThirdPartyVMailSPEntry ::= SEQUENCE {
    bwDXSThirdPartyVMailSPIndex                Unsigned32,
    bwDXSThirdPartyVMailSPID                   DisplayString,
    bwDXSThirdPartyVoiceMailSPNbOfCFWBusy      Counter32,
    bwDXSThirdPartyVoiceMailSPNbOfCFWNoAnswer  Counter32
  }

  bwDXSThirdPartyVMailSPIndex OBJECT-TYPE
    SYNTAX      Unsigned32
    MAX-ACCESS  read-only
    STATUS      current
    DESCRIPTION 
        "This column represents the index of the service provider in the system"
    ::= { bwDXSThirdPartyVMailSPEntry 1 }

  bwDXSThirdPartyVMailSPID OBJECT-TYPE
    SYNTAX      DisplayString
    MAX-ACCESS  read-only
    STATUS      current
    DESCRIPTION 
        "This string represents a service provider ID"
    ::= { bwDXSThirdPartyVMailSPEntry 2 }

  bwDXSThirdPartyVoiceMailSPNbOfCFWBusy OBJECT-TYPE
    SYNTAX      Counter32
    MAX-ACCESS  read-write
    STATUS      current
    DESCRIPTION 
        "Incremented each time a call is forwarded to an external VM (by the Third-Party Voice Mail Support User service) on busy condition for a particular service provider"
    ::= { bwDXSThirdPartyVMailSPEntry 3 }

  bwDXSThirdPartyVoiceMailSPNbOfCFWNoAnswer OBJECT-TYPE
    SYNTAX      Counter32
    MAX-ACCESS  read-write
    STATUS      current
    DESCRIPTION 
        "Incremented each time a call is forwarded to an external VM (by the Third-Party Voice Mail Support User service) on no-answer condition, at the group level"
    ::= { bwDXSThirdPartyVMailSPEntry 4 }

  bwDXSThirdPartyVMailGroupTable OBJECT-TYPE
    SYNTAX      SEQUENCE OF BwThirdPartyVMailGroupEntry
    MAX-ACCESS  not-accessible
    STATUS      current
    DESCRIPTION 
        "Counters for the Third Party Voice Mail service measurements for groups"
    ::= { thirdPartyVMail 4 }

  bwDXSThirdPartyVMailGroupEntry OBJECT-TYPE
    SYNTAX      BwThirdPartyVMailGroupEntry
    MAX-ACCESS  not-accessible
    STATUS      current
    DESCRIPTION 
        "Each row contains the service counters for the sd100 service for each group in the system"
    INDEX       { bwDXSThirdPartyVMailGroupIndex }
    ::= { bwDXSThirdPartyVMailGroupTable 1 }

  BwThirdPartyVMailGroupEntry ::= SEQUENCE {
    bwDXSThirdPartyVMailGroupIndex                 Unsigned32,
    bwDXSThirdPartyVMailGroupID                    DisplayString,
    bwDXSThirdPartyVoiceMailGroupNbOfCFWBusy       Counter32,
    bwDXSThirdPartyVoiceMailGroupNbOfCFWNoAnswer   Counter32
  }

  bwDXSThirdPartyVMailGroupIndex OBJECT-TYPE
    SYNTAX      Unsigned32
    MAX-ACCESS  read-only
    STATUS      current
    DESCRIPTION 
        "This column represents the index of the group in the system"
    ::= { bwDXSThirdPartyVMailGroupEntry 1 }

  bwDXSThirdPartyVMailGroupID OBJECT-TYPE
    SYNTAX      DisplayString
    MAX-ACCESS  read-only
    STATUS      current
    DESCRIPTION 
        "This string represents a group ID"
    ::= { bwDXSThirdPartyVMailGroupEntry 2 }

  bwDXSThirdPartyVoiceMailGroupNbOfCFWBusy OBJECT-TYPE
    SYNTAX      Counter32
    MAX-ACCESS  read-write
    STATUS      current
    DESCRIPTION 
        "Incremented each time a call is forwarded to an external VM (by the Third-Party Voice Mail Support User service) on busy condition for a particular group"
    ::= { bwDXSThirdPartyVMailGroupEntry 3 }

  bwDXSThirdPartyVoiceMailGroupNbOfCFWNoAnswer OBJECT-TYPE
    SYNTAX      Counter32
    MAX-ACCESS  read-write
    STATUS      current
    DESCRIPTION 
        "Incremented each time a call is forwarded to an external VM (by the Third-Party Voice Mail Support User service) on no-answer condition, at the group level for a particular group"
    ::= { bwDXSThirdPartyVMailGroupEntry 4 }

  bwDXSDirectedCallPickupNumAttempts OBJECT-TYPE
    SYNTAX      Counter32
    MAX-ACCESS  read-write
    STATUS      current
    DESCRIPTION 
        "This counter shall be incremented each time a user attempts to pick up a call using the Directed Call Pickup FAC"
    ::= { directedCallPickup 1 }

  bwDXSDirectedCallPickupNumFailures OBJECT-TYPE
    SYNTAX      Counter32
    MAX-ACCESS  read-write
    STATUS      current
    DESCRIPTION 
        "This counter shall be incremented each time a user is unsuccessful at picking up a call using the Directed Call Pickup FAC"
    ::= { directedCallPickup 2 }

  bwDXSDirectedCallPickupSPTable OBJECT-TYPE
    SYNTAX      SEQUENCE OF BwDirectedCallPickupSPEntry
    MAX-ACCESS  not-accessible
    STATUS      current
    DESCRIPTION 
        "Counters for the Directed Call Pick Up service measurements for service providers"
    ::= { directedCallPickup 3 }

  bwDXSDirectedCallPickupSPEntry OBJECT-TYPE
    SYNTAX      BwDirectedCallPickupSPEntry
    MAX-ACCESS  not-accessible
    STATUS      current
    DESCRIPTION 
        "Each row contains the service counters for the directed call pick-up service for each service provider in the system"
    INDEX       { bwDXSDirectedCallPickupSPIndex }
    ::= { bwDXSDirectedCallPickupSPTable 1 }

  BwDirectedCallPickupSPEntry ::= SEQUENCE {
    bwDXSDirectedCallPickupSPIndex         Unsigned32,
    bwDXSDirectedCallPickupSPID            DisplayString,
    bwDXSDirectedCallPickupSPNumAttempts   Counter32,
    bwDXSDirectedCallPickupSPNumFailures   Counter32
  }

  bwDXSDirectedCallPickupSPIndex OBJECT-TYPE
    SYNTAX      Unsigned32
    MAX-ACCESS  read-only
    STATUS      current
    DESCRIPTION 
        "This column represents the index of the service provider in the system"
    ::= { bwDXSDirectedCallPickupSPEntry 1 }

  bwDXSDirectedCallPickupSPID OBJECT-TYPE
    SYNTAX      DisplayString
    MAX-ACCESS  read-only
    STATUS      current
    DESCRIPTION 
        "This string represents a service provider ID"
    ::= { bwDXSDirectedCallPickupSPEntry 2 }

  bwDXSDirectedCallPickupSPNumAttempts OBJECT-TYPE
    SYNTAX      Counter32
    MAX-ACCESS  read-write
    STATUS      current
    DESCRIPTION 
        "This counter shall be incremented each time a user attempts to pick up a call using the Directed Call Pickup FAC for a particular service provider"
    ::= { bwDXSDirectedCallPickupSPEntry 3 }

  bwDXSDirectedCallPickupSPNumFailures OBJECT-TYPE
    SYNTAX      Counter32
    MAX-ACCESS  read-write
    STATUS      current
    DESCRIPTION 
        "This counter shall be incremented each time a user is unsuccessful at picking up a call using the Directed Call Pickup FAC for a particular service provider"
    ::= { bwDXSDirectedCallPickupSPEntry 4 }

  bwDXSDirectedCallPickupGroupTable OBJECT-TYPE
    SYNTAX      SEQUENCE OF BwDirectedCallPickupGroupEntry
    MAX-ACCESS  not-accessible
    STATUS      current
    DESCRIPTION 
        "Counters for the Directed Call Pick Up service measurements for groups"
    ::= { directedCallPickup 4 }

  bwDXSDirectedCallPickupGroupEntry OBJECT-TYPE
    SYNTAX      BwDirectedCallPickupGroupEntry
    MAX-ACCESS  not-accessible
    STATUS      current
    DESCRIPTION 
        "Each row contains the service counters for the directed call pick-up service for each service provider in the system"
    INDEX       { bwDXSDirectedCallPickupGroupIndex }
    ::= { bwDXSDirectedCallPickupGroupTable 1 }

  BwDirectedCallPickupGroupEntry ::= SEQUENCE {
    bwDXSDirectedCallPickupGroupIndex          Unsigned32,
    bwDXSDirectedCallPickupGroupID             DisplayString,
    bwDXSDirectedCallPickupGroupNumAttempts    Counter32,
    bwDXSDirectedCallPickupGroupNumFailures    Counter32
  }

  bwDXSDirectedCallPickupGroupIndex OBJECT-TYPE
    SYNTAX      Unsigned32
    MAX-ACCESS  read-only
    STATUS      current
    DESCRIPTION 
        "This column represents the index of the service provider in the system"
    ::= { bwDXSDirectedCallPickupGroupEntry 1 }

  bwDXSDirectedCallPickupGroupID OBJECT-TYPE
    SYNTAX      DisplayString
    MAX-ACCESS  read-only
    STATUS      current
    DESCRIPTION 
        "This string represents a service provider ID"
    ::= { bwDXSDirectedCallPickupGroupEntry 2 }

  bwDXSDirectedCallPickupGroupNumAttempts OBJECT-TYPE
    SYNTAX      Counter32
    MAX-ACCESS  read-write
    STATUS      current
    DESCRIPTION 
        "This counter shall be incremented each time a user attempts to pick up a call using the Directed Call Pickup FAC for a particular group"
    ::= { bwDXSDirectedCallPickupGroupEntry 3 }

  bwDXSDirectedCallPickupGroupNumFailures OBJECT-TYPE
    SYNTAX      Counter32
    MAX-ACCESS  read-write
    STATUS      current
    DESCRIPTION 
        "This counter shall be incremented each time a user is unsuccessful at picking up a call using the Directed Call Pickup FAC for a particular group"
    ::= { bwDXSDirectedCallPickupGroupEntry 4 }

  bwDXSFlashCallHoldNumActivations OBJECT-TYPE
    SYNTAX      Counter32
    MAX-ACCESS  read-write
    STATUS      current
    DESCRIPTION 
        "This counter shall be incremented each time a user successfully holds a call via the Flash Call Hold FAC"
    ::= { flashCallHold 1 }

  bwDXSFlashCallHoldSPTable OBJECT-TYPE
    SYNTAX      SEQUENCE OF BwFlashCallHoldSPEntry
    MAX-ACCESS  not-accessible
    STATUS      current
    DESCRIPTION 
        "Counters for the Flash Call Hold service measurements for service providers"
    ::= { flashCallHold 2 }

  bwDXSFlashCallHoldSPEntry OBJECT-TYPE
    SYNTAX      BwFlashCallHoldSPEntry
    MAX-ACCESS  not-accessible
    STATUS      current
    DESCRIPTION 
        "Each row contains the service counters for the directed call pick-up service for each service provider in the system"
    INDEX       { bwDXSFlashCallHoldSPIndex }
    ::= { bwDXSFlashCallHoldSPTable 1 }

  BwFlashCallHoldSPEntry ::= SEQUENCE {
    bwDXSFlashCallHoldSPIndex              Unsigned32,
    bwDXSFlashCallHoldSPID                 DisplayString,
    bwDXSFlashCallHoldSPNumActivations     Counter32
  }

  bwDXSFlashCallHoldSPIndex OBJECT-TYPE
    SYNTAX      Unsigned32
    MAX-ACCESS  read-only
    STATUS      current
    DESCRIPTION 
        "This column represents the index of the service provider in the system"
    ::= { bwDXSFlashCallHoldSPEntry 1 }

  bwDXSFlashCallHoldSPID OBJECT-TYPE
    SYNTAX      DisplayString
    MAX-ACCESS  read-only
    STATUS      current
    DESCRIPTION 
        "This string represents a service provider ID"
    ::= { bwDXSFlashCallHoldSPEntry 2 }

  bwDXSFlashCallHoldSPNumActivations OBJECT-TYPE
    SYNTAX      Counter32
    MAX-ACCESS  read-write
    STATUS      current
    DESCRIPTION 
        "This counter shall be incremented each time a user successfully holds a call via the Flash Call Hold FAC for a specigic service provider"
    ::= { bwDXSFlashCallHoldSPEntry 3 }

  bwDXSFlashCallHoldGroupTable OBJECT-TYPE
    SYNTAX      SEQUENCE OF BwFlashCallHoldGroupEntry
    MAX-ACCESS  not-accessible
    STATUS      current
    DESCRIPTION 
        "Counters for the Flash Call Hold service measurements for groups"
    ::= { flashCallHold 3 }

  bwDXSFlashCallHoldGroupEntry OBJECT-TYPE
    SYNTAX      BwFlashCallHoldGroupEntry
    MAX-ACCESS  not-accessible
    STATUS      current
    DESCRIPTION 
        "Each row contains the service counters for the directed call pick-up service for each group in the system"
    INDEX       { bwDXSFlashCallHoldGroupIndex }
    ::= { bwDXSFlashCallHoldGroupTable 1 }

  BwFlashCallHoldGroupEntry ::= SEQUENCE {
    bwDXSFlashCallHoldGroupIndex           Unsigned32,
    bwDXSFlashCallHoldGroupID              DisplayString,
    bwDXSFlashCallHoldGroupNumActivations  Counter32
  }

  bwDXSFlashCallHoldGroupIndex OBJECT-TYPE
    SYNTAX      Unsigned32
    MAX-ACCESS  read-only
    STATUS      current
    DESCRIPTION 
        "This column represents the index of the service provider in the system"
    ::= { bwDXSFlashCallHoldGroupEntry 1 }

  bwDXSFlashCallHoldGroupID OBJECT-TYPE
    SYNTAX      DisplayString
    MAX-ACCESS  read-only
    STATUS      current
    DESCRIPTION 
        "This string represents a service provider ID"
    ::= { bwDXSFlashCallHoldGroupEntry 2 }

  bwDXSFlashCallHoldGroupNumActivations OBJECT-TYPE
    SYNTAX      Counter32
    MAX-ACCESS  read-write
    STATUS      current
    DESCRIPTION 
        "This counter shall be incremented each time a user successfully holds a call via the Flash Call Hold FAC for a specigic group"
    ::= { bwDXSFlashCallHoldGroupEntry 3 }

  bwDXSDPUBIAttempt OBJECT-TYPE
    SYNTAX      Counter32
    MAX-ACCESS  read-write
    STATUS      current
    DESCRIPTION 
        "This counter is incremented each time a user attempts Directed Call Pickup with Barge-in"
    ::= { dpubi 1 }

  bwDXSDPUBIFailure OBJECT-TYPE
    SYNTAX      Counter32
    MAX-ACCESS  read-write
    STATUS      current
    DESCRIPTION 
        "This counter is incremented each time a user fails to pickup a call with Directed Call Pickup with Barge-in"
    ::= { dpubi 2 }

  bwDXSDPUBIBargeIn OBJECT-TYPE
    SYNTAX      Counter32
    MAX-ACCESS  read-write
    STATUS      current
    DESCRIPTION 
        "This counter is incremented each time a user successfully barges into a call with Directed Call Pickup with Barge-in"
    ::= { dpubi 3 }

  bwDXSDPUBIBargeInFailure OBJECT-TYPE
    SYNTAX      Counter32
    MAX-ACCESS  read-write
    STATUS      current
    DESCRIPTION 
        "This counter is incremented each time a user fails to barge into a call with Directed Call Pickup with Barge-in"
    ::= { dpubi 4 }

  bwDXSDPUBISPTable OBJECT-TYPE
    SYNTAX      SEQUENCE OF BwDPUBISPEntry
    MAX-ACCESS  not-accessible
    STATUS      current
    DESCRIPTION 
        "Counters for the Directed Call Pickup with Barge In service measurements for service providers"
    ::= { dpubi 5 }

  bwDXSDPUBISPEntry OBJECT-TYPE
    SYNTAX      BwDPUBISPEntry
    MAX-ACCESS  not-accessible
    STATUS      current
    DESCRIPTION 
        "Each row contains the service counters for the Directed Call Pickup with Barge In service for each service provider in the system"
    INDEX       { bwDXSDPUBISPIndex }
    ::= { bwDXSDPUBISPTable 1 }

  BwDPUBISPEntry ::= SEQUENCE {
    bwDXSDPUBISPIndex                            Unsigned32,
    bwDXSDPUBISPID                               DisplayString,
    bwDXSDPUBISPAttempt                          Counter32,
    bwDXSDPUBISPFailure                          Counter32,
    bwDXSDPUBISPBargeIn                          Counter32,
    bwDXSDPUBISPBargeInFailure                   Counter32,
    bwDXSDPUBISPExempt                           Counter32,
    bwDXSDPUBISPNumSilentlyMonitoredCalls        Counter32,
    bwDXSDPUBISPNumSilentlyMonitoredCallsFailure Counter32,
    bwDXSDPUBISPNumMonitorNextCallRequest        Counter32,
    bwDXSDPUBISPNumMonitorNextCallRequestFailure Counter32
  }

  bwDXSDPUBISPIndex OBJECT-TYPE
    SYNTAX      Unsigned32
    MAX-ACCESS  read-only
    STATUS      current
    DESCRIPTION 
        "This column represents the index of the service provider in the system"
    ::= { bwDXSDPUBISPEntry 1 }

  bwDXSDPUBISPID OBJECT-TYPE
    SYNTAX      DisplayString
    MAX-ACCESS  read-only
    STATUS      current
    DESCRIPTION 
        "This string represents a service provider ID"
    ::= { bwDXSDPUBISPEntry 2 }

  bwDXSDPUBISPAttempt OBJECT-TYPE
    SYNTAX      Counter32
    MAX-ACCESS  read-write
    STATUS      current
    DESCRIPTION 
        "This counter is incremented each time a user under the Service Provider attempts Directed Call Pickup with Barge-in"
    ::= { bwDXSDPUBISPEntry 3 }

  bwDXSDPUBISPFailure OBJECT-TYPE
    SYNTAX      Counter32
    MAX-ACCESS  read-write
    STATUS      current
    DESCRIPTION 
        "This counter is incremented each time a user under the Service Provider fails to pickup a call with Directed Call Pickup with Barge-in"
    ::= { bwDXSDPUBISPEntry 4 }

  bwDXSDPUBISPBargeIn OBJECT-TYPE
    SYNTAX      Counter32
    MAX-ACCESS  read-write
    STATUS      current
    DESCRIPTION 
        "This counter is incremented each time a user under the Service Provider successfully barges into a call with Directed Call Pickup with Barge-in"
    ::= { bwDXSDPUBISPEntry 5 }

  bwDXSDPUBISPBargeInFailure OBJECT-TYPE
    SYNTAX      Counter32
    MAX-ACCESS  read-write
    STATUS      current
    DESCRIPTION 
        "This counter is incremented each time a user under the Service Provider fails to barge into a call with Directed Call Pickup with Barge-in"
    ::= { bwDXSDPUBISPEntry 6 }

  bwDXSDPUBISPExempt OBJECT-TYPE
    SYNTAX      Counter32
    MAX-ACCESS  read-write
    STATUS      current
    DESCRIPTION 
        "This counter is incremented each time a DPUBI attempt is blocked by the picked up user's Barge-in Exempt service for a given service provider."
    ::= { bwDXSDPUBISPEntry 7 }

  bwDXSDPUBISPNumSilentlyMonitoredCalls OBJECT-TYPE
    SYNTAX      Counter32
    MAX-ACCESS  read-write
    STATUS      current
    DESCRIPTION 
        "This is the number of times that a supervisor silently monitored a call successfully. There is one instance of this counter for each service provider defined in the system."
    ::= { bwDXSDPUBISPEntry 8 }

  bwDXSDPUBISPNumSilentlyMonitoredCallsFailure OBJECT-TYPE
    SYNTAX      Counter32
    MAX-ACCESS  read-write
    STATUS      current
    DESCRIPTION 
        "This is the number of times that a supervisor failed to silently monitor a call. There is one instance of this counter for each service provider defined in the system."
    ::= { bwDXSDPUBISPEntry 9 }

  bwDXSDPUBISPNumMonitorNextCallRequest OBJECT-TYPE
    SYNTAX      Counter32
    MAX-ACCESS  read-write
    STATUS      current
    DESCRIPTION 
        "This is the number of times that a request to Monitor Next Call is invoked successfully.  There is one instance of this counter for each service provider defined in the system."
    ::= { bwDXSDPUBISPEntry 10 }

  bwDXSDPUBISPNumMonitorNextCallRequestFailure OBJECT-TYPE
    SYNTAX      Counter32
    MAX-ACCESS  read-write
    STATUS      current
    DESCRIPTION 
        "This is the number of times that a request to Monitor Next Call failed.  There is one instance of this counter for each service provider defined in the system."
    ::= { bwDXSDPUBISPEntry 11 }

  bwDXSDPUBIGroupTable OBJECT-TYPE
    SYNTAX      SEQUENCE OF BwDPUBIGroupEntry
    MAX-ACCESS  not-accessible
    STATUS      current
    DESCRIPTION 
        "Counters for the Directed Call Pickup with Barge In service measurements for groups"
    ::= { dpubi 6 }

  bwDXSDPUBIGroupEntry OBJECT-TYPE
    SYNTAX      BwDPUBIGroupEntry
    MAX-ACCESS  not-accessible
    STATUS      current
    DESCRIPTION 
        "Each row contains the service counters for the Directed Call Pickup with Barge In service for each group in the system"
    INDEX       { bwDXSDPUBIGroupIndex }
    ::= { bwDXSDPUBIGroupTable 1 }

  BwDPUBIGroupEntry ::= SEQUENCE {
    bwDXSDPUBIGroupIndex                            Unsigned32,
    bwDXSDPUBIGroupID                               DisplayString,
    bwDXSDPUBIGroupAttempt                          Counter32,
    bwDXSDPUBIGroupFailure                          Counter32,
    bwDXSDPUBIGroupBargeIn                          Counter32,
    bwDXSDPUBIGroupBargeInFailure                   Counter32,
    bwDXSDPUBIGroupExempt                           Counter32,
    bwDXSDPUBIGroupNumSilentlyMonitoredCalls        Counter32,
    bwDXSDPUBIGroupNumSilentlyMonitoredCallsFailure Counter32,
    bwDXSDPUBIGroupNumMonitorNextCallRequest        Counter32,
    bwDXSDPUBIGroupNumMonitorNextCallRequestFailure Counter32
  }

  bwDXSDPUBIGroupIndex OBJECT-TYPE
    SYNTAX      Unsigned32
    MAX-ACCESS  read-only
    STATUS      current
    DESCRIPTION 
        "This column represents the index of the group in the system"
    ::= { bwDXSDPUBIGroupEntry 1 }

  bwDXSDPUBIGroupID OBJECT-TYPE
    SYNTAX      DisplayString
    MAX-ACCESS  read-only
    STATUS      current
    DESCRIPTION 
        "This string represents a group ID"
    ::= { bwDXSDPUBIGroupEntry 2 }

  bwDXSDPUBIGroupAttempt OBJECT-TYPE
    SYNTAX      Counter32
    MAX-ACCESS  read-write
    STATUS      current
    DESCRIPTION 
        "This counter is incremented each time a user under the group attempts Directed Call Pickup with Barge-in"
    ::= { bwDXSDPUBIGroupEntry 3 }

  bwDXSDPUBIGroupFailure OBJECT-TYPE
    SYNTAX      Counter32
    MAX-ACCESS  read-write
    STATUS      current
    DESCRIPTION 
        "This counter is incremented each time a user under the group fails to pickup a call with Directed Call Pickup with Barge-in"
    ::= { bwDXSDPUBIGroupEntry 4 }

  bwDXSDPUBIGroupBargeIn OBJECT-TYPE
    SYNTAX      Counter32
    MAX-ACCESS  read-write
    STATUS      current
    DESCRIPTION 
        "This counter is incremented each time a user under the group successfully barges into a call with Directed Call Pickup with Barge-in"
    ::= { bwDXSDPUBIGroupEntry 5 }

  bwDXSDPUBIGroupBargeInFailure OBJECT-TYPE
    SYNTAX      Counter32
    MAX-ACCESS  read-write
    STATUS      current
    DESCRIPTION 
        "This counter is incremented each time a user under the group fails to barge into a call with Directed Call Pickup with Barge-in"
    ::= { bwDXSDPUBIGroupEntry 6 }

  bwDXSDPUBIGroupExempt OBJECT-TYPE
    SYNTAX      Counter32
    MAX-ACCESS  read-write
    STATUS      current
    DESCRIPTION 
        "This counter is incremented each time a DPUBI attempt is blocked by the picked up user's Barge-in Exempt service for a given group."
    ::= { bwDXSDPUBIGroupEntry 7 }

  bwDXSDPUBIGroupNumSilentlyMonitoredCalls OBJECT-TYPE
    SYNTAX      Counter32
    MAX-ACCESS  read-write
    STATUS      current
    DESCRIPTION 
        "This is the number of times that a supervisor silently monitored a call successfully. There is one instance of this counter for each group defined in the system."
    ::= { bwDXSDPUBIGroupEntry 8 }

  bwDXSDPUBIGroupNumSilentlyMonitoredCallsFailure OBJECT-TYPE
    SYNTAX      Counter32
    MAX-ACCESS  read-write
    STATUS      current
    DESCRIPTION 
        "This is the number of times that a supervisor failed to silently monitor a call.There is one instance of this counter for each group defined in the system."
    ::= { bwDXSDPUBIGroupEntry 9 }

  bwDXSDPUBIGroupNumMonitorNextCallRequest OBJECT-TYPE
    SYNTAX      Counter32
    MAX-ACCESS  read-write
    STATUS      current
    DESCRIPTION 
        "This is the number of times that a request to Monitor Next Call is invoked successfully.  There is one instance of this counter for each group defined in the system."
    ::= { bwDXSDPUBIGroupEntry 10 }

  bwDXSDPUBIGroupNumMonitorNextCallRequestFailure OBJECT-TYPE
    SYNTAX      Counter32
    MAX-ACCESS  read-write
    STATUS      current
    DESCRIPTION 
        "This is the number of times that a request to Monitor Next Call failed.  There is one instance of this counter for each group defined in the system."
    ::= { bwDXSDPUBIGroupEntry 11 }

  bwDXSDPUBIExempt OBJECT-TYPE
    SYNTAX      Counter32
    MAX-ACCESS  read-write
    STATUS      current
    DESCRIPTION 
        "This counter is incremented each time a DPUBI attempt is blocked by the picked up user's Barge-in Exempt service."
    ::= { dpubi 7 }

  bwDXSDPUBINumSilentlyMonitoredCalls OBJECT-TYPE
    SYNTAX      Counter32
    MAX-ACCESS  read-write
    STATUS      current
    DESCRIPTION 
        "This is the number of times that a supervisor silently monitored a call successfully."
    ::= { dpubi 8 }

  bwDXSDPUBINumSilentlyMonitoredCallsFailure OBJECT-TYPE
    SYNTAX      Counter32
    MAX-ACCESS  read-write
    STATUS      current
    DESCRIPTION 
        "This is the number of times that a supervisor failed to silently monitor a call."
    ::= { dpubi 9 }

  bwDXSDPUBINumMonitorNextCallRequest OBJECT-TYPE
    SYNTAX      Counter32
    MAX-ACCESS  read-write
    STATUS      current
    DESCRIPTION 
        "This is the number of times that a request to Monitor Next Call is invoked successfully."
    ::= { dpubi 10 }

  bwDXSDPUBINumMonitorNextCallRequestFailure OBJECT-TYPE
    SYNTAX      Counter32
    MAX-ACCESS  read-write
    STATUS      current
    DESCRIPTION 
        "This is the number of times that a request to Monitor Next Call failed."
    ::= { dpubi 11 }

-- Service : ACB ...........................................

  bwDXSACBStarted OBJECT-TYPE
    SYNTAX      Counter32
    MAX-ACCESS  read-write
    STATUS      current
    DESCRIPTION 
        "System wide, number of times Automatic Callback has been activated"
    ::= { acb 1 }

  bwDXSACBExpired OBJECT-TYPE
    SYNTAX      Counter32
    MAX-ACCESS  read-write
    STATUS      current
    DESCRIPTION 
        "System wide, number of times Automatic Callback's time to wait for an idle line has expired. The default time to wait is 30 minutes"
    ::= { acb 2 }

  bwDXSACBSPTable OBJECT-TYPE
    SYNTAX      SEQUENCE OF BwACBSPEntry
    MAX-ACCESS  not-accessible
    STATUS      current
    DESCRIPTION 
        "Counters for the Automatic Call Back service measurements for service providers"
    ::= { acb 4 }

  bwDXSACBSPEntry OBJECT-TYPE
    SYNTAX      BwACBSPEntry
    MAX-ACCESS  not-accessible
    STATUS      current
    DESCRIPTION 
        "Each row contains the service counters for the Automatic Call Back service for each service provider in the system"
    INDEX       { bwDXSACBSPIndex }
    ::= { bwDXSACBSPTable 1 }

  BwACBSPEntry ::= SEQUENCE {
    bwDXSACBSPIndex                    Unsigned32,
    bwDXSACBSPID                       DisplayString,
    bwDXSACBSPStarted                  Counter32,
    bwDXSACBSPExpired                  Counter32,
    bwDXSACBSPMaxOrigSession           Counter32,
    bwDXSACBSPMaxTermSession           Counter32,
    bwDXSLegacyACBSPOrigSession        Counter32,
    bwDXSLegacyACBSPOrigSuccessSession Counter32,
    bwDXSLegacyACBSPOrigFailedSession  Counter32,
    bwDXSLegacyACBSPTermSession        Counter32,
    bwDXSLegacyACBSPTermSuccessSession Counter32,
    bwDXSLegacyACBSPTermFailedSession  Counter32
  }

  bwDXSACBSPIndex OBJECT-TYPE
    SYNTAX      Unsigned32
    MAX-ACCESS  read-only
    STATUS      current
    DESCRIPTION 
        "This column represents the index of the service provider in the system"
    ::= { bwDXSACBSPEntry 1 }

  bwDXSACBSPID OBJECT-TYPE
    SYNTAX      DisplayString
    MAX-ACCESS  read-only
    STATUS      current
    DESCRIPTION 
        "This string represents a service provider ID"
    ::= { bwDXSACBSPEntry 2 }

  bwDXSACBSPStarted OBJECT-TYPE
    SYNTAX      Counter32
    MAX-ACCESS  read-write
    STATUS      current
    DESCRIPTION 
        "Number of times Automatic Callback has been activated for a given service provider"
    ::= { bwDXSACBSPEntry 3 }

  bwDXSACBSPExpired OBJECT-TYPE
    SYNTAX      Counter32
    MAX-ACCESS  read-write
    STATUS      current
    DESCRIPTION 
        "Number of times Automatic Callback's time to wait for an idle line has expired for a given service provider. The default time to wait is 30 minutes."
    ::= { bwDXSACBSPEntry 4 }

  bwDXSACBSPMaxOrigSession OBJECT-TYPE
    SYNTAX      Counter32
    MAX-ACCESS  read-write
    STATUS      current
    DESCRIPTION 
        "Service Provider level, number of times the max number of Automatic Callback sessions has been reached for the originator."
    ::= { bwDXSACBSPEntry 6 }

  bwDXSACBSPMaxTermSession OBJECT-TYPE
    SYNTAX      Counter32
    MAX-ACCESS  read-write
    STATUS      current
    DESCRIPTION 
        "Service Provider level, number of times the max number of Automatic Callback sessions has been reached for the terminator."
    ::= { bwDXSACBSPEntry 7 }

  bwDXSLegacyACBSPOrigSession OBJECT-TYPE
    SYNTAX      Counter32
    MAX-ACCESS  read-write
    STATUS      current
    DESCRIPTION 
        "This is the number of times the Automatic Callback session has been initiated. There is one instance of this counter for each service provider defined in the system."
    ::= { bwDXSACBSPEntry 8 }

  bwDXSLegacyACBSPOrigSuccessSession OBJECT-TYPE
    SYNTAX      Counter32
    MAX-ACCESS  read-write
    STATUS      current
    DESCRIPTION 
        "This is the number of times the Automatic Callback session has been initiated successfully.  There is one instance of this counter for each service provider defined in the system."
    ::= { bwDXSACBSPEntry 9 }

  bwDXSLegacyACBSPOrigFailedSession OBJECT-TYPE
    SYNTAX      Counter32
    MAX-ACCESS  read-write
    STATUS      current
    DESCRIPTION 
        "This is the number of times the Automatic Callback session has failed.  There is one instance of this counter for each service provider defined in the system."
    ::= { bwDXSACBSPEntry 10 }

  bwDXSLegacyACBSPTermSession OBJECT-TYPE
    SYNTAX      Counter32
    MAX-ACCESS  read-write
    STATUS      current
    DESCRIPTION 
        "This is the number of times an Automatic Callback session request has been received on this switch.  There is one instance of this counter for each service provider defined in the system."
    ::= { bwDXSACBSPEntry 11 }

  bwDXSLegacyACBSPTermSuccessSession OBJECT-TYPE
    SYNTAX      Counter32
    MAX-ACCESS  read-write
    STATUS      current
    DESCRIPTION 
        "This is the number of times an Automatic Callback session request has been received on this switch successfully.  There is one instance of this counter for each service provider defined in the system."
    ::= { bwDXSACBSPEntry 12 }

  bwDXSLegacyACBSPTermFailedSession OBJECT-TYPE
    SYNTAX      Counter32
    MAX-ACCESS  read-write
    STATUS      current
    DESCRIPTION 
        "This is the number of times an Automatic Callback session request has failed on this switch.  There is one instance of this counter for each service provider defined in the system."
    ::= { bwDXSACBSPEntry 13 }

  bwDXSACBGroupTable OBJECT-TYPE
    SYNTAX      SEQUENCE OF BwACBGroupEntry
    MAX-ACCESS  not-accessible
    STATUS      current
    DESCRIPTION 
        "Counters for the Automatic Call Back service measurements for groups"
    ::= { acb 5 }

  bwDXSACBGroupEntry OBJECT-TYPE
    SYNTAX      BwACBGroupEntry
    MAX-ACCESS  not-accessible
    STATUS      current
    DESCRIPTION 
        "Each row contains the service counters for the Automatic Call Back service for each group in the system"
    INDEX       { bwDXSACBGroupIndex }
    ::= { bwDXSACBGroupTable 1 }

  BwACBGroupEntry ::= SEQUENCE {
    bwDXSACBGroupIndex                    Unsigned32,
    bwDXSACBGroupID                       DisplayString,
    bwDXSACBGroupStarted                  Counter32,
    bwDXSACBGroupExpired                  Counter32,
    bwDXSACBGroupMaxOrigSession           Counter32,
    bwDXSACBGroupMaxTermSession           Counter32,
    bwDXSLegacyACBGroupOrigSession        Counter32,
    bwDXSLegacyACBGroupOrigSuccessSession Counter32,
    bwDXSLegacyACBGroupOrigFailedSession  Counter32,
    bwDXSLegacyACBGroupTermSession        Counter32,
    bwDXSLegacyACBGroupTermSuccessSession Counter32,
    bwDXSLegacyACBGroupTermFailedSession  Counter32
  }

  bwDXSACBGroupIndex OBJECT-TYPE
    SYNTAX      Unsigned32
    MAX-ACCESS  read-only
    STATUS      current
    DESCRIPTION 
        "This column represents the index of the group in the system"
    ::= { bwDXSACBGroupEntry 1 }

  bwDXSACBGroupID OBJECT-TYPE
    SYNTAX      DisplayString
    MAX-ACCESS  read-only
    STATUS      current
    DESCRIPTION 
        "This string represents a group ID"
    ::= { bwDXSACBGroupEntry 2 }

  bwDXSACBGroupStarted OBJECT-TYPE
    SYNTAX      Counter32
    MAX-ACCESS  read-write
    STATUS      current
    DESCRIPTION 
        "Number of times Automatic Callback has been activated for a given group"
    ::= { bwDXSACBGroupEntry 3 }

  bwDXSACBGroupExpired OBJECT-TYPE
    SYNTAX      Counter32
    MAX-ACCESS  read-write
    STATUS      current
    DESCRIPTION 
        "Number of times Automatic Callback's time to wait for an idle line has expired for a given group. The default time to wait is 30 minutes."
    ::= { bwDXSACBGroupEntry 4 }

  bwDXSACBGroupMaxOrigSession OBJECT-TYPE
    SYNTAX      Counter32
    MAX-ACCESS  read-write
    STATUS      current
    DESCRIPTION 
        "Group level, number of times the max number of Automatic Callback sessions has been reached for the originator."
    ::= { bwDXSACBGroupEntry 6 }

  bwDXSACBGroupMaxTermSession OBJECT-TYPE
    SYNTAX      Counter32
    MAX-ACCESS  read-write
    STATUS      current
    DESCRIPTION 
        "Group level, number of times the max number of Automatic Callback sessions has been reached for the terminator."
    ::= { bwDXSACBGroupEntry 7 }

  bwDXSLegacyACBGroupOrigSession OBJECT-TYPE
    SYNTAX      Counter32
    MAX-ACCESS  read-write
    STATUS      current
    DESCRIPTION 
        "This is the number of times the Automatic Callback session has been initiated.  There is one instance of this counter for each group defined in the system."
    ::= { bwDXSACBGroupEntry 8 }

  bwDXSLegacyACBGroupOrigSuccessSession OBJECT-TYPE
    SYNTAX      Counter32
    MAX-ACCESS  read-write
    STATUS      current
    DESCRIPTION 
        "This is the number of times the Automatic Callback session has been initiated successfully.  There is one instance of this counter for each group defined in the system."
    ::= { bwDXSACBGroupEntry 9 }

  bwDXSLegacyACBGroupOrigFailedSession OBJECT-TYPE
    SYNTAX      Counter32
    MAX-ACCESS  read-write
    STATUS      current
    DESCRIPTION 
        "This is the number of times the Automatic Callback session has failed.  There is one instance of this counter for each group defined in the system."
    ::= { bwDXSACBGroupEntry 10 }

  bwDXSLegacyACBGroupTermSession OBJECT-TYPE
    SYNTAX      Counter32
    MAX-ACCESS  read-write
    STATUS      current
    DESCRIPTION 
        "This is the number of times an Automatic Callback session request has been received on this switch.  There is one instance of this counter for each group defined in the system."
    ::= { bwDXSACBGroupEntry 11 }

  bwDXSLegacyACBGroupTermSuccessSession OBJECT-TYPE
    SYNTAX      Counter32
    MAX-ACCESS  read-write
    STATUS      current
    DESCRIPTION 
        "This is the number of times an Automatic Callback session request has been received on this switch successfully.  There is one instance of this counter for each group defined in the system."
    ::= { bwDXSACBGroupEntry 12 }

  bwDXSLegacyACBGroupTermFailedSession OBJECT-TYPE
    SYNTAX      Counter32
    MAX-ACCESS  read-write
    STATUS      current
    DESCRIPTION 
        "This is the number of times an Automatic Callback session request has failed on this switch.  There is one instance of this counter for each group defined in the system."
    ::= { bwDXSACBGroupEntry 13 }

  bwDXSACBMaxOrigSession OBJECT-TYPE
    SYNTAX      Counter32
    MAX-ACCESS  read-write
    STATUS      current
    DESCRIPTION 
        "System wide, number of times the max number of Automatic Callback sessions has been reached for the originator."
    ::= { acb 6 }

  bwDXSACBMaxTermSession OBJECT-TYPE
    SYNTAX      Counter32
    MAX-ACCESS  read-write
    STATUS      current
    DESCRIPTION 
        "System wide, number of times the max number of Automatic Callback sessions has been reached for the terminator."
    ::= { acb 7 }

  bwDXSLegacyACBOrigSession OBJECT-TYPE
    SYNTAX      Counter32
    MAX-ACCESS  read-write
    STATUS      current
    DESCRIPTION 
        "This is the number of times the Automatic Callback session has been initiated."
    ::= { acb 8 }

  bwDXSLegacyACBOrigSuccessSession OBJECT-TYPE
    SYNTAX      Counter32
    MAX-ACCESS  read-write
    STATUS      current
    DESCRIPTION 
        "This is the number of times the Automatic Callback session has been initiated successfully."
    ::= { acb 9 }

  bwDXSLegacyACBOrigFailedSession OBJECT-TYPE
    SYNTAX      Counter32
    MAX-ACCESS  read-write
    STATUS      current
    DESCRIPTION 
        "This is the number of times the Automatic Callback session has failed."
    ::= { acb 10 }

  bwDXSLegacyACBTermSession OBJECT-TYPE
    SYNTAX      Counter32
    MAX-ACCESS  read-write
    STATUS      current
    DESCRIPTION 
        "This is the number of times an Automatic Callback session request has been received on this switch."
    ::= { acb 11 }

  bwDXSLegacyACBTermSuccessSession OBJECT-TYPE
    SYNTAX      Counter32
    MAX-ACCESS  read-write
    STATUS      current
    DESCRIPTION 
        "This is the number of times an Automatic Callback session request has been received on this switch successfully."
    ::= { acb 12 }

  bwDXSLegacyACBTermFailedSession OBJECT-TYPE
    SYNTAX      Counter32
    MAX-ACCESS  read-write
    STATUS      current
    DESCRIPTION 
        "This is the number of times an Automatic Callback session request has failed on this switch."
    ::= { acb 13 }

  bwDXSSequentialRingNumAttempts OBJECT-TYPE
    SYNTAX      Counter32
    MAX-ACCESS  read-write
    STATUS      current
    DESCRIPTION 
        "This counter is incremented whenever the sequential ring service forwards a call to the next in the list. The counter is not incremented for an attempt to alert the base location, unless it appears in the sequential ring list."
    ::= { sequentialRing 1 }

  bwDXSSequentialRingNumNoAnswer OBJECT-TYPE
    SYNTAX      Counter32
    MAX-ACCESS  read-write
    STATUS      current
    DESCRIPTION 
        "This counter is incremented whenever the sequential ring service reaches the end of the list, and no users are available"
    ::= { sequentialRing 2 }

  bwDXSSequentialRingSPTable OBJECT-TYPE
    SYNTAX      SEQUENCE OF BwSequentialRingSPEntry
    MAX-ACCESS  not-accessible
    STATUS      current
    DESCRIPTION 
        "This table tracks sequential ring measurements per service provider"
    ::= { sequentialRing 3 }

  bwDXSSequentialRingSPEntry OBJECT-TYPE
    SYNTAX      BwSequentialRingSPEntry
    MAX-ACCESS  not-accessible
    STATUS      current
    DESCRIPTION 
        "Each row contains the service counters for the sequentialRing service for each service provider in the system"
    INDEX       { bwDXSSequentialRingSPIndex }
    ::= { bwDXSSequentialRingSPTable 1 }

  BwSequentialRingSPEntry ::= SEQUENCE {
    bwDXSSequentialRingSPIndex         Unsigned32,
    bwDXSSequentialRingSPID            DisplayString,
    bwDXSSequentialRingSPNumAttempts   Counter32,
    bwDXSSequentialRingSPNumNoAnswer   Counter32,
    bwDXSSequentialRingSPActivations   Counter32,
    bwDXSSequentialRingSPAnswered      Counter32,
    bwDXSSequentialRingSPAbandoned     Counter32
  }

  bwDXSSequentialRingSPIndex OBJECT-TYPE
    SYNTAX      Unsigned32
    MAX-ACCESS  read-only
    STATUS      current
    DESCRIPTION 
        "This column represents the index of the service provider in the system"
    ::= { bwDXSSequentialRingSPEntry 1 }

  bwDXSSequentialRingSPID OBJECT-TYPE
    SYNTAX      DisplayString
    MAX-ACCESS  read-only
    STATUS      current
    DESCRIPTION 
        "This string represents a service provider ID"
    ::= { bwDXSSequentialRingSPEntry 2 }

  bwDXSSequentialRingSPNumAttempts OBJECT-TYPE
    SYNTAX      Counter32
    MAX-ACCESS  read-write
    STATUS      current
    DESCRIPTION 
        "This counter is incremented whenever the sequential ring service forwards a call to the next user in the list for a given service provider. The counter is not incremented for an attempt to alert the base location, unless it appears in the sequential ring list."
    ::= { bwDXSSequentialRingSPEntry 3 }

  bwDXSSequentialRingSPNumNoAnswer OBJECT-TYPE
    SYNTAX      Counter32
    MAX-ACCESS  read-write
    STATUS      current
    DESCRIPTION 
        "This counter is incremented whenever the sequential ring service reaches the end of the list, and no users are available for a given service provider"
    ::= { bwDXSSequentialRingSPEntry 4 }

  bwDXSSequentialRingSPActivations OBJECT-TYPE
    SYNTAX      Counter32
    MAX-ACCESS  read-write
    STATUS      current
    DESCRIPTION 
        "This counter is incremented every time the Sequential Ring service is activated by an incoming call (service is active and screening is successful) for a given Service Provider."
    ::= { bwDXSSequentialRingSPEntry 5 }

  bwDXSSequentialRingSPAnswered OBJECT-TYPE
    SYNTAX      Counter32
    MAX-ACCESS  read-write
    STATUS      current
    DESCRIPTION 
        "This counter is incremented every time a caller gets connected to a location as a result of Sequential Ring for a given Service Provider"
    ::= { bwDXSSequentialRingSPEntry 6 }

  bwDXSSequentialRingSPAbandoned OBJECT-TYPE
    SYNTAX      Counter32
    MAX-ACCESS  read-write
    STATUS      current
    DESCRIPTION 
        "This counter is incremented every time a caller hangs up before Sequential Ring completes for a given Service Provider"
    ::= { bwDXSSequentialRingSPEntry 7 }

  bwDXSSequentialRingGroupTable OBJECT-TYPE
    SYNTAX      SEQUENCE OF BwSequentialRingGroupEntry
    MAX-ACCESS  not-accessible
    STATUS      current
    DESCRIPTION 
        "This table tracks sequential ring measurements per groups"
    ::= { sequentialRing 4 }

  bwDXSSequentialRingGroupEntry OBJECT-TYPE
    SYNTAX      BwSequentialRingGroupEntry
    MAX-ACCESS  not-accessible
    STATUS      current
    DESCRIPTION 
        "Each row contains the service counters for the sequentialRing service for each group in the system"
    INDEX       { bwDXSSequentialRingGroupIndex }
    ::= { bwDXSSequentialRingGroupTable 1 }

  BwSequentialRingGroupEntry ::= SEQUENCE {
    bwDXSSequentialRingGroupIndex          Unsigned32,
    bwDXSSequentialRingGroupID             DisplayString,
    bwDXSSequentialRingGroupNumAttempts    Counter32,
    bwDXSSequentialRingGroupNumNoAnswer    Counter32,
    bwDXSSequentialRingGroupActivations    Counter32,
    bwDXSSequentialRingGroupAnswered       Counter32,
    bwDXSSequentialRingGroupAbandoned      Counter32
  }

  bwDXSSequentialRingGroupIndex OBJECT-TYPE
    SYNTAX      Unsigned32
    MAX-ACCESS  read-only
    STATUS      current
    DESCRIPTION 
        "This column represents the index of the group in the system"
    ::= { bwDXSSequentialRingGroupEntry 1 }

  bwDXSSequentialRingGroupID OBJECT-TYPE
    SYNTAX      DisplayString
    MAX-ACCESS  read-only
    STATUS      current
    DESCRIPTION 
        "This string represents a group ID"
    ::= { bwDXSSequentialRingGroupEntry 2 }

  bwDXSSequentialRingGroupNumAttempts OBJECT-TYPE
    SYNTAX      Counter32
    MAX-ACCESS  read-write
    STATUS      current
    DESCRIPTION 
        "This counter is incremented whenever the sequential ring service forwards a call to the next user in the list for a given group. The counter is not incremented for an attempt to alert the base location, unless it appears in the sequential ring list."
    ::= { bwDXSSequentialRingGroupEntry 3 }

  bwDXSSequentialRingGroupNumNoAnswer OBJECT-TYPE
    SYNTAX      Counter32
    MAX-ACCESS  read-write
    STATUS      current
    DESCRIPTION 
        "This counter is incremented whenever the sequential ring service reaches the end of the list, and no users are available for a given group"
    ::= { bwDXSSequentialRingGroupEntry 4 }

  bwDXSSequentialRingGroupActivations OBJECT-TYPE
    SYNTAX      Counter32
    MAX-ACCESS  read-write
    STATUS      current
    DESCRIPTION 
        "This counter is incremented every time the Sequential Ring service is activated by an incoming call (service is active and screening is successful) for a given Group"
    ::= { bwDXSSequentialRingGroupEntry 5 }

  bwDXSSequentialRingGroupAnswered OBJECT-TYPE
    SYNTAX      Counter32
    MAX-ACCESS  read-write
    STATUS      current
    DESCRIPTION 
        "This counter is incremented every time a caller gets connected to a location as a result of Sequential Ring for a given Group"
    ::= { bwDXSSequentialRingGroupEntry 6 }

  bwDXSSequentialRingGroupAbandoned OBJECT-TYPE
    SYNTAX      Counter32
    MAX-ACCESS  read-write
    STATUS      current
    DESCRIPTION 
        "This counter is incremented every time a caller hangs up before Sequential Ring completes for a given Group"
    ::= { bwDXSSequentialRingGroupEntry 7 }

  bwDXSSequentialRingActivations OBJECT-TYPE
    SYNTAX      Counter32
    MAX-ACCESS  read-write
    STATUS      current
    DESCRIPTION 
        "This counter is incremented every time the Sequential Ring service is activated by an incoming call (service is active and screening is successful)."
    ::= { sequentialRing 5 }

  bwDXSSequentialRingAnswered OBJECT-TYPE
    SYNTAX      Counter32
    MAX-ACCESS  read-write
    STATUS      current
    DESCRIPTION 
        "This counter is incremented every time a caller gets connected to a location as a result of Sequential Ring"
    ::= { sequentialRing 6 }

  bwDXSSequentialRingAbandoned OBJECT-TYPE
    SYNTAX      Counter32
    MAX-ACCESS  read-write
    STATUS      current
    DESCRIPTION 
        "This counter is incremented every time a caller hangs up before Sequential Ring completes"
    ::= { sequentialRing 7 }

  bwDXSRingTimeoutNumExpires OBJECT-TYPE
    SYNTAX      Counter32
    MAX-ACCESS  read-write
    STATUS      current
    DESCRIPTION 
        "Number of times the ring timeout timer expires for the entire system."
    ::= { ringTimeout 1 }

  bwDXSRingTimeoutSPTable OBJECT-TYPE
    SYNTAX      SEQUENCE OF BwRingTimeoutSPEntry
    MAX-ACCESS  not-accessible
    STATUS      current
    DESCRIPTION 
        "Counters for the Ring Timeout service measurements for service providers"
    ::= { ringTimeout 2 }

  bwDXSRingTimeoutSPEntry OBJECT-TYPE
    SYNTAX      BwRingTimeoutSPEntry
    MAX-ACCESS  not-accessible
    STATUS      current
    DESCRIPTION 
        "Each row contains the service counters for the Ring Timeout service for each service provider in the system"
    INDEX       { bwDXSRingTimeoutSPIndex }
    ::= { bwDXSRingTimeoutSPTable 1 }

  BwRingTimeoutSPEntry ::= SEQUENCE {
    bwDXSRingTimeoutSPIndex        Unsigned32,
    bwDXSRingTimeoutSPID           DisplayString,
    bwDXSRingTimeoutSPNumExpires   Counter32
  }

  bwDXSRingTimeoutSPIndex OBJECT-TYPE
    SYNTAX      Unsigned32
    MAX-ACCESS  read-only
    STATUS      current
    DESCRIPTION 
        "This column represents the index of the service provider in the system"
    ::= { bwDXSRingTimeoutSPEntry 1 }

  bwDXSRingTimeoutSPID OBJECT-TYPE
    SYNTAX      DisplayString
    MAX-ACCESS  read-only
    STATUS      current
    DESCRIPTION 
        "This string represents a service provider ID"
    ::= { bwDXSRingTimeoutSPEntry 2 }

  bwDXSRingTimeoutSPNumExpires OBJECT-TYPE
    SYNTAX      Counter32
    MAX-ACCESS  read-write
    STATUS      current
    DESCRIPTION 
        "Number of times the ring timeout timer expires for a given service provider"
    ::= { bwDXSRingTimeoutSPEntry 3 }

  bwDXSRingTimeoutGroupTable OBJECT-TYPE
    SYNTAX      SEQUENCE OF BwRingTimeoutGroupEntry
    MAX-ACCESS  not-accessible
    STATUS      current
    DESCRIPTION 
        "Counters for the Ring Timeout service measurements for groups"
    ::= { ringTimeout 3 }

  bwDXSRingTimeoutGroupEntry OBJECT-TYPE
    SYNTAX      BwRingTimeoutGroupEntry
    MAX-ACCESS  not-accessible
    STATUS      current
    DESCRIPTION 
        "Each row contains the service counters for the Ring Timeout service for each group in the system"
    INDEX       { bwDXSRingTimeoutGroupIndex }
    ::= { bwDXSRingTimeoutGroupTable 1 }

  BwRingTimeoutGroupEntry ::= SEQUENCE {
    bwDXSRingTimeoutGroupIndex         Unsigned32,
    bwDXSRingTimeoutGroupID            DisplayString,
    bwDXSRingTimeoutGroupNumExpires    Counter32
  }

  bwDXSRingTimeoutGroupIndex OBJECT-TYPE
    SYNTAX      Unsigned32
    MAX-ACCESS  read-only
    STATUS      current
    DESCRIPTION 
        "This column represents the index of the group in the system"
    ::= { bwDXSRingTimeoutGroupEntry 1 }

  bwDXSRingTimeoutGroupID OBJECT-TYPE
    SYNTAX      DisplayString
    MAX-ACCESS  read-only
    STATUS      current
    DESCRIPTION 
        "This string represents a group ID"
    ::= { bwDXSRingTimeoutGroupEntry 2 }

  bwDXSRingTimeoutGroupNumExpires OBJECT-TYPE
    SYNTAX      Counter32
    MAX-ACCESS  read-write
    STATUS      current
    DESCRIPTION 
        "Number of times the ring timeout timer expires for a given group"
    ::= { bwDXSRingTimeoutGroupEntry 3 }

  bwDXSMaliciousCallTraceApplied OBJECT-TYPE
    SYNTAX      Counter32
    MAX-ACCESS  read-write
    STATUS      current
    DESCRIPTION 
        "This counter is incremented each time a the Malicious Call Trace serevice is activated."
    ::= { mct 1 }

  bwDXSMaliciousCallTraceAnnouncement OBJECT-TYPE
    SYNTAX      Counter32
    MAX-ACCESS  read-write
    STATUS      current
    DESCRIPTION
       "Number of Malicious Call Trace Announcements attempted."
    ::= { mct 4 }

  bwDXSMaliciousCallTraceSPTable OBJECT-TYPE
    SYNTAX      SEQUENCE OF BwMaliciousCallTraceSPEntry
    MAX-ACCESS  not-accessible
    STATUS      current
    DESCRIPTION 
        "Counters for the Malicious Call Trace service measurements for service providers"
    ::= { mct 2 }

  bwDXSMaliciousCallTraceSPEntry OBJECT-TYPE
    SYNTAX      BwMaliciousCallTraceSPEntry
    MAX-ACCESS  not-accessible
    STATUS      current
    DESCRIPTION 
        "Each row contains the service counters for the Malicious Call Trace service for each service provider in the system"
    INDEX       { bwDXSMaliciousCallTraceSPIndex }
    ::= { bwDXSMaliciousCallTraceSPTable 1 }

  BwMaliciousCallTraceSPEntry ::= SEQUENCE {
    bwDXSMaliciousCallTraceSPIndex        Unsigned32,
    bwDXSMaliciousCallTraceSPID           DisplayString,
    bwDXSMaliciousCallTraceSPApplied      Counter32,
    bwDXSMaliciousCallTraceSPAnnouncement Counter32
  }

  bwDXSMaliciousCallTraceSPIndex OBJECT-TYPE
    SYNTAX      Unsigned32
    MAX-ACCESS  read-only
    STATUS      current
    DESCRIPTION 
        "This column represents the index of the service provider in the system"
    ::= { bwDXSMaliciousCallTraceSPEntry 1 }

  bwDXSMaliciousCallTraceSPID OBJECT-TYPE
    SYNTAX      DisplayString
    MAX-ACCESS  read-only
    STATUS      current
    DESCRIPTION 
        "This string represents a service provider ID"
    ::= { bwDXSMaliciousCallTraceSPEntry 2 }

  bwDXSMaliciousCallTraceSPApplied OBJECT-TYPE
    SYNTAX      Counter32
    MAX-ACCESS  read-write
    STATUS      current
    DESCRIPTION 
        "This counter is incremented each time a the Malicious Call Trace serevice is activated for the given service provider."
    ::= { bwDXSMaliciousCallTraceSPEntry 3 }

  bwDXSMaliciousCallTraceSPAnnouncement OBJECT-TYPE
    SYNTAX      Counter32
    MAX-ACCESS  read-write
    STATUS      current
    DESCRIPTION
        "Number of Malicious Call Trace Announcements attempted for users in a given service provider."
    ::= { bwDXSMaliciousCallTraceSPEntry 4 }

  bwDXSMaliciousCallTraceGroupTable OBJECT-TYPE
    SYNTAX      SEQUENCE OF BwMaliciousCallTraceGroupEntry
    MAX-ACCESS  not-accessible
    STATUS      current
    DESCRIPTION 
        "Counters for the Malicious Call Trace service measurements for groups"
    ::= { mct 3 }

  bwDXSMaliciousCallTraceGroupEntry OBJECT-TYPE
    SYNTAX      BwMaliciousCallTraceGroupEntry
    MAX-ACCESS  not-accessible
    STATUS      current
    DESCRIPTION 
        "Each row contains the service counters for the Malicious Call Trace service for each group in the system"
    INDEX       { bwDXSMaliciousCallTraceGroupIndex }
    ::= { bwDXSMaliciousCallTraceGroupTable 1 }

  BwMaliciousCallTraceGroupEntry ::= SEQUENCE {
    bwDXSMaliciousCallTraceGroupIndex        Unsigned32,
    bwDXSMaliciousCallTraceGroupID           DisplayString,
    bwDXSMaliciousCallTraceGroupApplied      Counter32,
    bwDXSMaliciousCallTraceGroupAnnouncement Counter32
  }

  bwDXSMaliciousCallTraceGroupIndex OBJECT-TYPE
    SYNTAX      Unsigned32
    MAX-ACCESS  read-only
    STATUS      current
    DESCRIPTION 
        "This column represents the index of the service provider in the system"
    ::= { bwDXSMaliciousCallTraceGroupEntry 1 }

  bwDXSMaliciousCallTraceGroupID OBJECT-TYPE
    SYNTAX      DisplayString
    MAX-ACCESS  read-only
    STATUS      current
    DESCRIPTION 
        "This string represents a service provider ID"
    ::= { bwDXSMaliciousCallTraceGroupEntry 2 }

  bwDXSMaliciousCallTraceGroupApplied OBJECT-TYPE
    SYNTAX      Counter32
    MAX-ACCESS  read-write
    STATUS      current
    DESCRIPTION 
        "This counter is incremented each time a the Malicious Call Trace serevice is activated for the given group."
    ::= { bwDXSMaliciousCallTraceGroupEntry 3 }

  bwDXSMaliciousCallTraceGroupAnnouncement  OBJECT-TYPE
    SYNTAX      Counter32
    MAX-ACCESS  read-write
    STATUS      current
    DESCRIPTION
        "Number of Malicious Call Trace Announcements attempted for user in a given group."
    ::=  {  bwDXSMaliciousCallTraceGroupEntry  4  }

  bwDXSSubscriptionUserPIC OBJECT-TYPE
    SYNTAX      Counter32
    MAX-ACCESS  read-write
    STATUS      current
    DESCRIPTION 
        "This counter shall be incremented each time the user PICs are used, but not explicitly dialed."
    ::= { preferredCarrier 1 }

  bwDXSSubscriptionGroupPIC OBJECT-TYPE
    SYNTAX      Counter32
    MAX-ACCESS  read-write
    STATUS      current
    DESCRIPTION 
        "This counter shall be incremented each time the group PICs are used, but not explicitly dialed."
    ::= { preferredCarrier 2 }

  bwDXSSubscriptionServiceProviderPIC OBJECT-TYPE
    SYNTAX      Counter32
    MAX-ACCESS  read-write
    STATUS      current
    DESCRIPTION 
        "This counter shall be incremented each time the service provider PICs are used, but not explicitly dialed."
    ::= { preferredCarrier 3 }

  bwDXSSubscriptionDialedUserPIC OBJECT-TYPE
    SYNTAX      Counter32
    MAX-ACCESS  read-write
    STATUS      current
    DESCRIPTION 
        "This counter shall be incremented each time the user PICs are used and explicitly dialed."
    ::= { preferredCarrier 4 }

  bwDXSSubscriptionDialedGroupPIC OBJECT-TYPE
    SYNTAX      Counter32
    MAX-ACCESS  read-write
    STATUS      current
    DESCRIPTION 
        "This counter shall be incremented each time the group PICs are used and explicitly dialed."
    ::= { preferredCarrier 5 }

  bwDXSSubscriptionDialedServiceProviderPIC OBJECT-TYPE
    SYNTAX      Counter32
    MAX-ACCESS  read-write
    STATUS      current
    DESCRIPTION 
        "This counter shall be incremented each time the service provider PICs are used and explicitly dialed."
    ::= { preferredCarrier 6 }

  bwDXSNonSubscriptionDialedUserPIC OBJECT-TYPE
    SYNTAX      Counter32
    MAX-ACCESS  read-write
    STATUS      current
    DESCRIPTION 
        "This counter shall be incremented each time a casual dialed carrier is used instead of the user subscribed PIC."
    ::= { preferredCarrier 7 }

  bwDXSNonSubscriptionDialedGroupPIC OBJECT-TYPE
    SYNTAX      Counter32
    MAX-ACCESS  read-write
    STATUS      current
    DESCRIPTION 
        "This counter shall be incremented each time a casual dialed carrier is used instead of the group subscribed PIC."
    ::= { preferredCarrier 8 }

  bwDXSNonSubscriptionDialedServiceProviderPIC OBJECT-TYPE
    SYNTAX      Counter32
    MAX-ACCESS  read-write
    STATUS      current
    DESCRIPTION 
        "This counter shall be incremented each time a casual dialed carrier is used instead of the service provider subscribed PIC."
    ::= { preferredCarrier 9 }

  bwDXSNoIndicationUserPIC OBJECT-TYPE
    SYNTAX      Counter32
    MAX-ACCESS  read-write
    STATUS      current
    DESCRIPTION 
        "This counter shall be incremented each time the user subscribed PIC is used, but with no indication on how this PIC was specified."
    ::= { preferredCarrier 10 }

  bwDXSNoIndicationGroupPIC OBJECT-TYPE
    SYNTAX      Counter32
    MAX-ACCESS  read-write
    STATUS      current
    DESCRIPTION 
        "This counter shall be incremented each time the group subscribed PIC is used, but with no indication on how this PIC was specified."
    ::= { preferredCarrier 11 }

  bwDXSNoIndicationServiceProviderPIC OBJECT-TYPE
    SYNTAX      Counter32
    MAX-ACCESS  read-write
    STATUS      current
    DESCRIPTION 
        "This counter shall be incremented each time the service provider subscribed PIC is used, but with no indication on how this PIC was specified."
    ::= { preferredCarrier 12 }

  bwDXSPreferredCarrierSPTable OBJECT-TYPE
    SYNTAX      SEQUENCE OF BwPreferredCarrierSPEntry
    MAX-ACCESS  not-accessible
    STATUS      current
    DESCRIPTION 
        "Counters for the Preferred Carrier service measurements for service providers"
    ::= { preferredCarrier 13 }

  bwDXSPreferredCarrierSPEntry OBJECT-TYPE
    SYNTAX      BwPreferredCarrierSPEntry
    MAX-ACCESS  not-accessible
    STATUS      current
    DESCRIPTION 
        "Each row contains the service counters for the Preferred Carrier service for each service provider in the system"
    INDEX       { bwDXSPreferredCarrierSPIndex }
    ::= { bwDXSPreferredCarrierSPTable 1 }

  BwPreferredCarrierSPEntry ::= SEQUENCE {
    bwDXSPreferredCarrierSPIndex                       Unsigned32,
    bwDXSPreferredCarrierSPID                          DisplayString,
    bwDXSSPSubscriptionUserPIC                         Counter32,
    bwDXSSPSubscriptionGroupPIC                        Counter32,
    bwDXSSPSubscriptionServiceProviderPIC              Counter32,
    bwDXSSPSubscriptionDialedUserPIC                   Counter32,
    bwDXSSPSubscriptionDialedGroupPIC                  Counter32,
    bwDXSSPSubscriptionDialedServiceProviderPIC        Counter32,
    bwDXSSPNonSubscriptionDialedUserPIC                Counter32,
    bwDXSSPNonSubscriptionDialedGroupPIC               Counter32,
    bwDXSSPNonSubscriptionDialedServiceProviderPIC     Counter32,
    bwDXSSPNoIndicationUserPIC                         Counter32,
    bwDXSSPNoIndicationGroupPIC                        Counter32,
    bwDXSSPNoIndicationServiceProviderPIC              Counter32
  }

  bwDXSPreferredCarrierSPIndex OBJECT-TYPE
    SYNTAX      Unsigned32
    MAX-ACCESS  read-only
    STATUS      current
    DESCRIPTION 
        "This column represents the index of the service provider in the system"
    ::= { bwDXSPreferredCarrierSPEntry 1 }

  bwDXSPreferredCarrierSPID OBJECT-TYPE
    SYNTAX      DisplayString
    MAX-ACCESS  read-only
    STATUS      current
    DESCRIPTION 
        "This string represents a service provider ID"
    ::= { bwDXSPreferredCarrierSPEntry 2 }

  bwDXSSPSubscriptionUserPIC OBJECT-TYPE
    SYNTAX      Counter32
    MAX-ACCESS  read-write
    STATUS      current
    DESCRIPTION 
        "This counter shall be incremented each time the user PICs are used, but not explicitly dialed, on a per-service provider basis.."
    ::= { bwDXSPreferredCarrierSPEntry 3 }

  bwDXSSPSubscriptionGroupPIC OBJECT-TYPE
    SYNTAX      Counter32
    MAX-ACCESS  read-write
    STATUS      current
    DESCRIPTION 
        "This counter shall be incremented each time the group PICs are used, but not explicitly dialed, on a per-service provider basis.."
    ::= { bwDXSPreferredCarrierSPEntry 4 }

  bwDXSSPSubscriptionServiceProviderPIC OBJECT-TYPE
    SYNTAX      Counter32
    MAX-ACCESS  read-write
    STATUS      current
    DESCRIPTION 
        "This counter shall be incremented each time the service provider PICs are used, but not explicitly dialed, on a per-service provider basis.."
    ::= { bwDXSPreferredCarrierSPEntry 5 }

  bwDXSSPSubscriptionDialedUserPIC OBJECT-TYPE
    SYNTAX      Counter32
    MAX-ACCESS  read-write
    STATUS      current
    DESCRIPTION 
        "This counter shall be incremented each time the user PICs are used and explicitly dialed, on a per-service provider basis.."
    ::= { bwDXSPreferredCarrierSPEntry 6 }

  bwDXSSPSubscriptionDialedGroupPIC OBJECT-TYPE
    SYNTAX      Counter32
    MAX-ACCESS  read-write
    STATUS      current
    DESCRIPTION 
        "This counter shall be incremented each time the group PICs are used and explicitly dialed, on a per-service provider basis.."
    ::= { bwDXSPreferredCarrierSPEntry 7 }

  bwDXSSPSubscriptionDialedServiceProviderPIC OBJECT-TYPE
    SYNTAX      Counter32
    MAX-ACCESS  read-write
    STATUS      current
    DESCRIPTION 
        "This counter shall be incremented each time the service provider PICs are used and explicitly dialed, on a per-service provider basis.."
    ::= { bwDXSPreferredCarrierSPEntry 8 }

  bwDXSSPNonSubscriptionDialedUserPIC OBJECT-TYPE
    SYNTAX      Counter32
    MAX-ACCESS  read-write
    STATUS      current
    DESCRIPTION 
        "This counter shall be incremented each time a casual dialed carrier is used instead of the user subscribed PIC, on a per-service provider basis.."
    ::= { bwDXSPreferredCarrierSPEntry 9 }

  bwDXSSPNonSubscriptionDialedGroupPIC OBJECT-TYPE
    SYNTAX      Counter32
    MAX-ACCESS  read-write
    STATUS      current
    DESCRIPTION 
        "This counter shall be incremented each time a casual dialed carrier is used instead of the group subscribed PIC, on a per-service provider basis.."
    ::= { bwDXSPreferredCarrierSPEntry 10 }

  bwDXSSPNonSubscriptionDialedServiceProviderPIC OBJECT-TYPE
    SYNTAX      Counter32
    MAX-ACCESS  read-write
    STATUS      current
    DESCRIPTION 
        "This counter shall be incremented each time a casual dialed carrier is used instead of the service provider subscribed PIC, on a per-service provider basis.."
    ::= { bwDXSPreferredCarrierSPEntry 11 }

  bwDXSSPNoIndicationUserPIC OBJECT-TYPE
    SYNTAX      Counter32
    MAX-ACCESS  read-write
    STATUS      current
    DESCRIPTION 
        "This counter shall be incremented each time the user subscribed PIC is used, but with no indication on how this PIC was specified, on a per-service provider basis.."
    ::= { bwDXSPreferredCarrierSPEntry 12 }

  bwDXSSPNoIndicationGroupPIC OBJECT-TYPE
    SYNTAX      Counter32
    MAX-ACCESS  read-write
    STATUS      current
    DESCRIPTION 
        "This counter shall be incremented each time the group subscribed PIC is used, but with no indication on how this PIC was specified, on a per-service provider basis.."
    ::= { bwDXSPreferredCarrierSPEntry 13 }

  bwDXSSPNoIndicationServiceProviderPIC OBJECT-TYPE
    SYNTAX      Counter32
    MAX-ACCESS  read-write
    STATUS      current
    DESCRIPTION 
        "This counter shall be incremented each time the service provider subscribed PIC is used, but with no indication on how this PIC was specified, on a per-service provider basis.."
    ::= { bwDXSPreferredCarrierSPEntry 14 }

  bwDXSPreferredCarrierGroupTable OBJECT-TYPE
    SYNTAX      SEQUENCE OF BwPreferredCarrierGroupEntry
    MAX-ACCESS  not-accessible
    STATUS      current
    DESCRIPTION 
        "Counters for the Preferred Carrier service measurements for groups"
    ::= { preferredCarrier 14 }

  bwDXSPreferredCarrierGroupEntry OBJECT-TYPE
    SYNTAX      BwPreferredCarrierGroupEntry
    MAX-ACCESS  not-accessible
    STATUS      current
    DESCRIPTION 
        "Each row contains the service counters for the Preferred Carrier service for each group in the system"
    INDEX       { bwDXSPreferredCarrierGroupIndex }
    ::= { bwDXSPreferredCarrierGroupTable 1 }

  BwPreferredCarrierGroupEntry ::= SEQUENCE {
    bwDXSPreferredCarrierGroupIndex                    Unsigned32,
    bwDXSPreferredCarrierGroupID                       DisplayString,
    bwDXSGroupSubscriptionUserPIC                      Counter32,
    bwDXSGroupSubscriptionGroupPIC                     Counter32,
    bwDXSGroupSubscriptionServiceProviderPIC           Counter32,
    bwDXSGroupSubscriptionDialedUserPIC                Counter32,
    bwDXSGroupSubscriptionDialedGroupPIC               Counter32,
    bwDXSGroupSubscriptionDialedServiceProviderPIC     Counter32,
    bwDXSGroupNonSubscriptionDialedUserPIC             Counter32,
    bwDXSGroupNonSubscriptionDialedGroupPIC            Counter32,
    bwDXSGroupNonSubscriptionDialedServiceProviderPIC  Counter32,
    bwDXSGroupNoIndicationUserPIC                      Counter32,
    bwDXSGroupNoIndicationGroupPIC                     Counter32,
    bwDXSGroupNoIndicationServiceProviderPIC           Counter32
  }

  bwDXSPreferredCarrierGroupIndex OBJECT-TYPE
    SYNTAX      Unsigned32
    MAX-ACCESS  read-only
    STATUS      current
    DESCRIPTION 
        "This column represents the index of the group in the system"
    ::= { bwDXSPreferredCarrierGroupEntry 1 }

  bwDXSPreferredCarrierGroupID OBJECT-TYPE
    SYNTAX      DisplayString
    MAX-ACCESS  read-only
    STATUS      current
    DESCRIPTION 
        "This string represents a group ID"
    ::= { bwDXSPreferredCarrierGroupEntry 2 }

  bwDXSGroupSubscriptionUserPIC OBJECT-TYPE
    SYNTAX      Counter32
    MAX-ACCESS  read-write
    STATUS      current
    DESCRIPTION 
        "This counter shall be incremented each time the user PICs are used, but not explicitly dialed, on a per-group basis.."
    ::= { bwDXSPreferredCarrierGroupEntry 3 }

  bwDXSGroupSubscriptionGroupPIC OBJECT-TYPE
    SYNTAX      Counter32
    MAX-ACCESS  read-write
    STATUS      current
    DESCRIPTION 
        "This counter shall be incremented each time the group PICs are used, but not explicitly dialed, on a per-group basis.."
    ::= { bwDXSPreferredCarrierGroupEntry 4 }

  bwDXSGroupSubscriptionServiceProviderPIC OBJECT-TYPE
    SYNTAX      Counter32
    MAX-ACCESS  read-write
    STATUS      current
    DESCRIPTION 
        "This counter shall be incremented each time the service provider PICs are used, but not explicitly dialed, on a per-group basis.."
    ::= { bwDXSPreferredCarrierGroupEntry 5 }

  bwDXSGroupSubscriptionDialedUserPIC OBJECT-TYPE
    SYNTAX      Counter32
    MAX-ACCESS  read-write
    STATUS      current
    DESCRIPTION 
        "This counter shall be incremented each time the user PICs are used and explicitly dialed, on a per-group basis.."
    ::= { bwDXSPreferredCarrierGroupEntry 6 }

  bwDXSGroupSubscriptionDialedGroupPIC OBJECT-TYPE
    SYNTAX      Counter32
    MAX-ACCESS  read-write
    STATUS      current
    DESCRIPTION 
        "This counter shall be incremented each time the group PICs are used and explicitly dialed, on a per-group basis.."
    ::= { bwDXSPreferredCarrierGroupEntry 7 }

  bwDXSGroupSubscriptionDialedServiceProviderPIC OBJECT-TYPE
    SYNTAX      Counter32
    MAX-ACCESS  read-write
    STATUS      current
    DESCRIPTION 
        "This counter shall be incremented each time the service provider PICs are used and explicitly dialed, on a per-group basis.."
    ::= { bwDXSPreferredCarrierGroupEntry 8 }

  bwDXSGroupNonSubscriptionDialedUserPIC OBJECT-TYPE
    SYNTAX      Counter32
    MAX-ACCESS  read-write
    STATUS      current
    DESCRIPTION 
        "This counter shall be incremented each time a casual dialed carrier is used instead of the user subscribed PIC, on a per-group basis.."
    ::= { bwDXSPreferredCarrierGroupEntry 9 }

  bwDXSGroupNonSubscriptionDialedGroupPIC OBJECT-TYPE
    SYNTAX      Counter32
    MAX-ACCESS  read-write
    STATUS      current
    DESCRIPTION 
        "This counter shall be incremented each time a casual dialed carrier is used instead of the group subscribed PIC, on a per-group basis.."
    ::= { bwDXSPreferredCarrierGroupEntry 10 }

  bwDXSGroupNonSubscriptionDialedServiceProviderPIC OBJECT-TYPE
    SYNTAX      Counter32
    MAX-ACCESS  read-write
    STATUS      current
    DESCRIPTION 
        "This counter shall be incremented each time a casual dialed carrier is used instead of the service provider subscribed PIC, on a per-group basis.."
    ::= { bwDXSPreferredCarrierGroupEntry 11 }

  bwDXSGroupNoIndicationUserPIC OBJECT-TYPE
    SYNTAX      Counter32
    MAX-ACCESS  read-write
    STATUS      current
    DESCRIPTION 
        "This counter shall be incremented each time the user subscribed PIC is used, but with no indication on how this PIC was specified, on a per-group basis.."
    ::= { bwDXSPreferredCarrierGroupEntry 12 }

  bwDXSGroupNoIndicationGroupPIC OBJECT-TYPE
    SYNTAX      Counter32
    MAX-ACCESS  read-write
    STATUS      current
    DESCRIPTION 
        "This counter shall be incremented each time the group subscribed PIC is used, but with no indication on how this PIC was specified, on a per-group basis.."
    ::= { bwDXSPreferredCarrierGroupEntry 13 }

  bwDXSGroupNoIndicationServiceProviderPIC OBJECT-TYPE
    SYNTAX      Counter32
    MAX-ACCESS  read-write
    STATUS      current
    DESCRIPTION 
        "This counter shall be incremented each time the service provider subscribed PIC is used, but with no indication on how this PIC was specified, on a per-group basis.."
    ::= { bwDXSPreferredCarrierGroupEntry 14 }

  bwDXSFamilySimRingNumAttempts OBJECT-TYPE
    SYNTAX      Counter32
    MAX-ACCESS  read-write
    STATUS      current
    DESCRIPTION 
        "System wide counter for number of times family sim ring has been executed."
    ::= { familySimRing 1 }

  bwDXSFamilySimRingNumBusy OBJECT-TYPE
    SYNTAX      Counter32
    MAX-ACCESS  read-write
    STATUS      current
    DESCRIPTION 
        "System wide counter for number of times all sim ring numbers have failed."
    ::= { familySimRing 2 }

  bwDXSFamilySimRingSPTable OBJECT-TYPE
    SYNTAX      SEQUENCE OF BwFamilySimRingSPEntry
    MAX-ACCESS  not-accessible
    STATUS      current
    DESCRIPTION 
        "Counters for the Family Simring service measurements for service providers"
    ::= { familySimRing 3 }

  bwDXSFamilySimRingSPEntry OBJECT-TYPE
    SYNTAX      BwFamilySimRingSPEntry
    MAX-ACCESS  not-accessible
    STATUS      current
    DESCRIPTION 
        "Each row contains the service counters for the Family Simring service for each service provider in the system"
    INDEX       { bwDXSFamilySimRingSPIndex }
    ::= { bwDXSFamilySimRingSPTable 1 }

  BwFamilySimRingSPEntry ::= SEQUENCE {
    bwDXSFamilySimRingSPIndex          Unsigned32,
    bwDXSFamilySimRingSPID             DisplayString,
    bwDXSFamilySimRingSPNumAttempts    Counter32,
    bwDXSFamilySimRingSPNumBusy        Counter32
  }

  bwDXSFamilySimRingSPIndex OBJECT-TYPE
    SYNTAX      Unsigned32
    MAX-ACCESS  read-only
    STATUS      current
    DESCRIPTION 
        "This column represents the index of the service provider in the system"
    ::= { bwDXSFamilySimRingSPEntry 1 }

  bwDXSFamilySimRingSPID OBJECT-TYPE
    SYNTAX      DisplayString
    MAX-ACCESS  read-only
    STATUS      current
    DESCRIPTION 
        "This string represents a service provider ID"
    ::= { bwDXSFamilySimRingSPEntry 2 }

  bwDXSFamilySimRingSPNumAttempts OBJECT-TYPE
    SYNTAX      Counter32
    MAX-ACCESS  read-write
    STATUS      current
    DESCRIPTION 
        "System wide counter for number of times family sim ring has been executed for a given service provider."
    ::= { bwDXSFamilySimRingSPEntry 3 }

  bwDXSFamilySimRingSPNumBusy OBJECT-TYPE
    SYNTAX      Counter32
    MAX-ACCESS  read-write
    STATUS      current
    DESCRIPTION 
        "System wide counter for number of times all sim ring numbers have failed for a given service provider."
    ::= { bwDXSFamilySimRingSPEntry 4 }

  bwDXSFamilySimRingGroupTable OBJECT-TYPE
    SYNTAX      SEQUENCE OF BwFamilySimRingGroupEntry
    MAX-ACCESS  not-accessible
    STATUS      current
    DESCRIPTION 
        "Counters for the Family Simring service measurements for groups"
    ::= { familySimRing 4 }

  bwDXSFamilySimRingGroupEntry OBJECT-TYPE
    SYNTAX      BwFamilySimRingGroupEntry
    MAX-ACCESS  not-accessible
    STATUS      current
    DESCRIPTION 
        "Each row contains the service counters for the Family Simring service for each group in the system"
    INDEX       { bwDXSFamilySimRingGroupIndex }
    ::= { bwDXSFamilySimRingGroupTable 1 }

  BwFamilySimRingGroupEntry ::= SEQUENCE {
    bwDXSFamilySimRingGroupIndex           Unsigned32,
    bwDXSFamilySimRingGroupID              DisplayString,
    bwDXSFamilySimRingGroupNumAttempts     Counter32,
    bwDXSFamilySimRingGroupNumBusy         Counter32
  }

  bwDXSFamilySimRingGroupIndex OBJECT-TYPE
    SYNTAX      Unsigned32
    MAX-ACCESS  read-only
    STATUS      current
    DESCRIPTION 
        "This column represents the index of the group in the system"
    ::= { bwDXSFamilySimRingGroupEntry 1 }

  bwDXSFamilySimRingGroupID OBJECT-TYPE
    SYNTAX      DisplayString
    MAX-ACCESS  read-only
    STATUS      current
    DESCRIPTION 
        "This string represents a group ID"
    ::= { bwDXSFamilySimRingGroupEntry 2 }

  bwDXSFamilySimRingGroupNumAttempts OBJECT-TYPE
    SYNTAX      Counter32
    MAX-ACCESS  read-write
    STATUS      current
    DESCRIPTION 
        "System wide counter for number of times family sim ring has been executed for a given group."
    ::= { bwDXSFamilySimRingGroupEntry 3 }

  bwDXSFamilySimRingGroupNumBusy OBJECT-TYPE
    SYNTAX      Counter32
    MAX-ACCESS  read-write
    STATUS      current
    DESCRIPTION 
        "System wide counter for number of times all sim ring numbers have failed for a given group."
    ::= { bwDXSFamilySimRingGroupEntry 4 }

  bwDXSDiversionInhibited OBJECT-TYPE
    SYNTAX      Counter32
    MAX-ACCESS  read-write
    STATUS      current
    DESCRIPTION 
        "This counter is incremented each time Diversion Inhibitor FAC is invoked for a call, directly or via service configuration."
    ::= { diversionInhibitor 1 }

  bwDXSDiversionInhibitorSPTable OBJECT-TYPE
    SYNTAX      SEQUENCE OF BwDiversionInhibitorSPEntry
    MAX-ACCESS  not-accessible
    STATUS      current
    DESCRIPTION 
        "Counters for the Diversion Inhibitor service measurements for service providers"
    ::= { diversionInhibitor 2 }

  bwDXSDiversionInhibitorSPEntry OBJECT-TYPE
    SYNTAX      BwDiversionInhibitorSPEntry
    MAX-ACCESS  not-accessible
    STATUS      current
    DESCRIPTION 
        "Each row contains the service counters for the Diversion Inhibitor service for each service provider in the system"
    INDEX       { bwDXSDiversionInhibitorSPIndex }
    ::= { bwDXSDiversionInhibitorSPTable 1 }

  BwDiversionInhibitorSPEntry ::= SEQUENCE {
    bwDXSDiversionInhibitorSPIndex     Unsigned32,
    bwDXSDiversionInhibitorSPID        DisplayString,
    bwDXSSPDiversionInhibited          Counter32
  }

  bwDXSDiversionInhibitorSPIndex OBJECT-TYPE
    SYNTAX      Unsigned32
    MAX-ACCESS  read-only
    STATUS      current
    DESCRIPTION 
        "This column represents the index of the service provider in the system"
    ::= { bwDXSDiversionInhibitorSPEntry 1 }

  bwDXSDiversionInhibitorSPID OBJECT-TYPE
    SYNTAX      DisplayString
    MAX-ACCESS  read-only
    STATUS      current
    DESCRIPTION 
        "This string represents a service provider ID"
    ::= { bwDXSDiversionInhibitorSPEntry 2 }

  bwDXSSPDiversionInhibited OBJECT-TYPE
    SYNTAX      Counter32
    MAX-ACCESS  read-write
    STATUS      current
    DESCRIPTION 
        "This counter is incremented each time Diversion Inhibitor FAC is invoked for a call, directly or via service configuration for a service provider."
    ::= { bwDXSDiversionInhibitorSPEntry 3 }

  bwDXSDiversionInhibitorGroupTable OBJECT-TYPE
    SYNTAX      SEQUENCE OF BwDiversionInhibitorGroupEntry
    MAX-ACCESS  not-accessible
    STATUS      current
    DESCRIPTION 
        "Counters for the Diversion Inhibitor service measurements for groups"
    ::= { diversionInhibitor 3 }

  bwDXSDiversionInhibitorGroupEntry OBJECT-TYPE
    SYNTAX      BwDiversionInhibitorGroupEntry
    MAX-ACCESS  not-accessible
    STATUS      current
    DESCRIPTION 
        "Each row contains the service counters for the Diversion Inhibitor service for each group in the system"
    INDEX       { bwDXSDiversionInhibitorGroupIndex }
    ::= { bwDXSDiversionInhibitorGroupTable 1 }

  BwDiversionInhibitorGroupEntry ::= SEQUENCE {
    bwDXSDiversionInhibitorGroupIndex  Unsigned32,
    bwDXSDiversionInhibitorGroupID     DisplayString,
    bwDXSGroupDiversionInhibited       Counter32
  }

  bwDXSDiversionInhibitorGroupIndex OBJECT-TYPE
    SYNTAX      Unsigned32
    MAX-ACCESS  read-only
    STATUS      current
    DESCRIPTION 
        "This column represents the index of the group in the system"
    ::= { bwDXSDiversionInhibitorGroupEntry 1 }

  bwDXSDiversionInhibitorGroupID OBJECT-TYPE
    SYNTAX      DisplayString
    MAX-ACCESS  read-only
    STATUS      current
    DESCRIPTION 
        "This string represents a group ID"
    ::= { bwDXSDiversionInhibitorGroupEntry 2 }

  bwDXSGroupDiversionInhibited OBJECT-TYPE
    SYNTAX      Counter32
    MAX-ACCESS  read-write
    STATUS      current
    DESCRIPTION 
        "This counter is incremented each time Diversion Inhibitor FAC is invoked for a call, directly or via service configuration for a group."
    ::= { bwDXSDiversionInhibitorGroupEntry 3 }

  bwDXSCustomRingbackUserAudioAttempts OBJECT-TYPE
    SYNTAX      Counter32
    MAX-ACCESS  read-write
    STATUS      current
    DESCRIPTION 
        "This counter is incremented each time a command is sent to the Media Server in an attempt to play a user custom audio ringback."
    ::= { customRingback 1 }

  bwDXSCustomRingbackUserVideoAttempts OBJECT-TYPE
    SYNTAX      Counter32
    MAX-ACCESS  read-write
    STATUS      current
    DESCRIPTION 
        "This counter is incremented each time a command is sent to the Media Server in an attempt to play a user custom video ringback."
    ::= { customRingback 2 }

  bwDXSCustomRingbackUserAudioFailures OBJECT-TYPE
    SYNTAX      Counter32
    MAX-ACCESS  read-write
    STATUS      current
    DESCRIPTION 
        "This counter is incremented each time where an attempt is made to play a user custom audio ringback, and that the Media Server reports any failure to play it."
    ::= { customRingback 3 }

  bwDXSCustomRingbackUserVideoFailures OBJECT-TYPE
    SYNTAX      Counter32
    MAX-ACCESS  read-write
    STATUS      current
    DESCRIPTION 
        "This counter is incremented each time where an attempt is made to play a user custom video ringback, and that the Media Server reports any failure to play it."
    ::= { customRingback 4 }

  bwDXSCustomRingbackGroupAudioAttempts OBJECT-TYPE
    SYNTAX      Counter32
    MAX-ACCESS  read-write
    STATUS      current
    DESCRIPTION 
        "This counter is incremented each time a command is sent to the Media Server in an attempt to play a group custom audio ringback."
    ::= { customRingback 5 }

  bwDXSCustomRingbackGroupVideoAttempts OBJECT-TYPE
    SYNTAX      Counter32
    MAX-ACCESS  read-write
    STATUS      current
    DESCRIPTION 
        "This counter is incremented each time a command is sent to the Media Server in an attempt to play a group custom video ringback."
    ::= { customRingback 6 }

  bwDXSCustomRingbackGroupAudioFailures OBJECT-TYPE
    SYNTAX      Counter32
    MAX-ACCESS  read-write
    STATUS      current
    DESCRIPTION 
        "This counter is incremented each time where an attempt is made to play a group custom audio ringback, and that the Media Server reports any failure to play it."
    ::= { customRingback 7 }

  bwDXSCustomRingbackGroupVideoFailures OBJECT-TYPE
    SYNTAX      Counter32
    MAX-ACCESS  read-write
    STATUS      current
    DESCRIPTION 
        "This counter is incremented each time where an attempt is made to play a group custom video ringback, and that the Media Server reports any failure to play it."
    ::= { customRingback 8 }

  bwDXSCustomRingbackSPTable OBJECT-TYPE
    SYNTAX      SEQUENCE OF BwCustomRingbackSPEntry
    MAX-ACCESS  not-accessible
    STATUS      current
    DESCRIPTION 
        "Counters for the Custom Ringback service measurements for service providers."
    ::= { customRingback 9 }

  bwDXSCustomRingbackSPEntry OBJECT-TYPE
    SYNTAX      BwCustomRingbackSPEntry
    MAX-ACCESS  not-accessible
    STATUS      current
    DESCRIPTION 
        "Each row contains the service counters for the Custom Ringback service for each service provider in the system."
    INDEX       { bwDXSCustomRingbackSPIndex }
    ::= { bwDXSCustomRingbackSPTable 1 }

  BwCustomRingbackSPEntry ::= SEQUENCE {
    bwDXSCustomRingbackSPIndex                 Unsigned32,
    bwDXSCustomRingbackSPID                    DisplayString,
    bwDXSCustomRingbackUserAudioSPAttempts     Counter32,
    bwDXSCustomRingbackUserVideoSPAttempts     Counter32,
    bwDXSCustomRingbackUserAudioSPFailures     Counter32,
    bwDXSCustomRingbackUserVideoSPFailures     Counter32,
    bwDXSCustomRingbackGroupAudioSPAttempts    Counter32,
    bwDXSCustomRingbackGroupVideoSPAttempts    Counter32,
    bwDXSCustomRingbackGroupAudioSPFailures    Counter32,
    bwDXSCustomRingbackGroupVideoSPFailures    Counter32,
    bwDXSCustomRingbackUserAudioCWSPAttempts   Counter32,
    bwDXSCustomRingbackUserVideoCWSPAttempts   Counter32,
    bwDXSCustomRingbackUserAudioCWSPFailures   Counter32,
    bwDXSCustomRingbackUserVideoCWSPFailures   Counter32
  }

  bwDXSCustomRingbackSPIndex OBJECT-TYPE
    SYNTAX      Unsigned32
    MAX-ACCESS  read-only
    STATUS      current
    DESCRIPTION 
        "This column represents the index of the service provider in the system."
    ::= { bwDXSCustomRingbackSPEntry 1 }

  bwDXSCustomRingbackSPID OBJECT-TYPE
    SYNTAX      DisplayString
    MAX-ACCESS  read-only
    STATUS      current
    DESCRIPTION 
        "This string represents a service provider ID."
    ::= { bwDXSCustomRingbackSPEntry 2 }

  bwDXSCustomRingbackUserAudioSPAttempts OBJECT-TYPE
    SYNTAX      Counter32
    MAX-ACCESS  read-write
    STATUS      current
    DESCRIPTION 
        "This counter is incremented each time a command is sent to the Media Server in an attempt to play a user custom audio ringback for a given service provider."
    ::= { bwDXSCustomRingbackSPEntry 3 }

  bwDXSCustomRingbackUserVideoSPAttempts OBJECT-TYPE
    SYNTAX      Counter32
    MAX-ACCESS  read-write
    STATUS      current
    DESCRIPTION 
        "This counter is incremented each time a command is sent to the Media Server in an attempt to play a user custom video ringback for a given service provider."
    ::= { bwDXSCustomRingbackSPEntry 4 }

  bwDXSCustomRingbackUserAudioSPFailures OBJECT-TYPE
    SYNTAX      Counter32
    MAX-ACCESS  read-write
    STATUS      current
    DESCRIPTION 
        "This counter is incremented each time where an attempt is made to play a user custom audio ringback, and that the Media Server reports any failure to play it for a given service provider."
    ::= { bwDXSCustomRingbackSPEntry 5 }

  bwDXSCustomRingbackUserVideoSPFailures OBJECT-TYPE
    SYNTAX      Counter32
    MAX-ACCESS  read-write
    STATUS      current
    DESCRIPTION 
        "This counter is incremented each time where an attempt is made to play a user custom video ringback, and that the Media Server reports any failure to play it for a given service provider."
    ::= { bwDXSCustomRingbackSPEntry 6 }

  bwDXSCustomRingbackGroupAudioSPAttempts OBJECT-TYPE
    SYNTAX      Counter32
    MAX-ACCESS  read-write
    STATUS      current
    DESCRIPTION 
        "This counter is incremented each time a command is sent to the Media Server in an attempt to play a group custom audio ringback for a given service provider."
    ::= { bwDXSCustomRingbackSPEntry 7 }

  bwDXSCustomRingbackGroupVideoSPAttempts OBJECT-TYPE
    SYNTAX      Counter32
    MAX-ACCESS  read-write
    STATUS      current
    DESCRIPTION 
        "This counter is incremented each time a command is sent to the Media Server in an attempt to play a group custom video ringback for a given service provider."
    ::= { bwDXSCustomRingbackSPEntry 8 }

  bwDXSCustomRingbackGroupAudioSPFailures OBJECT-TYPE
    SYNTAX      Counter32
    MAX-ACCESS  read-write
    STATUS      current
    DESCRIPTION 
        "This counter is incremented each time where an attempt is made to play a group custom audio ringback, and that the Media Server reports any failure to play it for a given service provider."
    ::= { bwDXSCustomRingbackSPEntry 9 }

  bwDXSCustomRingbackGroupVideoSPFailures OBJECT-TYPE
    SYNTAX      Counter32
    MAX-ACCESS  read-write
    STATUS      current
    DESCRIPTION 
        "This counter is incremented each time where an attempt is made to play a group custom video ringback, and that the Media Server reports any failure to play it for a given service provider."
    ::= { bwDXSCustomRingbackSPEntry 10 }

  bwDXSCustomRingbackUserAudioCWSPAttempts OBJECT-TYPE
    SYNTAX      Counter32
    MAX-ACCESS  read-write
    STATUS      current
    DESCRIPTION 
        "Number of attempts to play a user custom audio Ringback for Call Waiting for a service provider."
    ::= { bwDXSCustomRingbackSPEntry 11 }

  bwDXSCustomRingbackUserVideoCWSPAttempts OBJECT-TYPE
    SYNTAX      Counter32
    MAX-ACCESS  read-write
    STATUS      current
    DESCRIPTION 
        "Number of attempts to play a user custom video Ringback for Call Waiting for a service provider."
    ::= { bwDXSCustomRingbackSPEntry 12 }

  bwDXSCustomRingbackUserAudioCWSPFailures OBJECT-TYPE
    SYNTAX      Counter32
    MAX-ACCESS  read-write
    STATUS      current
    DESCRIPTION 
        "Number of failures to play a user custom audio Ringback for Call Waiting for a service provider."
    ::= { bwDXSCustomRingbackSPEntry 13 }

  bwDXSCustomRingbackUserVideoCWSPFailures OBJECT-TYPE
    SYNTAX      Counter32
    MAX-ACCESS  read-write
    STATUS      current
    DESCRIPTION 
        "Number of failures to play a user custom video Ringback for Call Waiting for a service provider."
    ::= { bwDXSCustomRingbackSPEntry 14 }

  bwDXSCustomRingbackGroupTable OBJECT-TYPE
    SYNTAX      SEQUENCE OF BwCustomRingbackGroupEntry
    MAX-ACCESS  not-accessible
    STATUS      current
    DESCRIPTION 
        "Counters for the Custom Ringback service measurements for groups."
    ::= { customRingback 10 }

  bwDXSCustomRingbackGroupEntry OBJECT-TYPE
    SYNTAX      BwCustomRingbackGroupEntry
    MAX-ACCESS  not-accessible
    STATUS      current
    DESCRIPTION 
        "Each row contains the service counters for the Custom Ringback service for each group in the system."
    INDEX       { bwDXSCustomRingbackGroupIndex }
    ::= { bwDXSCustomRingbackGroupTable 1 }

  BwCustomRingbackGroupEntry ::= SEQUENCE {
    bwDXSCustomRingbackGroupIndex                  Unsigned32,
    bwDXSCustomRingbackGroupID                     DisplayString,
    bwDXSCustomRingbackUserAudioGroupAttempts      Counter32,
    bwDXSCustomRingbackUserVideoGroupAttempts      Counter32,
    bwDXSCustomRingbackUserAudioGroupFailures      Counter32,
    bwDXSCustomRingbackUserVideoGroupFailures      Counter32,
    bwDXSCustomRingbackGroupAudioGroupAttempts     Counter32,
    bwDXSCustomRingbackGroupVideoGroupAttempts     Counter32,
    bwDXSCustomRingbackGroupAudioGroupFailures     Counter32,
    bwDXSCustomRingbackGroupVideoGroupFailures     Counter32,
    bwDXSCustomRingbackUserAudioCWGroupAttempts    Counter32,
    bwDXSCustomRingbackUserVideoCWGroupAttempts    Counter32,
    bwDXSCustomRingbackUserAudioCWGroupFailures    Counter32,
    bwDXSCustomRingbackUserVideoCWGroupFailures    Counter32
  }

  bwDXSCustomRingbackGroupIndex OBJECT-TYPE
    SYNTAX      Unsigned32
    MAX-ACCESS  read-only
    STATUS      current
    DESCRIPTION 
        "This column represents the index of the group in the system."
    ::= { bwDXSCustomRingbackGroupEntry 1 }

  bwDXSCustomRingbackGroupID OBJECT-TYPE
    SYNTAX      DisplayString
    MAX-ACCESS  read-only
    STATUS      current
    DESCRIPTION 
        "This string represents a group ID."
    ::= { bwDXSCustomRingbackGroupEntry 2 }

  bwDXSCustomRingbackUserAudioGroupAttempts OBJECT-TYPE
    SYNTAX      Counter32
    MAX-ACCESS  read-write
    STATUS      current
    DESCRIPTION 
        "This counter is incremented each time a command is sent to the Media Server in an attempt to play a user custom audio ringback for a given group."
    ::= { bwDXSCustomRingbackGroupEntry 3 }

  bwDXSCustomRingbackUserVideoGroupAttempts OBJECT-TYPE
    SYNTAX      Counter32
    MAX-ACCESS  read-write
    STATUS      current
    DESCRIPTION 
        "This counter is incremented each time a command is sent to the Media Server in an attempt to play a user custom video ringback for a given group."
    ::= { bwDXSCustomRingbackGroupEntry 4 }

  bwDXSCustomRingbackUserAudioGroupFailures OBJECT-TYPE
    SYNTAX      Counter32
    MAX-ACCESS  read-write
    STATUS      current
    DESCRIPTION 
        "This counter is incremented each time where an attempt is made to play a user custom audio ringback, and that the Media Server reports any failure to play it for a given group."
    ::= { bwDXSCustomRingbackGroupEntry 5 }

  bwDXSCustomRingbackUserVideoGroupFailures OBJECT-TYPE
    SYNTAX      Counter32
    MAX-ACCESS  read-write
    STATUS      current
    DESCRIPTION 
        "This counter is incremented each time where an attempt is made to play a user custom video ringback, and that the Media Server reports any failure to play it for a given group."
    ::= { bwDXSCustomRingbackGroupEntry 6 }

  bwDXSCustomRingbackGroupAudioGroupAttempts OBJECT-TYPE
    SYNTAX      Counter32
    MAX-ACCESS  read-write
    STATUS      current
    DESCRIPTION 
        "This counter is incremented each time a command is sent to the Media Server in an attempt to play a group custom audio ringback for a given group."
    ::= { bwDXSCustomRingbackGroupEntry 7 }

  bwDXSCustomRingbackGroupVideoGroupAttempts OBJECT-TYPE
    SYNTAX      Counter32
    MAX-ACCESS  read-write
    STATUS      current
    DESCRIPTION 
        "This counter is incremented each time a command is sent to the Media Server in an attempt to play a group custom video ringback for a given group."
    ::= { bwDXSCustomRingbackGroupEntry 8 }

  bwDXSCustomRingbackGroupAudioGroupFailures OBJECT-TYPE
    SYNTAX      Counter32
    MAX-ACCESS  read-write
    STATUS      current
    DESCRIPTION 
        "This counter is incremented each time where an attempt is made to play a group custom audio ringback, and that the Media Server reports any failure to play it for a given group."
    ::= { bwDXSCustomRingbackGroupEntry 9 }

  bwDXSCustomRingbackGroupVideoGroupFailures OBJECT-TYPE
    SYNTAX      Counter32
    MAX-ACCESS  read-write
    STATUS      current
    DESCRIPTION 
        "This counter is incremented each time where an attempt is made to play a group custom video ringback, and that the Media Server reports any failure to play it for a given group."
    ::= { bwDXSCustomRingbackGroupEntry 10 }

  bwDXSCustomRingbackUserAudioCWGroupAttempts OBJECT-TYPE
    SYNTAX      Counter32
    MAX-ACCESS  read-write
    STATUS      current
    DESCRIPTION 
        "Number of attempts to play a user custom audio Ringback for Call Waiting for a group."
    ::= { bwDXSCustomRingbackGroupEntry 11 }

  bwDXSCustomRingbackUserVideoCWGroupAttempts OBJECT-TYPE
    SYNTAX      Counter32
    MAX-ACCESS  read-write
    STATUS      current
    DESCRIPTION 
        "Number of attempts to play a user custom video Ringback for Call Waiting for a group."
    ::= { bwDXSCustomRingbackGroupEntry 12 }

  bwDXSCustomRingbackUserAudioCWGroupFailures OBJECT-TYPE
    SYNTAX      Counter32
    MAX-ACCESS  read-write
    STATUS      current
    DESCRIPTION 
        "Number of failures to play a user custom audio Ringback for Call Waiting for a group."
    ::= { bwDXSCustomRingbackGroupEntry 13 }

  bwDXSCustomRingbackUserVideoCWGroupFailures OBJECT-TYPE
    SYNTAX      Counter32
    MAX-ACCESS  read-write
    STATUS      current
    DESCRIPTION 
        "Number of failures to play a user custom video Ringback for Call Waiting for a group."
    ::= { bwDXSCustomRingbackGroupEntry 14 }

  bwDXSCustomRingbackUserAudioCWAttempts OBJECT-TYPE
    SYNTAX      Counter32
    MAX-ACCESS  read-write
    STATUS      current
    DESCRIPTION 
        "Number of attempts to play a user custom audio Ringback for Call Waiting."
    ::= { customRingback 11 }

  bwDXSCustomRingbackUserVideoCWAttempts OBJECT-TYPE
    SYNTAX      Counter32
    MAX-ACCESS  read-write
    STATUS      current
    DESCRIPTION 
        "Number of attempts to play a user custom video Ringback for Call Waiting."
    ::= { customRingback 12 }

  bwDXSCustomRingbackUserAudioCWFailures OBJECT-TYPE
    SYNTAX      Counter32
    MAX-ACCESS  read-write
    STATUS      current
    DESCRIPTION 
        "Number of failures to play a user custom audio Ringback for Call Waiting."
    ::= { customRingback 13 }

  bwDXSCustomRingbackUserVideoCWFailures OBJECT-TYPE
    SYNTAX      Counter32
    MAX-ACCESS  read-write
    STATUS      current
    DESCRIPTION 
        "Number of failures to play a user custom video Ringback for Call Waiting."
    ::= { customRingback 14 }

  bwDXSFaxMessagingReceived OBJECT-TYPE
    SYNTAX      Counter32
    MAX-ACCESS  read-write
    STATUS      current
    DESCRIPTION 
        "This counter is incremented each time a user receives a fax."
    ::= { faxMessaging 1 }

  bwDXSFaxMessagingReceptionFailure OBJECT-TYPE
    SYNTAX      Counter32
    MAX-ACCESS  read-write
    STATUS      current
    DESCRIPTION 
        "This counter is incremented whenever the reception of a fax fails."
    ::= { faxMessaging 2 }

  bwDXSFaxMessagingPrinted OBJECT-TYPE
    SYNTAX      Counter32
    MAX-ACCESS  read-write
    STATUS      current
    DESCRIPTION 
        "This counter is incremented each time a user sends a fax."
    ::= { faxMessaging 3 }

  bwDXSFaxMessagingPrintingFailure OBJECT-TYPE
    SYNTAX      Counter32
    MAX-ACCESS  read-write
    STATUS      current
    DESCRIPTION 
        "This counter is incremented each time the printing of a fax over a fax number fails."
    ::= { faxMessaging 4 }

  bwDXSFaxMessagingSPTable OBJECT-TYPE
    SYNTAX      SEQUENCE OF BwFaxMessagingSPEntry
    MAX-ACCESS  not-accessible
    STATUS      current
    DESCRIPTION 
        "Counters for the Fax Messaging service measurements for service providers"
    ::= { faxMessaging 5 }

  bwDXSFaxMessagingSPEntry OBJECT-TYPE
    SYNTAX      BwFaxMessagingSPEntry
    MAX-ACCESS  not-accessible
    STATUS      current
    DESCRIPTION 
        "Each row contains the service counters for the Fax Messaging service for each service provider in the system"
    INDEX       { bwDXSFaxMessagingSPIndex }
    ::= { bwDXSFaxMessagingSPTable 1 }

  BwFaxMessagingSPEntry ::= SEQUENCE {
    bwDXSFaxMessagingSPIndex               Unsigned32,
    bwDXSFaxMessagingSPID                  DisplayString,
    bwDXSFaxMessagingSPReceived            Counter32,
    bwDXSFaxMessagingSPReceptionFailure    Counter32,
    bwDXSFaxMessagingSPPrinted             Counter32,
    bwDXSFaxMessagingSPPrintingFailure     Counter32
  }

  bwDXSFaxMessagingSPIndex OBJECT-TYPE
    SYNTAX      Unsigned32
    MAX-ACCESS  read-only
    STATUS      current
    DESCRIPTION 
        "This column represents the index of the service provider in the system"
    ::= { bwDXSFaxMessagingSPEntry 1 }

  bwDXSFaxMessagingSPID OBJECT-TYPE
    SYNTAX      DisplayString
    MAX-ACCESS  read-only
    STATUS      current
    DESCRIPTION 
        "This string represents a service provider ID"
    ::= { bwDXSFaxMessagingSPEntry 2 }

  bwDXSFaxMessagingSPReceived OBJECT-TYPE
    SYNTAX      Counter32
    MAX-ACCESS  read-write
    STATUS      current
    DESCRIPTION 
        "This counter is incremented each time a user for a given service provider receives a fax."
    ::= { bwDXSFaxMessagingSPEntry 3 }

  bwDXSFaxMessagingSPReceptionFailure OBJECT-TYPE
    SYNTAX      Counter32
    MAX-ACCESS  read-write
    STATUS      current
    DESCRIPTION 
        "This counter is incremented whenever the reception of a fax fails for a user for a given service provider."
    ::= { bwDXSFaxMessagingSPEntry 4 }

  bwDXSFaxMessagingSPPrinted OBJECT-TYPE
    SYNTAX      Counter32
    MAX-ACCESS  read-write
    STATUS      current
    DESCRIPTION 
        "This counter is incremented each time a user for a given service provider sends a fax."
    ::= { bwDXSFaxMessagingSPEntry 5 }

  bwDXSFaxMessagingSPPrintingFailure OBJECT-TYPE
    SYNTAX      Counter32
    MAX-ACCESS  read-write
    STATUS      current
    DESCRIPTION 
        "This counter is incremented each time the printing of a fax over a fax number fails for a user for a given service provider."
    ::= { bwDXSFaxMessagingSPEntry 6 }

  bwDXSFaxMessagingGroupTable OBJECT-TYPE
    SYNTAX      SEQUENCE OF BwFaxMessagingGroupEntry
    MAX-ACCESS  not-accessible
    STATUS      current
    DESCRIPTION 
        "Counters for the Fax Messaging service measurements for groups"
    ::= { faxMessaging 6 }

  bwDXSFaxMessagingGroupEntry OBJECT-TYPE
    SYNTAX      BwFaxMessagingGroupEntry
    MAX-ACCESS  not-accessible
    STATUS      current
    DESCRIPTION 
        "Each row contains the service counters for the Fax Messaging service for each group in the system"
    INDEX       { bwDXSFaxMessagingGroupIndex }
    ::= { bwDXSFaxMessagingGroupTable 1 }

  BwFaxMessagingGroupEntry ::= SEQUENCE {
    bwDXSFaxMessagingGroupIndex                Unsigned32,
    bwDXSFaxMessagingGroupID                   DisplayString,
    bwDXSFaxMessagingGroupReceived             Counter32,
    bwDXSFaxMessagingGroupReceptionFailure     Counter32,
    bwDXSFaxMessagingGroupPrinted              Counter32,
    bwDXSFaxMessagingGroupPrintingFailure      Counter32
  }

  bwDXSFaxMessagingGroupIndex OBJECT-TYPE
    SYNTAX      Unsigned32
    MAX-ACCESS  read-only
    STATUS      current
    DESCRIPTION 
        "This column represents the index of the group in the system"
    ::= { bwDXSFaxMessagingGroupEntry 1 }

  bwDXSFaxMessagingGroupID OBJECT-TYPE
    SYNTAX      DisplayString
    MAX-ACCESS  read-only
    STATUS      current
    DESCRIPTION 
        "This string represents a group ID"
    ::= { bwDXSFaxMessagingGroupEntry 2 }

  bwDXSFaxMessagingGroupReceived OBJECT-TYPE
    SYNTAX      Counter32
    MAX-ACCESS  read-write
    STATUS      current
    DESCRIPTION 
        "This counter is incremented each time a user for a given group receives a fax."
    ::= { bwDXSFaxMessagingGroupEntry 3 }

  bwDXSFaxMessagingGroupReceptionFailure OBJECT-TYPE
    SYNTAX      Counter32
    MAX-ACCESS  read-write
    STATUS      current
    DESCRIPTION 
        "This counter is incremented whenever the reception of a fax fails for a user for a given group."
    ::= { bwDXSFaxMessagingGroupEntry 4 }

  bwDXSFaxMessagingGroupPrinted OBJECT-TYPE
    SYNTAX      Counter32
    MAX-ACCESS  read-write
    STATUS      current
    DESCRIPTION 
        "This counter is incremented each time a user for a given group sends a fax."
    ::= { bwDXSFaxMessagingGroupEntry 5 }

  bwDXSFaxMessagingGroupPrintingFailure OBJECT-TYPE
    SYNTAX      Counter32
    MAX-ACCESS  read-write
    STATUS      current
    DESCRIPTION 
        "This counter is incremented each time the printing of a fax over a fax number fails for a user for a given group."
    ::= { bwDXSFaxMessagingGroupEntry 6 }

  bwDXSExtEmergencyRtgQuerySent OBJECT-TYPE
    SYNTAX      Counter32
    MAX-ACCESS  read-write
    STATUS      current
    DESCRIPTION 
        "The counter shall be incremented each time the service results in a query being sent to the EN Server."
    ::= { externalemergencyrouting 1 }

  bwDXSExtEmergencyRtgQueryFailure OBJECT-TYPE
    SYNTAX      Counter32
    MAX-ACCESS  read-write
    STATUS      current
    DESCRIPTION 
        "The counter shall be incremented each time the query is not successful, either because the EN Server is unreachable, or because the routing number is invalid."
    ::= { externalemergencyrouting 2 }

  bwDXSExtEmergencyRtgENServerTimeout OBJECT-TYPE
    SYNTAX      Counter32
    MAX-ACCESS  read-write
    STATUS      current
    DESCRIPTION 
        "The counter shall be incremented each time an active connection to an EN Server times out."
    ::= { externalemergencyrouting 3 }

  bwDXSCFNRcNumForwarded OBJECT-TYPE
    SYNTAX      Counter32
    MAX-ACCESS  read-write
    STATUS      current
    DESCRIPTION 
        "This is the number of times a call is redirected by the Call Forwarding Not Reachable service."
    ::= { callForwardingNotReachable 1 }

  bwDXSCFNRcNumPhoneActivations OBJECT-TYPE
    SYNTAX      Counter32
    MAX-ACCESS  read-write
    STATUS      current
    DESCRIPTION 
        "This is the number of times the Call Forwarding Not Reachable service is activated with a FAC."
    ::= { callForwardingNotReachable 2 }

  bwDXSCFNRcNumPhoneDeactivations OBJECT-TYPE
    SYNTAX      Counter32
    MAX-ACCESS  read-write
    STATUS      current
    DESCRIPTION 
        "This is the number of times the Call Forwarding Not Reachable service is deactivated with a FAC."
    ::= { callForwardingNotReachable 3 }

  bwDXSCFNRcDestinationChanged OBJECT-TYPE
    SYNTAX      Counter32
    MAX-ACCESS  read-write
    STATUS      current
    DESCRIPTION 
        "This is the number of times the Call Forwarding Not Reachable service destination is modified with the activation FAC."
    ::= { callForwardingNotReachable 4 }

  bwDXSCallForwardingNotReachableSPTable OBJECT-TYPE
    SYNTAX      SEQUENCE OF BwCallForwardingNotReachableSPEntry
    MAX-ACCESS  not-accessible
    STATUS      current
    DESCRIPTION 
        "This is the number of times a call is redirected by the Call Forwarding Not Reachable service.  There is one instance of this counter for each service provider or enterprise defined in the system."
    ::= { callForwardingNotReachable 5 }

  bwDXSCallForwardingNotReachableSPEntry OBJECT-TYPE
    SYNTAX      BwCallForwardingNotReachableSPEntry
    MAX-ACCESS  not-accessible
    STATUS      current
    DESCRIPTION 
        "Each row contains the service counters for the Call Forwarding Not Reachable service for each service provider in the system"
    INDEX       { bwDXSCFNRcSPIndex }
    ::= { bwDXSCallForwardingNotReachableSPTable 1 }

  BwCallForwardingNotReachableSPEntry ::= SEQUENCE {
    bwDXSCFNRcSPIndex                  Unsigned32,
    bwDXSCFNRcSPID                     DisplayString,
    bwDXSCFNRcSPNumForwarded           Counter32,
    bwDXSCFNRcSPNumPhoneActivations    Counter32,
    bwDXSCFNRcSPNumPhoneDeactivations  Counter32,
    bwDXSCFNRcSPDestinationChanged     Counter32,
    bwDXSCFNRcSPNumPhoneInterrogation  Counter32
  }

  bwDXSCFNRcSPIndex OBJECT-TYPE
    SYNTAX      Unsigned32
    MAX-ACCESS  read-only
    STATUS      current
    DESCRIPTION 
        "This column represents the index of the Service Provider in the system."
    ::= { bwDXSCallForwardingNotReachableSPEntry 1 }

  bwDXSCFNRcSPID OBJECT-TYPE
    SYNTAX      DisplayString
    MAX-ACCESS  read-only
    STATUS      current
    DESCRIPTION 
        "This string represents a Service Provider ID."
    ::= { bwDXSCallForwardingNotReachableSPEntry 2 }

  bwDXSCFNRcSPNumForwarded OBJECT-TYPE
    SYNTAX      Counter32
    MAX-ACCESS  read-write
    STATUS      current
    DESCRIPTION 
        "This is the number of times a call is redirected by the Call Forwarding Not Reachable service.  There is one instance of this counter for each service provider or enterprise defined in the system."
    ::= { bwDXSCallForwardingNotReachableSPEntry 3 }

  bwDXSCFNRcSPNumPhoneActivations OBJECT-TYPE
    SYNTAX      Counter32
    MAX-ACCESS  read-write
    STATUS      current
    DESCRIPTION 
        "This is the number of times the Call Forwarding Not Reachable service is activated with a FAC.  There is one instance of this counter for each service provider or enterprise defined in the system."
    ::= { bwDXSCallForwardingNotReachableSPEntry 4 }

  bwDXSCFNRcSPNumPhoneDeactivations OBJECT-TYPE
    SYNTAX      Counter32
    MAX-ACCESS  read-write
    STATUS      current
    DESCRIPTION 
        "This is the number of times the Call Forwarding Not Reachable service is deactivated with a FAC.  There is one instance of this counter for each service provider or enterprise defined in the system."
    ::= { bwDXSCallForwardingNotReachableSPEntry 5 }

  bwDXSCFNRcSPDestinationChanged OBJECT-TYPE
    SYNTAX      Counter32
    MAX-ACCESS  read-write
    STATUS      current
    DESCRIPTION 
        "This is the number of times the Call Forwarding Not Reachable service destination is modified with the activation FAC.  There is one instance of this counter for each service provider or enterprise defined in the system."
    ::= { bwDXSCallForwardingNotReachableSPEntry 6 }

  bwDXSCFNRcSPNumPhoneInterrogation OBJECT-TYPE
    SYNTAX      Counter32
    MAX-ACCESS  read-write
    STATUS      current
    DESCRIPTION
        "This is the number of times Call Forwarding Not Reachable has been interrogated with a FAC for users in a given service provider."
    ::= { bwDXSCallForwardingNotReachableSPEntry 7 }

  bwDXSCallForwardingNotReachableGroupTable OBJECT-TYPE
    SYNTAX      SEQUENCE OF BwCallForwardingNotReachableGroupEntry
    MAX-ACCESS  not-accessible
    STATUS      current
    DESCRIPTION 
        "This is the number of times a call is redirected by the Call Forwarding Not Reachable service.  There is one instance of this counter for each group defined in the system."
    ::= { callForwardingNotReachable 6 }

  bwDXSCallForwardingNotReachableGroupEntry OBJECT-TYPE
    SYNTAX      BwCallForwardingNotReachableGroupEntry
    MAX-ACCESS  not-accessible
    STATUS      current
    DESCRIPTION 
        "Each row contains the service counters for the Call Forwarding Not Reachable service for each group in the system"
    INDEX       { bwDXSCFNRcGroupIndex }
    ::= { bwDXSCallForwardingNotReachableGroupTable 1 }

  BwCallForwardingNotReachableGroupEntry ::= SEQUENCE {
    bwDXSCFNRcGroupIndex                   Unsigned32,
    bwDXSCFNRcGroupID                      DisplayString,
    bwDXSCFNRcGroupNumForwarded            Counter32,
    bwDXSCFNRcGroupNumPhoneActivations     Counter32,
    bwDXSCFNRcGroupNumPhoneDeactivations   Counter32,
    bwDXSCFNRcGroupDestinationChanged      Counter32,
    bwDXSCFNRcGroupNumPhoneInterrogation   Counter32
  }

  bwDXSCFNRcGroupIndex OBJECT-TYPE
    SYNTAX      Unsigned32
    MAX-ACCESS  read-only
    STATUS      current
    DESCRIPTION 
        "This column represents the index of the Group in the system."
    ::= { bwDXSCallForwardingNotReachableGroupEntry 1 }

  bwDXSCFNRcGroupID OBJECT-TYPE
    SYNTAX      DisplayString
    MAX-ACCESS  read-only
    STATUS      current
    DESCRIPTION 
        "This string represents a Group ID."
    ::= { bwDXSCallForwardingNotReachableGroupEntry 2 }

  bwDXSCFNRcGroupNumForwarded OBJECT-TYPE
    SYNTAX      Counter32
    MAX-ACCESS  read-write
    STATUS      current
    DESCRIPTION 
        "This is the number of times a call is redirected by the Call Forwarding Not Reachable service.  There is one instance of this counter for each group defined in the system."
    ::= { bwDXSCallForwardingNotReachableGroupEntry 3 }

  bwDXSCFNRcGroupNumPhoneActivations OBJECT-TYPE
    SYNTAX      Counter32
    MAX-ACCESS  read-write
    STATUS      current
    DESCRIPTION 
        "This is the number of times the Call Forwarding Not Reachable service is activated with a FAC.  There is one instance of this counter for each group defined in the system."
    ::= { bwDXSCallForwardingNotReachableGroupEntry 4 }

  bwDXSCFNRcGroupNumPhoneDeactivations OBJECT-TYPE
    SYNTAX      Counter32
    MAX-ACCESS  read-write
    STATUS      current
    DESCRIPTION 
        "This is the number of times the Call Forwarding Not Reachable service is deactivated with a FAC.  There is one instance of this counter for each group defined in the system."
    ::= { bwDXSCallForwardingNotReachableGroupEntry 5 }

  bwDXSCFNRcGroupDestinationChanged OBJECT-TYPE
    SYNTAX      Counter32
    MAX-ACCESS  read-write
    STATUS      current
    DESCRIPTION 
        "This is the number of times the Call Forwarding Not Reachable service destination is modified with the activation FAC.  There is one instance of this counter for each group defined in the system."
    ::= { bwDXSCallForwardingNotReachableGroupEntry 6 }

  bwDXSCFNRcGroupNumPhoneInterrogation    OBJECT-TYPE
    SYNTAX      Counter32
    MAX-ACCESS    read-write
    STATUS      current
    DESCRIPTION
        "This is the number of times Call Forwarding Not Reachable has been interrogated with a FAC for users in a given group."
    ::= { bwDXSCallForwardingNotReachableGroupEntry 7 }

  bwDXSCFNRcNumPhoneInterrogation OBJECT-TYPE
    SYNTAX      Counter32
    MAX-ACCESS  read-write
    STATUS      current
    DESCRIPTION
        "This is the number of times Call Forwarding Not Reachable has been interrogated with a FAC."
    ::= { callForwardingNotReachable 7 }

  bwDXSECNWarningAnnouncementAttempts OBJECT-TYPE
    SYNTAX      Counter32
    MAX-ACCESS  read-write
    STATUS      current
    DESCRIPTION 
        "This is the number of times the Expensive Call Notification service attempted to play a warning announcement for a call identified as expensive."
    ::= { expensiveCallNotification 1 }

  bwDXSECNExpensiveCallReleased OBJECT-TYPE
    SYNTAX      Counter32
    MAX-ACCESS  read-write
    STATUS      current
    DESCRIPTION 
        "This is the number of times a user released an expensive call (identified as such by the Expensive Call Notification service) before it was answered."
    ::= { expensiveCallNotification 2 }

  bwDXSLocationControlSPTable OBJECT-TYPE
    SYNTAX      SEQUENCE OF BwLocationControlSPEntry
    MAX-ACCESS  not-accessible
    STATUS      current
    DESCRIPTION 
        "Each row contains the service counters for the Location Control service for each service provider in the system"
    ::= { locationControl 1 }

  bwDXSLocationControlSPEntry OBJECT-TYPE
    SYNTAX      BwLocationControlSPEntry
    MAX-ACCESS  not-accessible
    STATUS      current
    DESCRIPTION 
        "Each row contains the service counters for the Location Control service for each service provider in the system"
    INDEX       { bwDXSLocationControlSPIndex }
    ::= { bwDXSLocationControlSPTable 1 }

  BwLocationControlSPEntry ::= SEQUENCE {
    bwDXSLocationControlSPIndex                Unsigned32,
    bwDXSLocationControlSPID                   DisplayString,
    bwDXSLocationControlSPActivationSuccess    Counter32,
    bwDXSLocationControlSPDeactivationSuccess  Counter32
  }

  bwDXSLocationControlSPIndex OBJECT-TYPE
    SYNTAX      Unsigned32
    MAX-ACCESS  read-only
    STATUS      current
    DESCRIPTION 
        "This column represents the index of the Service Provider in the system."
    ::= { bwDXSLocationControlSPEntry 1 }

  bwDXSLocationControlSPID OBJECT-TYPE
    SYNTAX      DisplayString
    MAX-ACCESS  read-only
    STATUS      current
    DESCRIPTION 
        "This string represents a Service Provider ID."
    ::= { bwDXSLocationControlSPEntry 2 }

  bwDXSLocationControlSPActivationSuccess OBJECT-TYPE
    SYNTAX      Counter32
    MAX-ACCESS  read-write
    STATUS      current
    DESCRIPTION 
        "This is the number of times a user activates an alternate or BroadWorks Anywhere location using the Location Control feature.  There is one instance of this counter for each service provider defined in the system."
    ::= { bwDXSLocationControlSPEntry 3 }

  bwDXSLocationControlSPDeactivationSuccess OBJECT-TYPE
    SYNTAX      Counter32
    MAX-ACCESS  read-write
    STATUS      current
    DESCRIPTION 
        "This is the number of times a user deactivates an alternate or BroadWorks Anywhere location using the Location Control feature.  There is one instance of this counter for each service provider defined in the system."
    ::= { bwDXSLocationControlSPEntry 4 }

  bwDXSLocationControlGroupTable OBJECT-TYPE
    SYNTAX      SEQUENCE OF BwLocationControlGroupEntry
    MAX-ACCESS  not-accessible
    STATUS      current
    DESCRIPTION 
        "Each row contains the service counters for the Location Control service for each group in the system"
    ::= { locationControl 2 }

  bwDXSLocationControlGroupEntry OBJECT-TYPE
    SYNTAX      BwLocationControlGroupEntry
    MAX-ACCESS  not-accessible
    STATUS      current
    DESCRIPTION 
        "Each row contains the service counters for the Location Control service for each group in the system"
    INDEX       { bwDXSLocationControlGroupIndex }
    ::= { bwDXSLocationControlGroupTable 1 }

  BwLocationControlGroupEntry ::= SEQUENCE {
    bwDXSLocationControlGroupIndex                 Unsigned32,
    bwDXSLocationControlGroupID                    DisplayString,
    bwDXSLocationControlGroupActivationSuccess     Counter32,
    bwDXSLocationControlGroupDeactivationSuccess   Counter32
  }

  bwDXSLocationControlGroupIndex OBJECT-TYPE
    SYNTAX      Unsigned32
    MAX-ACCESS  read-only
    STATUS      current
    DESCRIPTION 
        "This column represents the index of the Group in the system."
    ::= { bwDXSLocationControlGroupEntry 1 }

  bwDXSLocationControlGroupID OBJECT-TYPE
    SYNTAX      DisplayString
    MAX-ACCESS  read-only
    STATUS      current
    DESCRIPTION 
        "This string represents a Group ID."
    ::= { bwDXSLocationControlGroupEntry 2 }

  bwDXSLocationControlGroupActivationSuccess OBJECT-TYPE
    SYNTAX      Counter32
    MAX-ACCESS  read-write
    STATUS      current
    DESCRIPTION 
        "This is the number of times a user activates an alternate or BroadWorks Anywhere location using the Location Control feature.  There is one instance of this counter for each group defined in the system."
    ::= { bwDXSLocationControlGroupEntry 3 }

  bwDXSLocationControlGroupDeactivationSuccess OBJECT-TYPE
    SYNTAX      Counter32
    MAX-ACCESS  read-write
    STATUS      current
    DESCRIPTION 
        "This is the number of times a user deactivates an alternate or BroadWorks Anywhere location using the Location Control feature.  There is one instance of this counter for each group defined in the system."
    ::= { bwDXSLocationControlGroupEntry 4 }

  bwDXSLocationControlActivationSuccess OBJECT-TYPE
    SYNTAX      Counter32
    MAX-ACCESS  read-write
    STATUS      current
    DESCRIPTION 
        "This is the number of times a user activates an alternate or BroadWorks Anywhere location using the Location Control feature."
    ::= { locationControl 3 }

  bwDXSLocationControlDeactivationSuccess OBJECT-TYPE
    SYNTAX      Counter32
    MAX-ACCESS  read-write
    STATUS      current
    DESCRIPTION 
        "This is the number of times a user deactivates an alternate or BroadWorks Anywhere location using the Location Control feature."
    ::= { locationControl 4 }

  bwDXSCallRetrieveSPTable OBJECT-TYPE
    SYNTAX      SEQUENCE OF BwCallRetrieveSPEntry
    MAX-ACCESS  not-accessible
    STATUS      current
    DESCRIPTION 
        "Each row contains the service counters for the Call Retrieve service for each service provider in the system"
    ::= { callRetrieve 1 }

  bwDXSCallRetrieveSPEntry OBJECT-TYPE
    SYNTAX      BwCallRetrieveSPEntry
    MAX-ACCESS  not-accessible
    STATUS      current
    DESCRIPTION 
        "Each row contains the service counters for the Call Retrieve service for each service provider in the system"
    INDEX       { bwDXSCallRetrieveSPIndex }
    ::= { bwDXSCallRetrieveSPTable 1 }

  BwCallRetrieveSPEntry ::= SEQUENCE {
    bwDXSCallRetrieveSPIndex       Unsigned32,
    bwDXSCallRetrieveSPID          DisplayString,
    bwDXSCallRetrieveSPSuccess     Counter32
  }

  bwDXSCallRetrieveSPIndex OBJECT-TYPE
    SYNTAX      Unsigned32
    MAX-ACCESS  read-only
    STATUS      current
    DESCRIPTION 
        "This column represents the index of the Service Provider in the system."
    ::= { bwDXSCallRetrieveSPEntry 1 }

  bwDXSCallRetrieveSPID OBJECT-TYPE
    SYNTAX      DisplayString
    MAX-ACCESS  read-only
    STATUS      current
    DESCRIPTION 
        "This string represents a Service Provider ID."
    ::= { bwDXSCallRetrieveSPEntry 2 }

  bwDXSCallRetrieveSPSuccess OBJECT-TYPE
    SYNTAX      Counter32
    MAX-ACCESS  read-write
    STATUS      current
    DESCRIPTION 
        "The number of times a user successfully retrieves a call using the Call Retrieve feature.  There is one instance of this counter for each service provider defined in the system."
    ::= { bwDXSCallRetrieveSPEntry 3 }

  bwDXSCallRetrieveGroupTable OBJECT-TYPE
    SYNTAX      SEQUENCE OF BwCallRetrieveGroupEntry
    MAX-ACCESS  not-accessible
    STATUS      current
    DESCRIPTION 
        "Each row contains the service counters for the Call Retrieve service for each group in the system"
    ::= { callRetrieve 2 }

  bwDXSCallRetrieveGroupEntry OBJECT-TYPE
    SYNTAX      BwCallRetrieveGroupEntry
    MAX-ACCESS  not-accessible
    STATUS      current
    DESCRIPTION 
        "Each row contains the service counters for the Call Retrieve service for each service provider in the system"
    INDEX       { bwDXSCallRetrieveGroupIndex }
    ::= { bwDXSCallRetrieveGroupTable 1 }

  BwCallRetrieveGroupEntry ::= SEQUENCE {
    bwDXSCallRetrieveGroupIndex    Unsigned32,
    bwDXSCallRetrieveGroupID       DisplayString,
    bwDXSCallRetrieveGroupSuccess  Counter32
  }

  bwDXSCallRetrieveGroupIndex OBJECT-TYPE
    SYNTAX      Unsigned32
    MAX-ACCESS  read-only
    STATUS      current
    DESCRIPTION 
        "This column represents the index of the Group in the system."
    ::= { bwDXSCallRetrieveGroupEntry 1 }

  bwDXSCallRetrieveGroupID OBJECT-TYPE
    SYNTAX      DisplayString
    MAX-ACCESS  read-only
    STATUS      current
    DESCRIPTION 
        "This string represents a Group ID."
    ::= { bwDXSCallRetrieveGroupEntry 2 }

  bwDXSCallRetrieveGroupSuccess OBJECT-TYPE
    SYNTAX      Counter32
    MAX-ACCESS  read-write
    STATUS      current
    DESCRIPTION 
        "The number of times a user successfully retrieves a call using the Call Retrieve feature.  There is one instance of this counter for each group defined in the system."
    ::= { bwDXSCallRetrieveGroupEntry 3 }

  bwDXSCallRetrieveSuccess OBJECT-TYPE
    SYNTAX      Counter32
    MAX-ACCESS  read-write
    STATUS      current
    DESCRIPTION 
        "This is the number of times a user successfully retrieves a call using the Call Retrieve feature."
    ::= { callRetrieve 3 }

  bwDXSBroadWorksAnywhereSPTable OBJECT-TYPE
    SYNTAX      SEQUENCE OF BwBroadWorksAnywhereSPEntry
    MAX-ACCESS  not-accessible
    STATUS      current
    DESCRIPTION 
        "Each row contains the service counters for the BroadWorks Anywhere service for each service provider in the system"
    ::= { broadworksAnywhere 1 }

  bwDXSBroadWorksAnywhereSPEntry OBJECT-TYPE
    SYNTAX      BwBroadWorksAnywhereSPEntry
    MAX-ACCESS  not-accessible
    STATUS      current
    DESCRIPTION 
        "Each row contains the service counters for the BroadWorks Anywhere service for each service provider in the system"
    INDEX       { bwDXSBroadWorksAnywhereSPIndex }
    ::= { bwDXSBroadWorksAnywhereSPTable 1 }

  BwBroadWorksAnywhereSPEntry ::= SEQUENCE {
    bwDXSBroadWorksAnywhereSPIndex     Unsigned32,
    bwDXSBroadWorksAnywhereSPID        DisplayString,
    bwDXSBASPCallOriginations          Counter32,
    bwDXSBASPCallTerminations          Counter32
  }

  bwDXSBroadWorksAnywhereSPIndex OBJECT-TYPE
    SYNTAX      Unsigned32
    MAX-ACCESS  read-only
    STATUS      current
    DESCRIPTION 
        "This column represents the index of the Service Provider in the system."
    ::= { bwDXSBroadWorksAnywhereSPEntry 1 }

  bwDXSBroadWorksAnywhereSPID OBJECT-TYPE
    SYNTAX      DisplayString
    MAX-ACCESS  read-only
    STATUS      current
    DESCRIPTION 
        "This string represents a Service Provider ID."
    ::= { bwDXSBroadWorksAnywhereSPEntry 2 }

  bwDXSBASPCallOriginations OBJECT-TYPE
    SYNTAX      Counter32
    MAX-ACCESS  read-write
    STATUS      current
    DESCRIPTION 
        "This is the number of times a user originates a call through the BroadWorks Anywhere Portal. There is one instance of this counter for each service provider or enterprise defined in the system."
    ::= { bwDXSBroadWorksAnywhereSPEntry 3 }

  bwDXSBASPCallTerminations OBJECT-TYPE
    SYNTAX      Counter32
    MAX-ACCESS  read-write
    STATUS      current
    DESCRIPTION 
        "This is the number of times a call leg is extended to a BroadWorks Anywhere location. There is one instance of this counter for each service provider or enterprise defined in the system."
    ::= { bwDXSBroadWorksAnywhereSPEntry 4 }

  bwDXSBroadWorksAnywhereGroupTable OBJECT-TYPE
    SYNTAX      SEQUENCE OF BwBroadWorksAnywhereGroupEntry
    MAX-ACCESS  not-accessible
    STATUS      current
    DESCRIPTION 
        "Each row contains the service counters for the BroadWorks Anywhere service for each group in the system"
    ::= { broadworksAnywhere 2 }

  bwDXSBroadWorksAnywhereGroupEntry OBJECT-TYPE
    SYNTAX      BwBroadWorksAnywhereGroupEntry
    MAX-ACCESS  not-accessible
    STATUS      current
    DESCRIPTION 
        "Each row contains the service counters for the BroadWorks Anywhere service for each service provider in the system"
    INDEX       { bwDXSBroadWorksAnywhereGroupIndex }
    ::= { bwDXSBroadWorksAnywhereGroupTable 1 }

  BwBroadWorksAnywhereGroupEntry ::= SEQUENCE {
    bwDXSBroadWorksAnywhereGroupIndex  Unsigned32,
    bwDXSBroadWorksAnywhereGroupID     DisplayString,
    bwDXSBAGroupCallOriginations       Counter32,
    bwDXSBAGroupCallTerminations       Counter32
  }

  bwDXSBroadWorksAnywhereGroupIndex OBJECT-TYPE
    SYNTAX      Unsigned32
    MAX-ACCESS  read-only
    STATUS      current
    DESCRIPTION 
        "This column represents the index of the Group in the system."
    ::= { bwDXSBroadWorksAnywhereGroupEntry 1 }

  bwDXSBroadWorksAnywhereGroupID OBJECT-TYPE
    SYNTAX      DisplayString
    MAX-ACCESS  read-only
    STATUS      current
    DESCRIPTION 
        "This string represents a Group ID."
    ::= { bwDXSBroadWorksAnywhereGroupEntry 2 }

  bwDXSBAGroupCallOriginations OBJECT-TYPE
    SYNTAX      Counter32
    MAX-ACCESS  read-write
    STATUS      current
    DESCRIPTION 
        "This is the number of times a user originates a call through the BroadWorks Anywhere Portal. There is one instance of this counter for each group defined in the system."
    ::= { bwDXSBroadWorksAnywhereGroupEntry 3 }

  bwDXSBAGroupCallTerminations OBJECT-TYPE
    SYNTAX      Counter32
    MAX-ACCESS  read-write
    STATUS      current
    DESCRIPTION 
        "This is the number of times a call leg is extended to a BroadWorks Anywhere location. There is one instance of this counter for each group defined in the system."
    ::= { bwDXSBroadWorksAnywhereGroupEntry 4 }

  bwDXSBACallOriginations OBJECT-TYPE
    SYNTAX      Counter32
    MAX-ACCESS  read-write
    STATUS      current
    DESCRIPTION 
        "This is the number of times a user originates a call through the BroadWorks Anywhere Portal."
    ::= { broadworksAnywhere 3 }

  bwDXSBACallTerminations OBJECT-TYPE
    SYNTAX      Counter32
    MAX-ACCESS  read-write
    STATUS      current
    DESCRIPTION 
        "This is the number of times a call leg is extended to a BroadWorks Anywhere location. "
    ::= { broadworksAnywhere 4 }

  bwDXSCommunicationBarringBlockedTreatment OBJECT-TYPE
    SYNTAX      Counter32
    MAX-ACCESS  read-write
    STATUS      current
    DESCRIPTION 
        "This is the number of times a call is blocked by the Communication Barring service with an action of Block or Treatment."
    ::= { communicationBarring 1 }

  bwDXSCommunicationBarringBlockedTransfer OBJECT-TYPE
    SYNTAX      Counter32
    MAX-ACCESS  read-write
    STATUS      current
    DESCRIPTION 
        "This is the number of times a call is blocked by the Communication Barring service with an action of Transfer."
    ::= { communicationBarring 2 }

  bwDXSCommunicationBarringPromptedPIN OBJECT-TYPE
    SYNTAX      Counter32
    MAX-ACCESS  read-write
    STATUS      current
    DESCRIPTION 
        "This is the number of times a subscriber is prompted for a PIN by the Communication Barring service."
    ::= { communicationBarring 3 }

  bwDXSCommunicationBarringFailedPIN OBJECT-TYPE
    SYNTAX      Counter32
    MAX-ACCESS  read-write
    STATUS      current
    DESCRIPTION 
        "This is the number of times a subscriber fails to enter a valid PIN required by the Communication Barring service."
    ::= { communicationBarring 4 }

  bwDXSCommunicationBarringSPTable OBJECT-TYPE
    SYNTAX      SEQUENCE OF BwCommunicationBarringSPEntry
    MAX-ACCESS  not-accessible
    STATUS      current
    DESCRIPTION 
        "Each row contains the service counters for the Communication Barring service for each service provider in the system"
    ::= { communicationBarring 5 }

  bwDXSCommunicationBarringSPEntry OBJECT-TYPE
    SYNTAX      BwCommunicationBarringSPEntry
    MAX-ACCESS  not-accessible
    STATUS      current
    DESCRIPTION 
        "Each row contains the service counters for the Communication Barring service for each service provider in the system"
    INDEX       { bwDXSCommunicationBarringSPIndex }
    ::= { bwDXSCommunicationBarringSPTable 1 }

  BwCommunicationBarringSPEntry ::= SEQUENCE {
    bwDXSCommunicationBarringSPIndex                   Unsigned32,
    bwDXSCommunicationBarringSPID                      DisplayString,
    bwDXSCommunicationBarringSPBlockedTreatment        Counter32,
    bwDXSCommunicationBarringSPBlockedTransfer         Counter32,
    bwDXSCommunicationBarringSPPromptedPIN             Counter32,
    bwDXSCommunicationBarringSPFailedPIN               Counter32,
    bwDXSCommunicationBarringSPCallDurationExceeded    Counter32,
    bwDXSCommunicationBarringSPPhoneActivations        Counter32,
    bwDXSCommunicationBarringSPPhoneDeactivations      Counter32,
    bwDXSCommunicationBarringSPPhoneQueries            Counter32,
    bwDXSCommunicationBarringSPErroneousPinAttempts    Counter32,
    bwDXSCommunicationBarringSPLockouts                Counter32
  }

  bwDXSCommunicationBarringSPIndex OBJECT-TYPE
    SYNTAX      Unsigned32
    MAX-ACCESS  read-only
    STATUS      current
    DESCRIPTION 
        "This column represents the index of the Service Provider in the system."
    ::= { bwDXSCommunicationBarringSPEntry 1 }

  bwDXSCommunicationBarringSPID OBJECT-TYPE
    SYNTAX      DisplayString
    MAX-ACCESS  read-only
    STATUS      current
    DESCRIPTION 
        "This string represents a Service Provider ID."
    ::= { bwDXSCommunicationBarringSPEntry 2 }

  bwDXSCommunicationBarringSPBlockedTreatment OBJECT-TYPE
    SYNTAX      Counter32
    MAX-ACCESS  read-write
    STATUS      current
    DESCRIPTION 
        "This is the number of times a call is blocked by the Communication Barring service with an action of Block or Treatment.  There is one instance of this counter for each service provider or enterprise defined in the system."
    ::= { bwDXSCommunicationBarringSPEntry 3 }

  bwDXSCommunicationBarringSPBlockedTransfer OBJECT-TYPE
    SYNTAX      Counter32
    MAX-ACCESS  read-write
    STATUS      current
    DESCRIPTION 
        "This is the number of times a call is blocked by the Communication Barring service with an action of Transfer.  There is one instance of this counter for each service provider or enterprise defined in the system."
    ::= { bwDXSCommunicationBarringSPEntry 4 }

  bwDXSCommunicationBarringSPPromptedPIN OBJECT-TYPE
    SYNTAX      Counter32
    MAX-ACCESS  read-write
    STATUS      current
    DESCRIPTION 
        "This is the number of times a subscriber is prompted for a PIN by the Communication Barring service.  There is one instance of this counter for each service provider or enterprise defined in the system."
    ::= { bwDXSCommunicationBarringSPEntry 5 }

  bwDXSCommunicationBarringSPFailedPIN OBJECT-TYPE
    SYNTAX      Counter32
    MAX-ACCESS  read-write
    STATUS      current
    DESCRIPTION 
        "This is the number of times a subscriber fails to enter a valid PIN required by the Communication Barring service.  There is one instance of this counter for each service provider or enterprise defined in the system."
    ::= { bwDXSCommunicationBarringSPEntry 6 }

  bwDXSCommunicationBarringSPCallDurationExceeded OBJECT-TYPE
    SYNTAX      Counter32
    MAX-ACCESS  read-write
    STATUS      current
    DESCRIPTION 
        "This is the number of times the call duration exceeds the maximum allowed duration specified by the Allow Timed or Authorization Code Timed action of Communication Barring service.  There is one instance of this counter for each service provider or enterprise defined in the system."
    ::= { bwDXSCommunicationBarringSPEntry 7 }

  bwDXSCommunicationBarringSPPhoneActivations  OBJECT-TYPE
    SYNTAX      Counter32
    MAX-ACCESS  read-write
    STATUS      current
    DESCRIPTION
        "This is the number of times the Communication Barring User-Control service is activated with a FAC.  There is one instance of this counter for each service provider or enterprise defined in the system."
    ::= { bwDXSCommunicationBarringSPEntry 8 }

  bwDXSCommunicationBarringSPPhoneDeactivations  OBJECT-TYPE
    SYNTAX      Counter32
    MAX-ACCESS  read-write
    STATUS      current
    DESCRIPTION
        "This is the number of times the Communication Barring User-Control service is deactivated with a FAC.  There is one instance of this counter for each service provider or enterprise defined in the system."
    ::= { bwDXSCommunicationBarringSPEntry 9 }

  bwDXSCommunicationBarringSPPhoneQueries  OBJECT-TYPE
    SYNTAX      Counter32
    MAX-ACCESS  read-write
    STATUS      current
    DESCRIPTION
        "This is the number of times the Communication Barring User-Control service status is queried with a FAC.  There is one instance of this counter for each service provider or enterprise defined in the system."
    ::= { bwDXSCommunicationBarringSPEntry 10 }

  bwDXSCommunicationBarringSPErroneousPinAttempts  OBJECT-TYPE
    SYNTAX      Counter32
    MAX-ACCESS  read-write
    STATUS      current
    DESCRIPTION
        "This is the number of times an attempt to activate or deactivate the Communication Barring User-Control service is made with an invalid PIN code or without a PIN.  There is one instance of this counter for each service provider or enterprise defined in the system."
    ::= { bwDXSCommunicationBarringSPEntry 11 }

  bwDXSCommunicationBarringSPLockouts  OBJECT-TYPE
    SYNTAX      Counter32
    MAX-ACCESS  read-write
    STATUS      current
    DESCRIPTION
        "This is the number of times a user is locked out of the activation and deactivation FAC access to the Communication Barring User-Control service.  There is one instance of this counter for each service provider or enterprise defined in the system."
    ::= { bwDXSCommunicationBarringSPEntry 12 }

  bwDXSCommunicationBarringGroupTable OBJECT-TYPE
    SYNTAX      SEQUENCE OF BwCommunicationBarringGroupEntry
    MAX-ACCESS  not-accessible
    STATUS      current
    DESCRIPTION 
        "Each row contains the service counters for the Communication Barring service for each group in the system"
    ::= { communicationBarring 6 }

  bwDXSCommunicationBarringGroupEntry OBJECT-TYPE
    SYNTAX      BwCommunicationBarringGroupEntry
    MAX-ACCESS  not-accessible
    STATUS      current
    DESCRIPTION 
        "Each row contains the service counters for the Communication Barring service for each group in the system"
    INDEX       { bwDXSCommunicationBarringGroupIndex }
    ::= { bwDXSCommunicationBarringGroupTable 1 }

  BwCommunicationBarringGroupEntry ::= SEQUENCE {
    bwDXSCommunicationBarringGroupIndex                    Unsigned32,
    bwDXSCommunicationBarringGroupID                       DisplayString,
    bwDXSCommunicationBarringGroupBlockedTreatment         Counter32,
    bwDXSCommunicationBarringGroupBlockedTransfer          Counter32,
    bwDXSCommunicationBarringGroupPromptedPIN              Counter32,
    bwDXSCommunicationBarringGroupFailedPIN                Counter32,
    bwDXSCommunicationBarringGroupCallDurationExceeded     Counter32,
    bwDXSCommunicationBarringGroupPhoneActivations         Counter32,
    bwDXSCommunicationBarringGroupPhoneDeactivations       Counter32,
    bwDXSCommunicationBarringGroupPhoneQueries             Counter32,
    bwDXSCommunicationBarringGroupErroneousPinAttempts     Counter32,
    bwDXSCommunicationBarringGroupLockouts                 Counter32
  }

  bwDXSCommunicationBarringGroupIndex OBJECT-TYPE
    SYNTAX      Unsigned32
    MAX-ACCESS  read-only
    STATUS      current
    DESCRIPTION 
        "This column represents the index of the Group in the system."
    ::= { bwDXSCommunicationBarringGroupEntry 1 }

  bwDXSCommunicationBarringGroupID OBJECT-TYPE
    SYNTAX      DisplayString
    MAX-ACCESS  read-only
    STATUS      current
    DESCRIPTION 
        "This string represents a Group ID."
    ::= { bwDXSCommunicationBarringGroupEntry 2 }

  bwDXSCommunicationBarringGroupBlockedTreatment OBJECT-TYPE
    SYNTAX      Counter32
    MAX-ACCESS  read-write
    STATUS      current
    DESCRIPTION 
        "This is the number of times a call is blocked by the Communication Barring service with an action of Block or Treatment.  There is one instance of this counter for each group defined in the system."
    ::= { bwDXSCommunicationBarringGroupEntry 3 }

  bwDXSCommunicationBarringGroupBlockedTransfer OBJECT-TYPE
    SYNTAX      Counter32
    MAX-ACCESS  read-write
    STATUS      current
    DESCRIPTION 
        "This is the number of times a call is blocked by the Communication Barring service with an action of Transfer.  There is one instance of this counter for each group defined in the system."
    ::= { bwDXSCommunicationBarringGroupEntry 4 }

  bwDXSCommunicationBarringGroupPromptedPIN OBJECT-TYPE
    SYNTAX      Counter32
    MAX-ACCESS  read-write
    STATUS      current
    DESCRIPTION 
        "This is the number of times a subscriber is prompted for a PIN by the Communication Barring service.  There is one instance of this counter for each group defined in the system."
    ::= { bwDXSCommunicationBarringGroupEntry 5 }

  bwDXSCommunicationBarringGroupFailedPIN OBJECT-TYPE
    SYNTAX      Counter32
    MAX-ACCESS  read-write
    STATUS      current
    DESCRIPTION 
        "This is the number of times a subscriber fails to enter a valid PIN required by the Communication Barring service.  There is one instance of this counter for each group defined in the system."
    ::= { bwDXSCommunicationBarringGroupEntry 6 }

  bwDXSCommunicationBarringGroupCallDurationExceeded OBJECT-TYPE
    SYNTAX      Counter32
    MAX-ACCESS  read-write
    STATUS      current
    DESCRIPTION 
        "This is the number of times the call duration exceeds the maximum allowed duration specified by the Allow Timed or Authorization Code Timed action of Communication Barring service.  There is one instance of this counter for each group defined in the system."
    ::= { bwDXSCommunicationBarringGroupEntry 7 }

  bwDXSCommunicationBarringCallDurationExceeded OBJECT-TYPE
    SYNTAX      Counter32
    MAX-ACCESS  read-write
    STATUS      current
    DESCRIPTION 
        "This is the number of times the call duration exceeds the maximum allowed duration specified by the Allow Timed or Authorization Code Timed action of Communication Barring service."
    ::= { communicationBarring 7 }

  bwDXSCommunicationBarringGroupPhoneActivations OBJECT-TYPE
    SYNTAX      Counter32
    MAX-ACCESS  read-write
    STATUS      current
    DESCRIPTION
        "This is the number of times the Communication Barring User-Control service is activated with a FAC.  There is one instance of this counter for each group defined in the system."
    ::= { bwDXSCommunicationBarringGroupEntry 8 }

  bwDXSCommunicationBarringGroupPhoneDeactivations OBJECT-TYPE
    SYNTAX      Counter32
    MAX-ACCESS  read-write
    STATUS      current
    DESCRIPTION
        "This is the number of times the Communication Barring User-Control service is deactivated with a FAC.  There is one instance of this counter for each group defined in the system."
    ::= { bwDXSCommunicationBarringGroupEntry 9 }

  bwDXSCommunicationBarringGroupPhoneQueries OBJECT-TYPE
    SYNTAX      Counter32
    MAX-ACCESS  read-write
    STATUS      current
    DESCRIPTION
        "This is the number of times the Communication Barring User-Control service status is queried with a FAC.  There is one instance of this counter for each group defined in the system."
    ::= { bwDXSCommunicationBarringGroupEntry 10 }

  bwDXSCommunicationBarringGroupErroneousPinAttempts OBJECT-TYPE
    SYNTAX      Counter32
    MAX-ACCESS  read-write
    STATUS      current
    DESCRIPTION
        "This is the number of times an attempt to activate or deactivate the Communication Barring User-Control service is made with an invalid PIN code or without a PIN.  There is one instance of this counter for each group defined in the system."
    ::= { bwDXSCommunicationBarringGroupEntry 11 }

  bwDXSCommunicationBarringGroupLockouts OBJECT-TYPE
    SYNTAX      Counter32
    MAX-ACCESS  read-write
    STATUS      current
    DESCRIPTION
        "This is the number of times a user is locked out of the activation and deactivation FAC access to the Communication Barring User-Control service.  There is one instance of this counter for each group defined in the system."
    ::= { bwDXSCommunicationBarringGroupEntry 12 }

  bwDXSCommunicationBarringPhoneActivations OBJECT-TYPE
    SYNTAX      Counter32
    MAX-ACCESS  read-write
    STATUS      current
    DESCRIPTION
        "This is the number of times the Communication Barring User-Control service is activated with a FAC."
    ::= { communicationBarring 8 }

  bwDXSCommunicationBarringPhoneDeactivations OBJECT-TYPE
    SYNTAX      Counter32
    MAX-ACCESS  read-write
    STATUS      current
    DESCRIPTION
        "This is the number of times the Communication Barring User-Control service is deactivated with a FAC."
    ::= { communicationBarring 9 }

  bwDXSCommunicationBarringPhoneQueries OBJECT-TYPE
    SYNTAX      Counter32
    MAX-ACCESS  read-write
    STATUS      current
    DESCRIPTION
        "This is the number of times the Communication Barring User-Control service status is queried with a FAC."
    ::= { communicationBarring 10 }

  bwDXSCommunicationBarringErroneousPinAttempts OBJECT-TYPE
    SYNTAX      Counter32
    MAX-ACCESS  read-write
    STATUS      current
    DESCRIPTION
        "This is the number of times an attempt to activate or deactivate the Communication Barring User-Control service is made with an invalid PIN code or without a PIN."
    ::= { communicationBarring 11 }

  bwDXSCommunicationBarringLockouts OBJECT-TYPE
    SYNTAX      Counter32
    MAX-ACCESS  read-write
    STATUS      current
    DESCRIPTION
        "This is the number of times a user is locked out of the activation and deactivation FAC access to the Communication Barring User-Control service."
    ::= { communicationBarring 12 }

  bwDXSCallBridgeSuccess OBJECT-TYPE
    SYNTAX      Counter32
    MAX-ACCESS  read-write
    STATUS      current
    DESCRIPTION 
        "This is the number of times a user successfully initiates/join a SCA-Bridge using the Call Retrieve feature."
    ::= { callBridge 1 }

  bwDXSCallBridgeSPTable OBJECT-TYPE
    SYNTAX      SEQUENCE OF BwCallBridgeSPEntry
    MAX-ACCESS  not-accessible
    STATUS      current
    DESCRIPTION 
        "Each row contains the service counters for the Call Bridge service for each service provider in the system"
    ::= { callBridge 2 }

  bwDXSCallBridgeSPEntry OBJECT-TYPE
    SYNTAX      BwCallBridgeSPEntry
    MAX-ACCESS  not-accessible
    STATUS      current
    DESCRIPTION 
        "Each row contains the service counters for the Communication Barring service for each service provider in the system"
    INDEX       { bwDXSCallBridgeSPIndex }
    ::= { bwDXSCallBridgeSPTable 1 }

  BwCallBridgeSPEntry ::= SEQUENCE {
    bwDXSCallBridgeSPIndex     Unsigned32,
    bwDXSCallBridgeSPID        DisplayString,
    bwDXSCallBridgeSPSuccess   Counter32
  }

  bwDXSCallBridgeSPIndex OBJECT-TYPE
    SYNTAX      Unsigned32
    MAX-ACCESS  read-only
    STATUS      current
    DESCRIPTION 
        "This column represents the index of the Service Provider in the system."
    ::= { bwDXSCallBridgeSPEntry 1 }

  bwDXSCallBridgeSPID OBJECT-TYPE
    SYNTAX      DisplayString
    MAX-ACCESS  read-only
    STATUS      current
    DESCRIPTION 
        "This string represents a Service Provider ID."
    ::= { bwDXSCallBridgeSPEntry 2 }

  bwDXSCallBridgeSPSuccess OBJECT-TYPE
    SYNTAX      Counter32
    MAX-ACCESS  read-write
    STATUS      current
    DESCRIPTION 
        "The number of times a user successfully initiates/join a SCA-Bridge using the Call Bridge feature.  There is one instance of this counter for each service provider defined in the system."
    ::= { bwDXSCallBridgeSPEntry 3 }

  bwDXSCallBridgeGroupTable OBJECT-TYPE
    SYNTAX      SEQUENCE OF BwCallBridgeGroupEntry
    MAX-ACCESS  not-accessible
    STATUS      current
    DESCRIPTION 
        "Each row contains the service counters for the Call Bridge service for each group in the system"
    ::= { callBridge 3 }

  bwDXSCallBridgeGroupEntry OBJECT-TYPE
    SYNTAX      BwCallBridgeGroupEntry
    MAX-ACCESS  not-accessible
    STATUS      current
    DESCRIPTION 
        "Each row contains the service counters for the Communication Barring service for each group in the system"
    INDEX       { bwDXSCallBridgeGroupIndex }
    ::= { bwDXSCallBridgeGroupTable 1 }

  BwCallBridgeGroupEntry ::= SEQUENCE {
    bwDXSCallBridgeGroupIndex      Unsigned32,
    bwDXSCallBridgeGroupID         DisplayString,
    bwDXSCallBridgeGroupSuccess    Counter32
  }

  bwDXSCallBridgeGroupIndex OBJECT-TYPE
    SYNTAX      Unsigned32
    MAX-ACCESS  read-only
    STATUS      current
    DESCRIPTION 
        "This column represents the index of the Group in the system."
    ::= { bwDXSCallBridgeGroupEntry 1 }

  bwDXSCallBridgeGroupID OBJECT-TYPE
    SYNTAX      DisplayString
    MAX-ACCESS  read-only
    STATUS      current
    DESCRIPTION 
        "This string represents a Group ID."
    ::= { bwDXSCallBridgeGroupEntry 2 }

  bwDXSCallBridgeGroupSuccess OBJECT-TYPE
    SYNTAX      Counter32
    MAX-ACCESS  read-write
    STATUS      current
    DESCRIPTION 
        "The number of times a user successfully initiates/join a SCA-Bridge using the Call Bridge feature.  There is one instance of this counter for each group defined in the system."
    ::= { bwDXSCallBridgeGroupEntry 3 }

  bwDXSDirectoryNumberHuntingIncomingCalls OBJECT-TYPE
    SYNTAX      Counter32
    MAX-ACCESS  read-write
    STATUS      current
    DESCRIPTION 
        "This is the number of calls to an agent belonging to Directory Number Hunting groups."
    ::= { directoryNumberHunting 1 }

  bwDXSDirectoryNumberHuntingSPTable OBJECT-TYPE
    SYNTAX      SEQUENCE OF BwDirectoryNumberHuntingSPEntry
    MAX-ACCESS  not-accessible
    STATUS      current
    DESCRIPTION 
        "Each row contains the service counters for the Directory Number Hunting service for each service provider in the system"
    ::= { directoryNumberHunting 2 }

  bwDXSDirectoryNumberHuntingSPEntry OBJECT-TYPE
    SYNTAX      BwDirectoryNumberHuntingSPEntry
    MAX-ACCESS  not-accessible
    STATUS      current
    DESCRIPTION 
        "Each row contains the service counters for the Directory Number Hunting service for each service provider in the system"
    INDEX       { bwDXSDirectoryNumberHuntingSPIndex }
    ::= { bwDXSDirectoryNumberHuntingSPTable 1 }

  BwDirectoryNumberHuntingSPEntry ::= SEQUENCE {
    bwDXSDirectoryNumberHuntingSPIndex             Unsigned32,
    bwDXSDirectoryNumberHuntingSPID                DisplayString,
    bwDXSDirectoryNumberHuntingSPIncomingCalls     Counter32
  }

  bwDXSDirectoryNumberHuntingSPIndex OBJECT-TYPE
    SYNTAX      Unsigned32
    MAX-ACCESS  read-only
    STATUS      current
    DESCRIPTION 
        "This column represents the index of the Service Provider in the system."
    ::= { bwDXSDirectoryNumberHuntingSPEntry 1 }

  bwDXSDirectoryNumberHuntingSPID OBJECT-TYPE
    SYNTAX      DisplayString
    MAX-ACCESS  read-only
    STATUS      current
    DESCRIPTION 
        "This string represents a Service Provider ID."
    ::= { bwDXSDirectoryNumberHuntingSPEntry 2 }

  bwDXSDirectoryNumberHuntingSPIncomingCalls OBJECT-TYPE
    SYNTAX      Counter32
    MAX-ACCESS  read-write
    STATUS      current
    DESCRIPTION 
        "This is the number of calls to an agent belonging to Directory Number Hunting groups.  There is one instance of this counter for each service provider defined in the system."
    ::= { bwDXSDirectoryNumberHuntingSPEntry 3 }

  bwDXSDirectoryNumberHuntingGroupTable OBJECT-TYPE
    SYNTAX      SEQUENCE OF BwDirectoryNumberHuntingGroupEntry
    MAX-ACCESS  not-accessible
    STATUS      current
    DESCRIPTION 
        "Each row contains the service counters for the Directory Number Hunting service for each group in the system"
    ::= { directoryNumberHunting 3 }

  bwDXSDirectoryNumberHuntingGroupEntry OBJECT-TYPE
    SYNTAX      BwDirectoryNumberHuntingGroupEntry
    MAX-ACCESS  not-accessible
    STATUS      current
    DESCRIPTION 
        "Each row contains the service counters for the Directory Number Hunting service for each group in the system"
    INDEX       { bwDXSDirectoryNumberHuntingGroupIndex }
    ::= { bwDXSDirectoryNumberHuntingGroupTable 1 }

  BwDirectoryNumberHuntingGroupEntry ::= SEQUENCE {
    bwDXSDirectoryNumberHuntingGroupIndex          Unsigned32,
    bwDXSDirectoryNumberHuntingGroupID             DisplayString,
    bwDXSDirectoryNumberHuntingGroupIncomingCalls  Counter32
  }

  bwDXSDirectoryNumberHuntingGroupIndex OBJECT-TYPE
    SYNTAX      Unsigned32
    MAX-ACCESS  read-only
    STATUS      current
    DESCRIPTION 
        "This column represents the index of the Group in the system."
    ::= { bwDXSDirectoryNumberHuntingGroupEntry 1 }

  bwDXSDirectoryNumberHuntingGroupID OBJECT-TYPE
    SYNTAX      DisplayString
    MAX-ACCESS  read-only
    STATUS      current
    DESCRIPTION 
        "This string represents a Group ID."
    ::= { bwDXSDirectoryNumberHuntingGroupEntry 2 }

  bwDXSDirectoryNumberHuntingGroupIncomingCalls OBJECT-TYPE
    SYNTAX      Counter32
    MAX-ACCESS  read-write
    STATUS      current
    DESCRIPTION 
        "This is the number of calls to an agent belonging to Directory Number Hunting groups.  There is one instance of this counter for each group defined in the system."
    ::= { bwDXSDirectoryNumberHuntingGroupEntry 3 }

  bwDXSAoCIncompatibleTariff OBJECT-TYPE
    SYNTAX      Counter32
    MAX-ACCESS  read-write
    STATUS      current
    DESCRIPTION 
        "This is the number of times an active Advice of Charge service receives a tariff update that is incompatible with the current active charge."
    ::= { adviceOfCharge 1 }

  bwDXSAoCIncompatibleAoC OBJECT-TYPE
    SYNTAX      Counter32
    MAX-ACCESS  read-write
    STATUS      current
    DESCRIPTION 
        "This is the number of times an active Advice of charge Service receives an incoming advice of charge body that is incompatible with the current active charge."
    ::= { adviceOfCharge 2 }

  bwDXSAoCUnsupportedCostUnit OBJECT-TYPE
    SYNTAX      Counter32
    MAX-ACCESS  read-write
    STATUS      current
    DESCRIPTION 
        "This is the number of times an active Advice of Charge service receives an unsupported cost-unit in a Cost-Information CCA from the OCS."
    ::= { adviceOfCharge 3 }

  bwDXSAoCActivation OBJECT-TYPE
    SYNTAX      Counter32
    MAX-ACCESS  read-write
    STATUS      current
    DESCRIPTION 
        "This is the number of times an active Advice of Charge service triggers an activation for the next call using the associated FAC."
    ::= { adviceOfCharge 4 }

  bwDXSAoCSPTable OBJECT-TYPE
    SYNTAX      SEQUENCE OF BwAoCSPEntry
    MAX-ACCESS  not-accessible
    STATUS      current
    DESCRIPTION 
        "Each row contains the service counters for the Advice of Charge service for each service provider in the system"
    ::= { adviceOfCharge 5 }

  bwDXSAoCSPEntry OBJECT-TYPE
    SYNTAX      BwAoCSPEntry
    MAX-ACCESS  not-accessible
    STATUS      current
    DESCRIPTION 
        "Each row contains the service counters for the Advice of Charge service for each service provider in the system"
    INDEX       { bwDXSAoCSPIndex }
    ::= { bwDXSAoCSPTable 1 }

  BwAoCSPEntry ::= SEQUENCE {
    bwDXSAoCSPIndex                Unsigned32,
    bwDXSAoCSPID                   DisplayString,
    bwDXSAoCSPIncompatibleTariff   Counter32,
    bwDXSAoCSPIncompatibleAoC      Counter32,
    bwDXSAoCSPActivation           Counter32
  }

  bwDXSAoCSPIndex OBJECT-TYPE
    SYNTAX      Unsigned32
    MAX-ACCESS  read-only
    STATUS      current
    DESCRIPTION 
        "This column represents the index of the Service Provider in the system."
    ::= { bwDXSAoCSPEntry 1 }

  bwDXSAoCSPID OBJECT-TYPE
    SYNTAX      DisplayString
    MAX-ACCESS  read-only
    STATUS      current
    DESCRIPTION 
        "This string represents a Service Provider ID."
    ::= { bwDXSAoCSPEntry 2 }

  bwDXSAoCSPIncompatibleTariff OBJECT-TYPE
    SYNTAX      Counter32
    MAX-ACCESS  read-write
    STATUS      current
    DESCRIPTION 
        "This is the number of times an active Advice of Charge service receives a tariff update that is incompatible with the current active charge within a service provider."
    ::= { bwDXSAoCSPEntry 3 }

  bwDXSAoCSPIncompatibleAoC OBJECT-TYPE
    SYNTAX      Counter32
    MAX-ACCESS  read-write
    STATUS      current
    DESCRIPTION 
        "This is the number of times an active Advice of Charge service receives an incoming advice of charge body that is incompatible with the current active charge within a service provider."
    ::= { bwDXSAoCSPEntry 4 }

  bwDXSAoCSPActivation OBJECT-TYPE
    SYNTAX      Counter32
    MAX-ACCESS  read-write
    STATUS      current
    DESCRIPTION 
        "This is the number of times an active Advice of Charge service triggers an activation for the next call using the associated FAC a service provider or enterprise."
    ::= { bwDXSAoCSPEntry 5 }

  bwDXSAoCGroupTable OBJECT-TYPE
    SYNTAX      SEQUENCE OF BwAoCGroupEntry
    MAX-ACCESS  not-accessible
    STATUS      current
    DESCRIPTION 
        "Each row contains the service counters for the Advice of Charge service for each group in the system"
    ::= { adviceOfCharge 6 }

  bwDXSAoCGroupEntry OBJECT-TYPE
    SYNTAX      BwAoCGroupEntry
    MAX-ACCESS  not-accessible
    STATUS      current
    DESCRIPTION 
        "Each row contains the service counters for the Advice of Charge service for each group in the system"
    INDEX       { bwDXSAoCGroupIndex }
    ::= { bwDXSAoCGroupTable 1 }

  BwAoCGroupEntry ::= SEQUENCE {
    bwDXSAoCGroupIndex                 Unsigned32,
    bwDXSAoCGroupID                    DisplayString,
    bwDXSAoCGroupIncompatibleTariff    Counter32,
    bwDXSAoCGroupIncompatibleAoC       Counter32,
    bwDXSAoCGroupActivation            Counter32
  }

  bwDXSAoCGroupIndex OBJECT-TYPE
    SYNTAX      Unsigned32
    MAX-ACCESS  read-only
    STATUS      current
    DESCRIPTION 
        "This column represents the index of the Group in the system."
    ::= { bwDXSAoCGroupEntry 1 }

  bwDXSAoCGroupID OBJECT-TYPE
    SYNTAX      DisplayString
    MAX-ACCESS  read-only
    STATUS      current
    DESCRIPTION 
        "This string represents a Group ID."
    ::= { bwDXSAoCGroupEntry 2 }

  bwDXSAoCGroupIncompatibleTariff OBJECT-TYPE
    SYNTAX      Counter32
    MAX-ACCESS  read-write
    STATUS      current
    DESCRIPTION 
        "This is the number of times an active Advice of Charge service receives a tariff update that is incompatible with the current active charge within a group."
    ::= { bwDXSAoCGroupEntry 3 }

  bwDXSAoCGroupIncompatibleAoC OBJECT-TYPE
    SYNTAX      Counter32
    MAX-ACCESS  read-write
    STATUS      current
    DESCRIPTION 
        "This is the number of times an active Advice of Charge service receives an incoming advice of charge body that is incompatible with the current active charge within a group."
    ::= { bwDXSAoCGroupEntry 4 }

  bwDXSAoCGroupActivation OBJECT-TYPE
    SYNTAX      Counter32
    MAX-ACCESS  read-write
    STATUS      current
    DESCRIPTION 
        "This is the number of times an active Advice of Charge service triggers an activation for the next call using the associated FAC within a group."
    ::= { bwDXSAoCGroupEntry 5 }

-- Services :: SCCC  ...........................................

  bwDXSSCCCentralization OBJECT-TYPE
    SYNTAX      Counter32
    MAX-ACCESS  read-write
    STATUS      current
    DESCRIPTION 
        "This is the number of successful service centralization calls setup at the Execution Server."
    ::= { serviceCentralizationContinuity 1 }

  bwDXSSCCContinuity OBJECT-TYPE
    SYNTAX      Counter32
    MAX-ACCESS  read-write
    STATUS      current
    DESCRIPTION 
        "This is the number of successful service continuity topology changes at the Execution Server."
    ::= { serviceCentralizationContinuity 2 }

  bwDXSSCCASPSIDNAllocationFailures OBJECT-TYPE
    SYNTAX      Counter32
    MAX-ACCESS  read-write
    STATUS      current
    DESCRIPTION 
        "The number of times SCC AS PSI DN allocation has failed."
    ::= { serviceCentralizationContinuity 3 }

  bwDXSSCCTimeOuts OBJECT-TYPE
    SYNTAX      Counter32
    MAX-ACCESS  read-write
    STATUS      current
    DESCRIPTION 
        "The number of times service centralization and continuity has timed out. "
    ::= { serviceCentralizationContinuity 4 }

  bwDXSSCCASPSIDNMaxUsed OBJECT-TYPE
    SYNTAX      Gauge32
    MAX-ACCESS  read-write
    STATUS      current
    DESCRIPTION 
        "The maximum number number of SCC AS PSI DN used by the system (High Watermark)."
    ::= { serviceCentralizationContinuity 5 }

  bwDXSSCCASPSIDNInUse OBJECT-TYPE
    SYNTAX      Gauge32
    MAX-ACCESS  read-write
    STATUS      current
    DESCRIPTION 
        "This gauge is incremented when an SCC AS PSI DN is allocated and decremented when an SCC AS PSI DN is de-allocated."
    ::= { serviceCentralizationContinuity 6 }

  bwDXSSCCASPSIDNMaxHoldTime OBJECT-TYPE
    SYNTAX      Gauge32
    MAX-ACCESS  read-write
    STATUS      current
    DESCRIPTION 
        "This gauge is updated when an SCC AS PSI DN hold time is greater than the last maximum SCC AS PSI DN hold time.  This is in milliseconds."
    ::= { serviceCentralizationContinuity 7 }

  bwDXSSCCASPSIDNAvgHoldTime OBJECT-TYPE
    SYNTAX      Gauge32
    MAX-ACCESS  read-write
    STATUS      current
    DESCRIPTION 
        "This gauge is computed by adding the total SCC AS PSI DN hold times, up to the last 1,000, and dividing it by the total number of SCC AS PSI DN operations (up to the last 1,000).  This is in milliseconds."
    ::= { serviceCentralizationContinuity 8 }

  bwDXSSCCIMRNCentralization OBJECT-TYPE
    SYNTAX      Counter32
    MAX-ACCESS  read-write
    STATUS      current
    DESCRIPTION
        "This counter tracks the number of successful service centralization and continuity calls (originating or terminating) are set up at the Execution Server by receiving a call to an IP Multimedia Routing Number (IMRN)."
-- @feature:159744
    ::= { serviceCentralizationContinuity 9 }

  bwDXSSCCCSRNCentralization OBJECT-TYPE
    SYNTAX      Counter32
    MAX-ACCESS  read-write
    STATUS      current
    DESCRIPTION
        "This is the number of successful service centralization calls set up at the Execution Server by making a call to a CSRN."
-- @feature:159744
    ::= { serviceCentralizationContinuity 10 }

  bwDXSSCCSTNSRContinuity OBJECT-TYPE
    SYNTAX      Counter32
    MAX-ACCESS  read-write
    STATUS      current
    DESCRIPTION
        "This is the number of successful service continuity topology changes at the Execution Server made after receiving an STN-SR call."
-- @feature:159744
    ::= { serviceCentralizationContinuity 11 }

  bwDXSSCCATUSTIContinuity OBJECT-TYPE
    SYNTAX      Counter32
    MAX-ACCESS  read-write
    STATUS      current
    DESCRIPTION
        "This is the number of successful service continuity topology changes at the Execution Server made after receiving an ATU-STI call."
-- @feature:159744
    ::= { serviceCentralizationContinuity 12 }

  bwDXSSCCIMRNAllocationFailures OBJECT-TYPE
    SYNTAX      Counter32
    MAX-ACCESS  read-write
    STATUS      current
    DESCRIPTION
        "This is the number of times IMRN allocation has failed."
-- @feature:159744
    ::= { serviceCentralizationContinuity 13 }

  bwDXSSCCIMRNTimeOuts OBJECT-TYPE
    SYNTAX      Counter32
    MAX-ACCESS  read-write
    STATUS      current
    DESCRIPTION
        "This is the number of times service centralization using an IMRN has timed out."
-- @feature:159744
    ::= { serviceCentralizationContinuity 14 }

  bwDXSSCCIMRNMaxUsed OBJECT-TYPE
    SYNTAX      Gauge32
    MAX-ACCESS  read-only
    STATUS      current
    DESCRIPTION
        "This is the maximum number of IMRNs used by the system (high watermark)."
-- @feature:159744
    ::= { serviceCentralizationContinuity 15 }

  bwDXSSCCIMRNInUse OBJECT-TYPE
    SYNTAX      Gauge32
    MAX-ACCESS  read-only
    STATUS      current
    DESCRIPTION
        "This gauge is incremented when an IMRN is allocated and decremented when an IMRN is deallocated."
-- @feature:159744
    ::= { serviceCentralizationContinuity 16 }

  bwDXSSCCIMRNMaxHoldTime OBJECT-TYPE
    SYNTAX      Gauge32
    MAX-ACCESS  read-only
    STATUS      current
    DESCRIPTION
        "This gauge is updated when an IMRN hold time is greater than the last maximum IMRN hold time.  This is in milliseconds."
-- @feature:159744
    ::= { serviceCentralizationContinuity 17 }

  bwDXSSCCIMRNAvgHoldTime OBJECT-TYPE
    SYNTAX      Gauge32
    MAX-ACCESS  read-only
    STATUS      current
    DESCRIPTION
        "This gauge is computed by adding the total IMRN hold times, up to the last 1,000, and dividing it by the total number of IMRN operations (up to the last 1,000).  This is in milliseconds."
-- @feature:159744
    ::= { serviceCentralizationContinuity 18 }

  bwDXSSCCEarlyReleaseTimeOut OBJECT-TYPE
    SYNTAX      Counter32
    MAX-ACCESS  read-write
    STATUS      current
    DESCRIPTION
        "This counter tracks the number of times the service centralization and continuity times out early, which is the number of times the Execution Server receives the release from the packed switched (network) leg without receiving the INVITE to the Session Transfer Number - Single Radio (STN-SR)."
-- @feature:181047
    ::= { serviceCentralizationContinuity 19 }

-- Service : CallLogs  ...........................................

  bwDXSCallLogEventInstanceTable OBJECT-TYPE
     SYNTAX      SEQUENCE  OF  BwDXSCallLogEventInstanceEntry
     MAX-ACCESS  not-accessible
     STATUS      current
     DESCRIPTION "Each row contains the number of occurence of a call log event."
-- @feature:117143
     ::= { callLogQueue 1 }

   bwDXSCallLogEventInstanceEntry OBJECT-TYPE
     SYNTAX      BwDXSCallLogEventInstanceEntry
     MAX-ACCESS  not-accessible
     STATUS      current
     DESCRIPTION
         "Each row contains the number of occurence of a call log event."
     INDEX { bwDXSCallLogSchemaInstanceIndex }
-- @feature:117143
     ::= { bwDXSCallLogEventInstanceTable 1 }

   BwDXSCallLogEventInstanceEntry ::= SEQUENCE {
     bwDXSCallLogSchemaInstanceIndex  Unsigned32,
     bwDXSCallLogSchemaInstanceName   DisplayString,
     bwDXSCallLogEventsReported       Counter32,
     bwDXSCallLogEventsIgnored        Counter32,
     bwDXSCallLogEventsFailed         Counter32,
     bwDXSCallLogDatabaseInserts      Counter32,
     bwDXSCallLogDatabaseUpdates      Counter32,
     bwDXSCallLogDatabaseQueries      Counter32,
     bwDXSCallLogDatabaseDeletes      Counter32,
     bwDXSCallLogDatabaseFailures     Counter32 }

  bwDXSCallLogSchemaInstanceIndex OBJECT-TYPE
     SYNTAX       Unsigned32
     MAX-ACCESS   read-only
     STATUS       current
     DESCRIPTION  
         "This is the index of the Call Log event table entry."
-- @feature:117143
     ::= { bwDXSCallLogEventInstanceEntry 1 }

  bwDXSCallLogSchemaInstanceName OBJECT-TYPE
     SYNTAX       DisplayString
     MAX-ACCESS   read-only
     STATUS       current
     DESCRIPTION  
         "This displays the instance schema name of the call log event table entry."
-- @feature:117143
     ::= { bwDXSCallLogEventInstanceEntry 2 }

  bwDXSCallLogEventsReported OBJECT-TYPE
     SYNTAX      Counter32
     MAX-ACCESS  read-write
     STATUS      current
     DESCRIPTION
         "This counter represents the number of call log events reported by the Enhanced Call Logs service regardless of type.  Note that more specific counters can also be incremented."
-- @feature:117143
     ::= { bwDXSCallLogEventInstanceEntry 3 }
 
  bwDXSCallLogEventsIgnored OBJECT-TYPE
     SYNTAX      Counter32
     MAX-ACCESS  read-write
     STATUS      current
     DESCRIPTION
         "This counter represents the number of call log events reported by the Enhanced Call Logs service, which are ignored.  While events are not generally ignored, certain situations cause this to occur.  One example is when enhanced call log events are being reported but no database has been configured to receive the reported data."
-- @feature:117143
     ::= { bwDXSCallLogEventInstanceEntry 4 }

  bwDXSCallLogEventsFailed OBJECT-TYPE
     SYNTAX      Counter32
     MAX-ACCESS  read-write
     STATUS      current
     DESCRIPTION
         "This counter represents the number of call log events reported by the Enhanced Call Logs service, which failed to be recorded in the database.  One example of a failure is when events are reported while the database connection is down."
-- @feature:117143
     ::= { bwDXSCallLogEventInstanceEntry 5 }

  bwDXSCallLogDatabaseInserts OBJECT-TYPE
     SYNTAX      Counter32
     MAX-ACCESS  read-write
     STATUS      current
     DESCRIPTION
         "This counter represents the number of database insert operations performed while recording data reported by the Enhanced Call Logs service."
-- @feature:117143
     ::= { bwDXSCallLogEventInstanceEntry 6 }

  bwDXSCallLogDatabaseUpdates OBJECT-TYPE
     SYNTAX      Counter32
     MAX-ACCESS  read-write
     STATUS      current
     DESCRIPTION
         "This counter represents the number of database update operations performed while recording data reported by the Enhanced Call Logs service."
-- @feature:117143
     ::= { bwDXSCallLogEventInstanceEntry 7 }

  bwDXSCallLogDatabaseQueries OBJECT-TYPE
     SYNTAX      Counter32
     MAX-ACCESS  read-write
     STATUS      current
     DESCRIPTION
         "This counter represents the number of database select operations performed while recording data reported by the Enhanced Call Logs service."
-- @feature:117143
     ::= { bwDXSCallLogEventInstanceEntry 8 }

  bwDXSCallLogDatabaseDeletes OBJECT-TYPE
     SYNTAX      Counter32
     MAX-ACCESS  read-write
     STATUS      current
     DESCRIPTION
         "This counter represents the number of database delete operations performed while recording data reported by the Enhanced Call Logs service."
-- @feature:117143
     ::= { bwDXSCallLogEventInstanceEntry 9 }

  bwDXSCallLogDatabaseFailures OBJECT-TYPE
     SYNTAX      Counter32
     MAX-ACCESS  read-write
     STATUS      current
     DESCRIPTION
         "This counter represents the number of database failures that have occurred while recording data reported by the Enhanced Call Logs service."
-- @feature:117143
     ::= { bwDXSCallLogEventInstanceEntry 10 }

  bwDXSCallLogEventResets OBJECT-TYPE
     SYNTAX      Counter32
     MAX-ACCESS  read-write
     STATUS      current
     DESCRIPTION
         "When set to a value other than 0, all event statistics stored in the callLogEventTable are reset to 0."
-- @feature:117143
     ::= { callLogQueue 2 }

   bwDXSCallLogEventTable OBJECT-TYPE
     SYNTAX      SEQUENCE  OF  BwDXSCallLogEventEntry
     MAX-ACCESS  not-accessible
     STATUS      current
     DESCRIPTION "Each row contains the number of occurence of a call log event."
-- @feature:117143
     ::= { callLogQueue 3 }

   bwDXSCallLogEventEntry OBJECT-TYPE
     SYNTAX      BwDXSCallLogEventEntry
     MAX-ACCESS  not-accessible
     STATUS      current
     DESCRIPTION
         "Each row contains the number of occurence of a call log event."
     INDEX { bwDXSCallLogEventIndex }
-- @feature:117143
     ::= { bwDXSCallLogEventTable 1 }

   BwDXSCallLogEventEntry ::= SEQUENCE {
     bwDXSCallLogEventIndex  Unsigned32,
     bwDXSCallLogSchemaName  DisplayString,
     bwDXSCallLogEventName   DisplayString,
     bwDXSCallLogEventCount  Counter32 }

  bwDXSCallLogEventIndex OBJECT-TYPE
     SYNTAX       Unsigned32
     MAX-ACCESS   read-only
     STATUS       current
     DESCRIPTION  
         "This is the index of the queue event table entry."
-- @feature:117143
     ::= { bwDXSCallLogEventEntry 1 }

  bwDXSCallLogEventName OBJECT-TYPE
     SYNTAX       DisplayString
     MAX-ACCESS   read-only
     STATUS       current
     DESCRIPTION  
         "This displays the name of the call log event table entry."
-- @feature:117143
     ::= { bwDXSCallLogEventEntry 2 }

  bwDXSCallLogSchemaName OBJECT-TYPE
     SYNTAX       DisplayString
     MAX-ACCESS   read-only
     STATUS       current
     DESCRIPTION  
         "This displays the instance schema name of the call log event table entry."
-- @feature:117143
     ::= { bwDXSCallLogEventEntry 3 }

  bwDXSCallLogEventCount OBJECT-TYPE
     SYNTAX       Counter32
     MAX-ACCESS   read-write
     STATUS       current
     DESCRIPTION  
         "This displays the number of events reported for the specific event table entry."
-- @feature:117143
     ::= { bwDXSCallLogEventEntry 4 }

  bwDXSCallLogProcessorResets OBJECT-TYPE
     SYNTAX      Gauge32
     MAX-ACCESS  read-write
     STATUS      current
     DESCRIPTION
         "When set to a value other than '0', all processor statistics stored in the callLogProcessorTable are reset to '0'."
-- @feature:117143
     ::= { callLogProcessors 1 }
 
   bwDXSCallLogProcessorTable OBJECT-TYPE
     SYNTAX      SEQUENCE  OF  BwDXSCallLogProcessorEntry
     MAX-ACCESS  not-accessible
     STATUS      current
     DESCRIPTION "Each row contains the number of occurence of a call log processor."
-- @feature:117143
     ::= { callLogProcessors 2 }
 
   bwDXSCallLogProcessorEntry OBJECT-TYPE
     SYNTAX      BwDXSCallLogProcessorEntry
     MAX-ACCESS  not-accessible
     STATUS      current
     DESCRIPTION
         "Each row contains the number of occurence of a call log processor."
     INDEX { bwDXSCallLogProcessorIndex }
-- @feature:117143
     ::= { bwDXSCallLogProcessorTable 1 }
 
   BwDXSCallLogProcessorEntry ::= SEQUENCE {
     bwDXSCallLogProcessorIndex       Unsigned32,
     bwDXSCallLogProcessorSchemaName  DisplayString,
     bwDXSCallLogProcessorId          DisplayString,
     bwDXSCallLogProcessorEventCount  Counter32 }
 
  bwDXSCallLogProcessorIndex OBJECT-TYPE
     SYNTAX       Unsigned32
     MAX-ACCESS   read-only
     STATUS       current
     DESCRIPTION  
         "This is the index of the processor table entry."
-- @feature:117143
     ::= { bwDXSCallLogProcessorEntry 1 }
 
  bwDXSCallLogProcessorSchemaName OBJECT-TYPE
     SYNTAX       DisplayString
     MAX-ACCESS   read-only
     STATUS       current
     DESCRIPTION  
         "This displays the instance schema name of the call log processor table entry."
-- @feature:117143
     ::= { bwDXSCallLogProcessorEntry 2 }

  bwDXSCallLogProcessorId OBJECT-TYPE
     SYNTAX       DisplayString
     MAX-ACCESS   read-only
     STATUS       current
     DESCRIPTION  
         "This displays the processor instance Id of the call log processor table entry."
-- @feature:117143
     ::= { bwDXSCallLogProcessorEntry 3 }

  bwDXSCallLogProcessorEventCount OBJECT-TYPE
     SYNTAX       Counter32
     MAX-ACCESS   read-write
     STATUS       current
     DESCRIPTION  
         "This is the number of events committed to the database by the processor table entry."
-- @feature:117143
     ::= { bwDXSCallLogProcessorEntry 4 }

-- Services :: externalCustomRingback  ...........................................

  bwDXSExternalCustomRingbackAttempts OBJECT-TYPE
    SYNTAX      Counter32
    MAX-ACCESS  read-write
    STATUS      current
    DESCRIPTION 
        "This is the number of attempts made to play ringback from an external custom ringback source."
-- @feature:159646
    ::= { externalCustomRingback 1 }

  bwDXSExternalCustomRingbackFailures OBJECT-TYPE
    SYNTAX      Counter32
    MAX-ACCESS  read-write
    STATUS      current
    DESCRIPTION 
        "This is the number of times an attempt to play ringback from an external custom ringback source failed due to timeout or error."
-- @feature:159646
    ::= { externalCustomRingback 2 }

  bwDXSExternalCustomRingbackSPTable OBJECT-TYPE
    SYNTAX      SEQUENCE OF BwDXSExternalCustomRingbackSPEntry
    MAX-ACCESS  not-accessible
    STATUS      current
    DESCRIPTION 
        "Each row contains the service counters for the External Custom Ringback service for each service provider in the system"
-- @feature:159646
    ::= { externalCustomRingback 3 }

  bwDXSExternalCustomRingbackSPEntry OBJECT-TYPE
    SYNTAX      BwDXSExternalCustomRingbackSPEntry
    MAX-ACCESS  not-accessible
    STATUS      current
    DESCRIPTION 
        "Each row contains the service counters for the External Custom Ringback service for each service provider in the system"
    INDEX       { bwDXSExternalCustomRingbackSPIndex }
 -- @feature:159646
   ::= { bwDXSExternalCustomRingbackSPTable 1 }

  BwDXSExternalCustomRingbackSPEntry ::= SEQUENCE {
    bwDXSExternalCustomRingbackSPIndex    Unsigned32,
    bwDXSExternalCustomRingbackSPID       DisplayString,
    bwDXSExternalCustomRingbackSPAttempts Counter32,
    bwDXSExternalCustomRingbackSPFailures Counter32
  }

  bwDXSExternalCustomRingbackSPIndex OBJECT-TYPE
    SYNTAX      Unsigned32
    MAX-ACCESS  read-only
    STATUS      current
    DESCRIPTION 
        "This column represents the index of the Service Provider in the system."
-- @feature:159646
    ::= { bwDXSExternalCustomRingbackSPEntry 1 }

  bwDXSExternalCustomRingbackSPID OBJECT-TYPE
    SYNTAX      DisplayString
    MAX-ACCESS  read-only
    STATUS      current
    DESCRIPTION 
        "This string represents a Service Provider ID."
-- @feature:159646
    ::= { bwDXSExternalCustomRingbackSPEntry 2 }

  bwDXSExternalCustomRingbackSPAttempts OBJECT-TYPE
    SYNTAX      Counter32
    MAX-ACCESS  read-write
    STATUS      current
    DESCRIPTION 
        "This is the number of attempts made to play ringback from an external custom ringback source for a given service provider."
-- @feature:159646
    ::= { bwDXSExternalCustomRingbackSPEntry 3 }

  bwDXSExternalCustomRingbackSPFailures OBJECT-TYPE
    SYNTAX      Counter32
    MAX-ACCESS  read-write
    STATUS      current
    DESCRIPTION 
        "This is the number of times an attempt to play ringback from an external custom ringback source failed due to timeout or error for a given service provider."
-- @feature:159646
    ::= { bwDXSExternalCustomRingbackSPEntry 4 }

  bwDXSExternalCustomRingbackGroupTable OBJECT-TYPE
    SYNTAX      SEQUENCE OF BwDXSExternalCustomRingbackGroupEntry
    MAX-ACCESS  not-accessible
    STATUS      current
    DESCRIPTION 
        "Each row contains the service counters for the External Custom Ringback service for each group in the system"
-- @feature:159646
    ::= { externalCustomRingback 4 }

  bwDXSExternalCustomRingbackGroupEntry OBJECT-TYPE
    SYNTAX      BwDXSExternalCustomRingbackGroupEntry
    MAX-ACCESS  not-accessible
    STATUS      current
    DESCRIPTION 
        "Each row contains the service counters for the External Custome Ringback service for each group in the system"
    INDEX       { bwDXSExternalCustomRingbackGroupIndex }
-- @feature:159646
    ::= { bwDXSExternalCustomRingbackGroupTable 1 }

  BwDXSExternalCustomRingbackGroupEntry ::= SEQUENCE {
    bwDXSExternalCustomRingbackGroupIndex    Unsigned32,
    bwDXSExternalCustomRingbackGroupID       DisplayString,
    bwDXSExternalCustomRingbackGroupAttempts Counter32,
    bwDXSExternalCustomRingbackGroupFailures Counter32
  }

  bwDXSExternalCustomRingbackGroupIndex OBJECT-TYPE
    SYNTAX      Unsigned32
    MAX-ACCESS  read-only
    STATUS      current
    DESCRIPTION 
        "This column represents the index of the Group in the system."
-- @feature:159646
    ::= { bwDXSExternalCustomRingbackGroupEntry 1 }

  bwDXSExternalCustomRingbackGroupID OBJECT-TYPE
    SYNTAX      DisplayString
    MAX-ACCESS  read-only
    STATUS      current
    DESCRIPTION 
        "This string represents a Group ID."
-- @feature:159646
    ::= { bwDXSExternalCustomRingbackGroupEntry 2 }

  bwDXSExternalCustomRingbackGroupAttempts OBJECT-TYPE
    SYNTAX      Counter32
    MAX-ACCESS  read-write
    STATUS      current
    DESCRIPTION 
        "This is the number of attempts made to play ringback from an external custom ringback source for a given group."
-- @feature:159646
    ::= { bwDXSExternalCustomRingbackGroupEntry 3 }

  bwDXSExternalCustomRingbackGroupFailures OBJECT-TYPE
    SYNTAX      Counter32
    MAX-ACCESS  read-write
    STATUS      current
    DESCRIPTION 
        "This is the number of times an attempt to play ringback from an external custom ringback source failed due to timeout or error for a given group."
-- @feature:159646
    ::= { bwDXSExternalCustomRingbackGroupEntry 4 }

-- Services :: callForwardingGroupNotReachable  ...........................................

  bwDXSCFGNRcForward OBJECT-TYPE
    SYNTAX      Counter32
    MAX-ACCESS  read-write
    STATUS      current
    DESCRIPTION 
        "The number of times Call Forwarding Group Not Reachable has forwarded the call to the external destination."
-- @feature:170958
    ::= { callForwardingGroupNotReachable 1 }

  bwDXSCFGNRcNoForward OBJECT-TYPE
    SYNTAX      Counter32
    MAX-ACCESS  read-write
    STATUS      current
    DESCRIPTION 
        "The number of times Call Forwarding Group Not Reachable fails to forward the call."
-- @feature:170958
    ::= { callForwardingGroupNotReachable 2 }

  bwDXSCFGNRcSPTable OBJECT-TYPE
    SYNTAX      SEQUENCE OF BwDXSCFGNRcSPEntry
    MAX-ACCESS  not-accessible
    STATUS      current
    DESCRIPTION 
        "Each row contains the service counters for the Call Forwarding Not Reachable service for each service provider in the system"
-- @feature:170958
    ::= { callForwardingGroupNotReachable 3 }

  bwDXSCFGNRcSPEntry OBJECT-TYPE
    SYNTAX      BwDXSCFGNRcSPEntry
    MAX-ACCESS  not-accessible
    STATUS      current
    DESCRIPTION 
        "Each row contains the service counters for the Call Forwarding Not Reachable service for each service provider in the system"
    INDEX       { bwDXSCFGNRcSPIndex }
 -- @feature:170958
   ::= { bwDXSCFGNRcSPTable 1 }

  BwDXSCFGNRcSPEntry ::= SEQUENCE {
    bwDXSCFGNRcSPIndex     Unsigned32,
    bwDXSCFGNRcSPID        DisplayString,
    bwDXSCFGNRcSPForward   Counter32,
    bwDXSCFGNRcSPNoForward Counter32
  }

  bwDXSCFGNRcSPIndex OBJECT-TYPE
    SYNTAX      Unsigned32
    MAX-ACCESS  read-only
    STATUS      current
    DESCRIPTION 
        "This column represents the index of the Service Provider in the system."
-- @feature:170958
    ::= { bwDXSCFGNRcSPEntry 1 }

  bwDXSCFGNRcSPID OBJECT-TYPE
    SYNTAX      DisplayString
    MAX-ACCESS  read-only
    STATUS      current
    DESCRIPTION 
        "This string represents a Service Provider ID."
-- @feature:170958
    ::= { bwDXSCFGNRcSPEntry 2 }

  bwDXSCFGNRcSPForward OBJECT-TYPE
    SYNTAX      Counter32
    MAX-ACCESS  read-write
    STATUS      current
    DESCRIPTION 
        "The number of times Call Forwarding Group Not Reachable has forwarded the call to the external destination.  There is one instance of this counter for each service provider defined on the system."
-- @feature:170958
    ::= { bwDXSCFGNRcSPEntry 3 }

  bwDXSCFGNRcSPNoForward OBJECT-TYPE
    SYNTAX      Counter32
    MAX-ACCESS  read-write
    STATUS      current
    DESCRIPTION 
        "The number of times Call Forwarding Group Not Reachable fails to forward the call.  There is one instance of this counter for each service provider defined on the system."
-- @feature:170958
    ::= { bwDXSCFGNRcSPEntry 4 }

  bwDXSCFGNRcGroupTable OBJECT-TYPE
    SYNTAX      SEQUENCE OF BwDXSCFGNRcGroupEntry
    MAX-ACCESS  not-accessible
    STATUS      current
    DESCRIPTION 
        "Each row contains the service counters for the Call Forwarding Not Reachable service for each group in the system"
-- @feature:170958
    ::= { callForwardingGroupNotReachable 4 }

  bwDXSCFGNRcGroupEntry OBJECT-TYPE
    SYNTAX      BwDXSCFGNRcGroupEntry
    MAX-ACCESS  not-accessible
    STATUS      current
    DESCRIPTION 
        "Each row contains the service counters for the Call Forwarding Not Reachable service for each group in the system"
    INDEX       { bwDXSCFGNRcGroupIndex }
 -- @feature:170958
   ::= { bwDXSCFGNRcGroupTable 1 }

  BwDXSCFGNRcGroupEntry ::= SEQUENCE {
    bwDXSCFGNRcGroupIndex     Unsigned32,
    bwDXSCFGNRcGroupID        DisplayString,
    bwDXSCFGNRcGroupForward   Counter32,
    bwDXSCFGNRcGroupNoForward Counter32
  }

  bwDXSCFGNRcGroupIndex OBJECT-TYPE
    SYNTAX      Unsigned32
    MAX-ACCESS  read-only
    STATUS      current
    DESCRIPTION 
        "This column represents the index of the group in the system."
-- @feature:170958
    ::= { bwDXSCFGNRcGroupEntry 1 }

  bwDXSCFGNRcGroupID OBJECT-TYPE
    SYNTAX      DisplayString
    MAX-ACCESS  read-only
    STATUS      current
    DESCRIPTION 
        "This string represents a Group ID."
-- @feature:170958
    ::= { bwDXSCFGNRcGroupEntry 2 }

  bwDXSCFGNRcGroupForward OBJECT-TYPE
    SYNTAX      Counter32
    MAX-ACCESS  read-write
    STATUS      current
    DESCRIPTION 
        "The number of times Call Forwarding Group Not Reachable has forwarded the call to the external destination.  There is one instance of this counter for each group defined on the system."
-- @feature:170958
    ::= { bwDXSCFGNRcGroupEntry 3 }

  bwDXSCFGNRcGroupNoForward OBJECT-TYPE
    SYNTAX      Counter32
    MAX-ACCESS  read-write
    STATUS      current
    DESCRIPTION 
        "The number of times Call Forwarding Group Not Reachable fails to forward the call.  There is one instance of this counter for each group defined on the system."
-- @feature:170958
    ::= { bwDXSCFGNRcGroupEntry 4 }

-- Services :: groupNightForwarding  ...........................................

  bwDXSGroupNightForwardingNumInvocations OBJECT-TYPE
    SYNTAX      Counter32
    MAX-ACCESS  read-write
    STATUS      current
    DESCRIPTION 
        "This is the number of times that the Group Night Forwarding service has redirected a call."
-- @feature:213830
    ::= { groupNightForwarding 1 }

  bwDXSGroupNightForwardingSPTable OBJECT-TYPE
    SYNTAX      SEQUENCE OF BwDXSGroupNightForwardingSPEntry
    MAX-ACCESS  not-accessible
    STATUS      current
    DESCRIPTION 
        "Each row contains the service counters for the Group Night Forwarding service for each service provider in the system"
-- @feature:213830
    ::= { groupNightForwarding 2 }

  bwDXSGroupNightForwardingSPEntry OBJECT-TYPE
    SYNTAX      BwDXSGroupNightForwardingSPEntry
    MAX-ACCESS  not-accessible
    STATUS      current
    DESCRIPTION 
        "Each row contains the service counters for the Group Night Forwarding service for each service provider in the system"
    INDEX       { bwDXSGroupNightForwardingSPIndex }
 -- @feature:213830
   ::= { bwDXSGroupNightForwardingSPTable 1 }

  BwDXSGroupNightForwardingSPEntry ::= SEQUENCE {
    bwDXSGroupNightForwardingSPIndex          Unsigned32,
    bwDXSGroupNightForwardingSPID             DisplayString,
    bwDXSGroupNightForwardingSPNumInvocations Counter32
  }

  bwDXSGroupNightForwardingSPIndex OBJECT-TYPE
    SYNTAX      Unsigned32
    MAX-ACCESS  read-only
    STATUS      current
    DESCRIPTION 
        "This column represents the index of the Service Provider in the system."
-- @feature:213830
    ::= { bwDXSGroupNightForwardingSPEntry 1 }

  bwDXSGroupNightForwardingSPID OBJECT-TYPE
    SYNTAX      DisplayString
    MAX-ACCESS  read-only
    STATUS      current
    DESCRIPTION 
        "This string represents a Service Provider ID."
-- @feature:213830
    ::= { bwDXSGroupNightForwardingSPEntry 2 }

  bwDXSGroupNightForwardingSPNumInvocations OBJECT-TYPE
    SYNTAX      Counter32
    MAX-ACCESS  read-write
    STATUS      current
    DESCRIPTION 
        "This is the number of times that the Group Night Forwarding service has redirected a call.  There is one instance of this counter for each service provider defined in the system."
-- @feature:213830
    ::= { bwDXSGroupNightForwardingSPEntry 3 }

  bwDXSGroupNightForwardingGroupTable OBJECT-TYPE
    SYNTAX      SEQUENCE OF BwDXSGroupNightForwardingGroupEntry
    MAX-ACCESS  not-accessible
    STATUS      current
    DESCRIPTION 
        "Each row contains the service counters for the Group Night Forwarding service for each group in the system"
-- @feature:213830
    ::= { groupNightForwarding 3 }

  bwDXSGroupNightForwardingGroupEntry OBJECT-TYPE
    SYNTAX      BwDXSGroupNightForwardingGroupEntry
    MAX-ACCESS  not-accessible
    STATUS      current
    DESCRIPTION 
        "Each row contains the service counters for the Group Night Forwarding service for each group in the system"
    INDEX       { bwDXSGroupNightForwardingGroupIndex }
 -- @feature:213830
   ::= { bwDXSGroupNightForwardingGroupTable 1 }

  BwDXSGroupNightForwardingGroupEntry ::= SEQUENCE {
    bwDXSGroupNightForwardingGroupIndex          Unsigned32,
    bwDXSGroupNightForwardingGroupID             DisplayString,
    bwDXSGroupNightForwardingGroupNumInvocations Counter32
  }

  bwDXSGroupNightForwardingGroupIndex OBJECT-TYPE
    SYNTAX      Unsigned32
    MAX-ACCESS  read-only
    STATUS      current
    DESCRIPTION 
        "This column represents the index of the group in the system."
-- @feature:213830
    ::= { bwDXSGroupNightForwardingGroupEntry 1 }

  bwDXSGroupNightForwardingGroupID OBJECT-TYPE
    SYNTAX      DisplayString
    MAX-ACCESS  read-only
    STATUS      current
    DESCRIPTION 
        "This string represents a Group ID."
-- @feature:213830
    ::= { bwDXSGroupNightForwardingGroupEntry 2 }

  bwDXSGroupNightForwardingGroupNumInvocations OBJECT-TYPE
    SYNTAX      Counter32
    MAX-ACCESS  read-write
    STATUS      current
    DESCRIPTION 
        "This is the number of times that the Group Night Forwarding service has redirected a call.  There is one instance of this counter for each group defined in the system."
-- @feature:213830
    ::= { bwDXSGroupNightForwardingGroupEntry 3 }

-- Services :: preAlertingAnnouncement  ...........................................

  bwDXSPreAlertingAnnouncementNumAttempts OBJECT-TYPE
    SYNTAX      Counter32
    MAX-ACCESS  read-write
    STATUS      current
    DESCRIPTION 
        "This counter tracks the number of times that pre-alerting announcements are attempted."
-- @feature:213842
    ::= { preAlertingAnnouncement 1 }

-- Services :: SP preAlertingAnnouncement  ...........................................

bwDXSPreAlertingAnnouncementSPTable OBJECT-TYPE
    SYNTAX      SEQUENCE OF BwDXSPreAlertingAnnouncementSPEntry
    MAX-ACCESS  not-accessible
    STATUS      current
    DESCRIPTION 
        "Each row contains the service counters for the Pre-Alerting Announcement service for each service provider in the system"
-- @feature:213842
    ::= { preAlertingAnnouncement 2 }

  bwDXSPreAlertingAnnouncementSPEntry OBJECT-TYPE
    SYNTAX      BwDXSPreAlertingAnnouncementSPEntry
    MAX-ACCESS  not-accessible
    STATUS      current
    DESCRIPTION 
        "Each row contains the service counters for the Pre Alerting Announcement service for each service provider in the system"
    INDEX       { bwDXSPreAlertingAnnouncementSPIndex }
 -- @feature:213842
   ::= { bwDXSPreAlertingAnnouncementSPTable 1 }

  BwDXSPreAlertingAnnouncementSPEntry ::= SEQUENCE {
    bwDXSPreAlertingAnnouncementSPIndex          Unsigned32,
    bwDXSPreAlertingAnnouncementSPID             DisplayString,
    bwDXSPreAlertingAnnouncementSPNumAttempts    Counter32
  }

  bwDXSPreAlertingAnnouncementSPIndex OBJECT-TYPE
    SYNTAX      Unsigned32
    MAX-ACCESS  read-only
    STATUS      current
    DESCRIPTION 
        "This column represents the index of the Service Provider in the system."
-- @feature:213842
    ::= { bwDXSPreAlertingAnnouncementSPEntry 1 }

  bwDXSPreAlertingAnnouncementSPID OBJECT-TYPE
    SYNTAX      DisplayString
    MAX-ACCESS  read-only
    STATUS      current
    DESCRIPTION 
        "This string represents a Service Provider ID."
-- @feature:213842
    ::= { bwDXSPreAlertingAnnouncementSPEntry 2 }

  bwDXSPreAlertingAnnouncementSPNumAttempts OBJECT-TYPE
    SYNTAX      Counter32
    MAX-ACCESS  read-write
    STATUS      current
    DESCRIPTION 
        "This counter tracks the number of pre-alerting announcements for users in a given service provider."
-- @feature:213842
    ::= { bwDXSPreAlertingAnnouncementSPEntry 3 }

-- Services :: Group preAlertingAnnouncement  ...........................................

  bwDXSPreAlertingAnnouncementGroupTable OBJECT-TYPE
    SYNTAX      SEQUENCE OF BwDXSPreAlertingAnnouncementGroupEntry
    MAX-ACCESS  not-accessible
    STATUS      current
    DESCRIPTION 
        "Each row contains the service counters for the Pre Alerting Announcement service for each group in the system"
-- @feature:213842
    ::= { preAlertingAnnouncement 3 }

  bwDXSPreAlertingAnnouncementGroupEntry OBJECT-TYPE
    SYNTAX      BwDXSPreAlertingAnnouncementGroupEntry
    MAX-ACCESS  not-accessible
    STATUS      current
    DESCRIPTION 
        "Each row contains the service counters for the Pre Alerting Announcement service for each group in the system"
    INDEX       { bwDXSPreAlertingAnnouncementGroupIndex }
 -- @feature:213842
   ::= { bwDXSPreAlertingAnnouncementGroupTable 1 }

  BwDXSPreAlertingAnnouncementGroupEntry ::= SEQUENCE {
    bwDXSPreAlertingAnnouncementGroupIndex          Unsigned32,
    bwDXSPreAlertingAnnouncementGroupID             DisplayString,
    bwDXSPreAlertingAnnouncementGroupNumAttempts    Counter32
  }

  bwDXSPreAlertingAnnouncementGroupIndex OBJECT-TYPE
    SYNTAX      Unsigned32
    MAX-ACCESS  read-only
    STATUS      current
    DESCRIPTION 
        "This column represents the index of the group in the system."
-- @feature:213842
    ::= { bwDXSPreAlertingAnnouncementGroupEntry 1 }

  bwDXSPreAlertingAnnouncementGroupID OBJECT-TYPE
    SYNTAX      DisplayString
    MAX-ACCESS  read-only
    STATUS      current
    DESCRIPTION 
        "This string represents a Group ID."
-- @feature:213842
    ::= { bwDXSPreAlertingAnnouncementGroupEntry 2 }

  bwDXSPreAlertingAnnouncementGroupNumAttempts OBJECT-TYPE
    SYNTAX      Counter32
    MAX-ACCESS  read-write
    STATUS      current
    DESCRIPTION 
        "This counter tracks the number of pre-alerting announcements for user in a given group."
-- @feature:213842
    ::= { bwDXSPreAlertingAnnouncementGroupEntry 3 }

-- Services :: Hoteling  ...........................................

  bwDXSHotelingAssociate OBJECT-TYPE
    SYNTAX      Counter32
    MAX-ACCESS  read-write
    STATUS      current
    DESCRIPTION 
        "This counter tracks each time a guest/host association is created."
-- @feature:213841
    ::= { hoteling 1 }

  bwDXSHotelingDisassociate OBJECT-TYPE
    SYNTAX      Counter32
    MAX-ACCESS  read-write
    STATUS      current
    DESCRIPTION 
        "This counter tracks each time a guest/host association is removed."
-- @feature:213841
    ::= { hoteling 2 }

  bwDXSHotelingTimeout OBJECT-TYPE
    SYNTAX      Counter32
    MAX-ACCESS  read-write
    STATUS      current
    DESCRIPTION 
        "This counter tracks each time a guest/host association is removed due to a timeout."
-- @feature:213841
    ::= { hoteling 3 }

-- Services :: SP hoteling  ...........................................

bwDXSHotelingSPTable OBJECT-TYPE
    SYNTAX      SEQUENCE OF BwDXSHotelingSPEntry
    MAX-ACCESS  not-accessible
    STATUS      current
    DESCRIPTION 
        "Each row contains the service counters for the Hoteling service for each service provider in the system"
-- @feature:213841
    ::= { hoteling 4 }

  bwDXSHotelingSPEntry OBJECT-TYPE
    SYNTAX      BwDXSHotelingSPEntry
    MAX-ACCESS  not-accessible
    STATUS      current
    DESCRIPTION 
        "Each row contains the service counters for the Hoteling service for each service provider in the system"
    INDEX       { bwDXSHotelingSPIndex }
 -- @feature:213841
   ::= { bwDXSHotelingSPTable 1 }

  BwDXSHotelingSPEntry ::= SEQUENCE {
    bwDXSHotelingSPIndex          Unsigned32,
    bwDXSHotelingSPID             DisplayString,
    bwDXSHotelingSPAssociate      Counter32,
    bwDXSHotelingSPDisassociate   Counter32,
    bwDXSHotelingSPTimeout        Counter32
  }

  bwDXSHotelingSPIndex OBJECT-TYPE
    SYNTAX      Unsigned32
    MAX-ACCESS  read-only
    STATUS      current
    DESCRIPTION 
        "This column represents the index of the Service Provider in the system."
-- @feature:213841
    ::= { bwDXSHotelingSPEntry 1 }

  bwDXSHotelingSPID OBJECT-TYPE
    SYNTAX      DisplayString
    MAX-ACCESS  read-only
    STATUS      current
    DESCRIPTION 
        "This string represents a Service Provider ID."
-- @feature:213841
    ::= { bwDXSHotelingSPEntry 2 }

  bwDXSHotelingSPAssociate OBJECT-TYPE
    SYNTAX      Counter32
    MAX-ACCESS  read-write
    STATUS      current
    DESCRIPTION 
        "This counter tracks each time a guest/host association is created, per service provider"
-- @feature:213841
    ::= { bwDXSHotelingSPEntry 3 }

  bwDXSHotelingSPDisassociate OBJECT-TYPE
    SYNTAX      Counter32
    MAX-ACCESS  read-write
    STATUS      current
    DESCRIPTION 
        "This counter tracks each time a guest/host association is removed, per service provider."
-- @feature:213841
    ::= { bwDXSHotelingSPEntry 4 }

  bwDXSHotelingSPTimeout OBJECT-TYPE
    SYNTAX      Counter32
    MAX-ACCESS  read-write
    STATUS      current
    DESCRIPTION 
        "This counter tracks each time a guest/host association is removed due to a timeout, per service provider."
-- @feature:213841
    ::= { bwDXSHotelingSPEntry 5 }

-- Services :: Group hoteling  ...........................................

  bwDXSHotelingGroupTable OBJECT-TYPE
    SYNTAX      SEQUENCE OF BwDXSHotelingGroupEntry
    MAX-ACCESS  not-accessible
    STATUS      current
    DESCRIPTION 
        "Each row contains the service counters for the Hoteling service for each group in the system"
-- @feature:213842
    ::= { hoteling 5 }

  bwDXSHotelingGroupEntry OBJECT-TYPE
    SYNTAX      BwDXSHotelingGroupEntry
    MAX-ACCESS  not-accessible
    STATUS      current
    DESCRIPTION 
        "Each row contains the service counters for the Hoteling service for each group in the system"
    INDEX       { bwDXSHotelingGroupIndex }
 -- @feature:213842
   ::= { bwDXSHotelingGroupTable 1 }

  BwDXSHotelingGroupEntry ::= SEQUENCE {
    bwDXSHotelingGroupIndex          Unsigned32,
    bwDXSHotelingGroupID             DisplayString,
    bwDXSHotelingGroupAssociate      Counter32,
    bwDXSHotelingGroupDisassociate   Counter32,
    bwDXSHotelingGroupTimeout        Counter32
  }

  bwDXSHotelingGroupIndex OBJECT-TYPE
    SYNTAX      Unsigned32
    MAX-ACCESS  read-only
    STATUS      current
    DESCRIPTION 
        "This column represents the index of the group in the system."
-- @feature:213842
    ::= { bwDXSHotelingGroupEntry 1 }

  bwDXSHotelingGroupID OBJECT-TYPE
    SYNTAX      DisplayString
    MAX-ACCESS  read-only
    STATUS      current
    DESCRIPTION 
        "This string represents a Group ID."
-- @feature:213842
    ::= { bwDXSHotelingGroupEntry 2 }

  bwDXSHotelingGroupAssociate OBJECT-TYPE
    SYNTAX      Counter32
    MAX-ACCESS  read-write
    STATUS      current
    DESCRIPTION 
        "This counter tracks each time a guest/host association is created, per group."
-- @feature:213841
    ::= { bwDXSHotelingGroupEntry 3 }

  bwDXSHotelingGroupDisassociate OBJECT-TYPE
    SYNTAX      Counter32
    MAX-ACCESS  read-write
    STATUS      current
    DESCRIPTION 
        "This counter tracks each time a guest/host association is removed, per group."
-- @feature:213841
    ::= { bwDXSHotelingGroupEntry 4 }

  bwDXSHotelingGroupTimeout OBJECT-TYPE
    SYNTAX      Counter32
    MAX-ACCESS  read-write
    STATUS      current
    DESCRIPTION 
        "This counter tracks each time a guest/host association is removed due to a timeout, per group."
-- @feature:213841
    ::= { bwDXSHotelingGroupEntry 5 }

-- Protocol :: MSS  ...........................................

  bwDXSNSqueryRequestsTransmitted OBJECT-TYPE
    SYNTAX      Counter32
    MAX-ACCESS  read-write
    STATUS      current
    DESCRIPTION
        "incremented each time a Media Server selection query transmission is attempted toward a Network Server"
    ::= { mssStats 1 }

  bwDXSNSqueryCommFailures OBJECT-TYPE
    SYNTAX      Counter32
    MAX-ACCESS  read-write
    STATUS      current
    DESCRIPTION
        "This counter is incremented when Media Server selection query has been transmitted toward all available Network Servers and no response has been received from any Network Server."
    ::= { mssStats 3 }

-- Protocol :: NRS  ...........................................

  bwDXSNbInvalidMessagesReceived OBJECT-TYPE
    SYNTAX      Counter32
    MAX-ACCESS  read-write
    STATUS      current
    DESCRIPTION 
        "This counter is incremented when an invalid NRS message is received (either the header was valid but the body was not, or the message was pure junk)"
    ::= { nrsStats 6 }

  bwDXSNbRequestsReceived OBJECT-TYPE
    SYNTAX      Counter32
    MAX-ACCESS  read-write
    STATUS      current
    DESCRIPTION 
        "This counter is incremented when a NRS request is received"
    ::= { nrsStats 7 }

  bwDXSNbResponsesReceived OBJECT-TYPE
    SYNTAX      Counter32
    MAX-ACCESS  read-write
    STATUS      current
    DESCRIPTION 
        "This counter is incremented when a NRS response is received"
    ::= { nrsStats 8 }

  bwDXSNbErrorsReceived OBJECT-TYPE
    SYNTAX      Counter32
    MAX-ACCESS  read-write
    STATUS      current
    DESCRIPTION 
        "This counter is incremented when a NRS error is received"
    ::= { nrsStats 9 }

  bwDXSNbRequestsSent OBJECT-TYPE
    SYNTAX      Counter32
    MAX-ACCESS  read-write
    STATUS      current
    DESCRIPTION 
        "This counter is incremented when a NRS request is sent"
    ::= { nrsStats 10 }

  bwDXSNbResponsesSent OBJECT-TYPE
    SYNTAX      Counter32
    MAX-ACCESS  read-write
    STATUS      current
    DESCRIPTION 
        "This counter is incremented when a NRS response is sent"
    ::= { nrsStats 11 }

  bwDXSNbErrorsSent OBJECT-TYPE
    SYNTAX      Counter32
    MAX-ACCESS  read-write
    STATUS      current
    DESCRIPTION 
        "This counter is incremented when a NRS error is sent"
    ::= { nrsStats 12 }

  bwDXSNbRequestsResent OBJECT-TYPE
    SYNTAX      Counter32
    MAX-ACCESS  read-write
    STATUS      current
    DESCRIPTION 
        "This counter is incremented when a NRS request is re-sent"
    ::= { nrsStats 13 }

  bwDXSNbResponsesResent OBJECT-TYPE
    SYNTAX      Counter32
    MAX-ACCESS  read-write
    STATUS      current
    DESCRIPTION 
        "This counter is incremented when a NRS response is re-sent"
    ::= { nrsStats 14 }

  bwDXSNbRequestsUnanswered OBJECT-TYPE
    SYNTAX      Counter32
    MAX-ACCESS  read-write
    STATUS      current
    DESCRIPTION 
        "This counter is incremented when a NRS request remains unanswered after a series of retries"
    ::= { nrsStats 15 }

  bwDXSNRSStatsTable OBJECT-TYPE
    SYNTAX      SEQUENCE OF BwNRSStatsEntry
    MAX-ACCESS  not-accessible
    STATUS      current
    DESCRIPTION 
        "This table contains the counters for all NRS protocols"
    ::= { nrsStats 16 }

  bwDXSNRSStatsEntry OBJECT-TYPE
    SYNTAX      BwNRSStatsEntry
    MAX-ACCESS  not-accessible
    STATUS      current
    DESCRIPTION 
        "This row contains information on a particular NRS protocol"
    INDEX       { bwDXSNRSStatsTableIndex }
    ::= { bwDXSNRSStatsTable 1 }

  BwNRSStatsEntry ::= SEQUENCE {
    bwDXSNRSStatsTableIndex                    Unsigned32,
    bwDXSNRSStatsTableProtocolName             DisplayString,
    bwDXSNRSStatsTableNbRequestsReceived       Counter32,
    bwDXSNRSStatsTableNbResponsesReceived      Counter32,
    bwDXSNRSStatsTableNbErrorsReceived         Counter32,
    bwDXSNRSStatsTableNbRequestsSent           Counter32,
    bwDXSNRSStatsTableNbResponsesSent          Counter32,
    bwDXSNRSStatsTableNbErrorsSent             Counter32,
    bwDXSNRSStatsTableNbRequestsResent         Counter32,
    bwDXSNRSStatsTableNbResponsesResent        Counter32,
    bwDXSNRSStatsTableNbRequestsUnanswered     Counter32
  }

  bwDXSNRSStatsTableIndex OBJECT-TYPE
    SYNTAX      Unsigned32
    MAX-ACCESS  not-accessible
    STATUS      current
    DESCRIPTION 
        "This integer represents a NRS protocol status code.  The rest of the information in this row is related to this value."
    ::= { bwDXSNRSStatsEntry 1 }

  bwDXSNRSStatsTableProtocolName OBJECT-TYPE
    SYNTAX      DisplayString
    MAX-ACCESS  read-only
    STATUS      current
    DESCRIPTION 
        "This string represents the NRS protocol name"
    ::= { bwDXSNRSStatsEntry 2 }

  bwDXSNRSStatsTableNbRequestsReceived OBJECT-TYPE
    SYNTAX      Counter32
    MAX-ACCESS  read-write
    STATUS      current
    DESCRIPTION 
        "This counter is incremented when a request is received"
    ::= { bwDXSNRSStatsEntry 3 }

  bwDXSNRSStatsTableNbResponsesReceived OBJECT-TYPE
    SYNTAX      Counter32
    MAX-ACCESS  read-write
    STATUS      current
    DESCRIPTION 
        "This counter is incremented when a response is received"
    ::= { bwDXSNRSStatsEntry 4 }

  bwDXSNRSStatsTableNbErrorsReceived OBJECT-TYPE
    SYNTAX      Counter32
    MAX-ACCESS  read-write
    STATUS      current
    DESCRIPTION 
        "This counter is incremented when an error is received"
    ::= { bwDXSNRSStatsEntry 5 }

  bwDXSNRSStatsTableNbRequestsSent OBJECT-TYPE
    SYNTAX      Counter32
    MAX-ACCESS  read-write
    STATUS      current
    DESCRIPTION 
        "This counter is incremented when a request is sent"
    ::= { bwDXSNRSStatsEntry 6 }

  bwDXSNRSStatsTableNbResponsesSent OBJECT-TYPE
    SYNTAX      Counter32
    MAX-ACCESS  read-write
    STATUS      current
    DESCRIPTION 
        "This counter is incremented when a response is sent"
    ::= { bwDXSNRSStatsEntry 7 }

  bwDXSNRSStatsTableNbErrorsSent OBJECT-TYPE
    SYNTAX      Counter32
    MAX-ACCESS  read-write
    STATUS      current
    DESCRIPTION 
        "This counter is incremented when an error is sent"
    ::= { bwDXSNRSStatsEntry 8 }

  bwDXSNRSStatsTableNbRequestsResent OBJECT-TYPE
    SYNTAX      Counter32
    MAX-ACCESS  read-write
    STATUS      current
    DESCRIPTION 
        "This counter is incremented when a request is re-sent"
    ::= { bwDXSNRSStatsEntry 9 }

  bwDXSNRSStatsTableNbResponsesResent OBJECT-TYPE
    SYNTAX      Counter32
    MAX-ACCESS  read-write
    STATUS      current
    DESCRIPTION 
        "This counter is incremented when a response is re-sent"
    ::= { bwDXSNRSStatsEntry 10 }

  bwDXSNRSStatsTableNbRequestsUnanswered OBJECT-TYPE
    SYNTAX      Counter32
    MAX-ACCESS  read-write
    STATUS      current
    DESCRIPTION 
        "This counter is incremented when a request remains unanswered after a series of retries"
    ::= { bwDXSNRSStatsEntry 11 }

-- Protocol :: Protocol Monitor  ...........................................

  bwDXSPMTNumMonitorsCreated OBJECT-TYPE
    SYNTAX      Counter32
    MAX-ACCESS  read-write
    STATUS      current
    DESCRIPTION 
        "This counter is incremented when a monitor is created"
    ::= { pmtStats 1 }

  bwDXSPMTNumMonitorsOpen OBJECT-TYPE
    SYNTAX      Gauge32
    MAX-ACCESS  read-only
    STATUS      current
    DESCRIPTION 
        "Number of open monitors in the system"
    ::= { pmtStats 2 }

  bwDXSPMTNumLoggerCreated OBJECT-TYPE
    SYNTAX      Counter32
    MAX-ACCESS  read-write
    STATUS      current
    DESCRIPTION 
        "This counter is incremented when a logger registers"
    ::= { pmtStats 3 }

  bwDXSPMTNumLoggerOpen OBJECT-TYPE
    SYNTAX      Gauge32
    MAX-ACCESS  read-only
    STATUS      current
    DESCRIPTION 
        "The number of loggers registered in the system"
    ::= { pmtStats 4 }

-- system statistics ...........................................

internalStats OBJECT IDENTIFIER
    ::= { systemModule 2 }

  bwDXSSystemInternalQueueResets OBJECT-TYPE
    SYNTAX      Counter32
    MAX-ACCESS  read-write
    STATUS      current
    DESCRIPTION 
        "When set to a value other then 0, all the internal queue statistic stored under bwDXSSystemInternalQueueTable are reset to 0."
    ::= { internalStats 1 }

  bwDXSSystemInternalQueueTable OBJECT-TYPE
    SYNTAX      SEQUENCE OF BwSystemInternalQueueEntry
    MAX-ACCESS  not-accessible
    STATUS      current
    DESCRIPTION 
        "This table contains statistics about the BroadWorks internal queues"
    ::= { internalStats 2 }

  bwDXSSystemInternalQueueEntry OBJECT-TYPE
    SYNTAX      BwSystemInternalQueueEntry
    MAX-ACCESS  not-accessible
    STATUS      current
    DESCRIPTION 
        "This row contains the statistics for a given internal queue in the system"
    INDEX       { bwDXSSystemInternalQueueIndex }
    ::= { bwDXSSystemInternalQueueTable 1 }

  BwSystemInternalQueueEntry ::= SEQUENCE {
    bwDXSSystemInternalQueueIndex                  Unsigned32,
    bwDXSSystemInternalQueueName                   DisplayString,
    bwDXSSystemInternalQueueSize                   Counter32,
    bwDXSSystemInternalQueueTimeAvg                Gauge32,
    bwDXSSystemInternalQueueTimeMin                Gauge32,
    bwDXSSystemInternalQueueTimeMax                Gauge32,
    bwDXSSystemInternalQueueLengthCurrent          Gauge32,
    bwDXSSystemInternalQueueLengthAvg              Gauge32,
    bwDXSSystemInternalQueueLengthMax              Gauge32,
    bwDXSSystemInternalQueueTimeMaxTimestampMSB    Gauge32,
    bwDXSSystemInternalQueueLengthMaxTimestampMSB  Gauge32,
    bwDXSSystemInternalQueueLengthMaxTimestampLSB  Gauge32,
    bwDXSSystemInternalQueueTimeMaxTimestampLSB    Gauge32
  }

  bwDXSSystemInternalQueueIndex OBJECT-TYPE
    SYNTAX      Unsigned32
    MAX-ACCESS  read-only
    STATUS      current
    DESCRIPTION 
        "This integer represents an index to an internal queue in the system."
    ::= { bwDXSSystemInternalQueueEntry 1 }

  bwDXSSystemInternalQueueName OBJECT-TYPE
    SYNTAX      DisplayString
    MAX-ACCESS  read-only
    STATUS      current
    DESCRIPTION 
        "This string represents the name of an internal queue."
    ::= { bwDXSSystemInternalQueueEntry 2 }

  bwDXSSystemInternalQueueSize OBJECT-TYPE
    SYNTAX      Counter32
    MAX-ACCESS  read-only
    STATUS      current
    DESCRIPTION 
        "The number of sample elements that the average, minimum and maximum holding time were calculated from."
    ::= { bwDXSSystemInternalQueueEntry 3 }

  bwDXSSystemInternalQueueTimeAvg OBJECT-TYPE
    SYNTAX      Gauge32
    MAX-ACCESS  read-only
    STATUS      current
    DESCRIPTION 
        "The average queue holding time. Note that this value is in 1/1000 of millisec, i.e. divide by 1000 to get the value in milliseconds."
    ::= { bwDXSSystemInternalQueueEntry 4 }

  bwDXSSystemInternalQueueTimeMin OBJECT-TYPE
    SYNTAX      Gauge32
    MAX-ACCESS  read-only
    STATUS      current
    DESCRIPTION 
        "The smallest queue sample holding time."
    ::= { bwDXSSystemInternalQueueEntry 5 }

  bwDXSSystemInternalQueueTimeMax OBJECT-TYPE
    SYNTAX      Gauge32
    MAX-ACCESS  read-only
    STATUS      current
    DESCRIPTION 
        "The biggest queue sample holding time."
    ::= { bwDXSSystemInternalQueueEntry 6 }

  bwDXSSystemInternalQueueLengthCurrent OBJECT-TYPE
    SYNTAX      Gauge32
    MAX-ACCESS  read-only
    STATUS      current
    DESCRIPTION 
        "The number of elements currently hold in the queue."
    ::= { bwDXSSystemInternalQueueEntry 8 }

  bwDXSSystemInternalQueueLengthAvg OBJECT-TYPE
    SYNTAX      Gauge32
    MAX-ACCESS  read-only
    STATUS      current
    DESCRIPTION 
        "The average number of elements simultaneously held in the queue multiple by 1000. Divide by 1000 to get the value in units."
    ::= { bwDXSSystemInternalQueueEntry 9 }

  bwDXSSystemInternalQueueLengthMax OBJECT-TYPE
    SYNTAX      Gauge32
    MAX-ACCESS  read-only
    STATUS      current
    DESCRIPTION 
        "The maximum number of elements simultaneously held in the queue multiple by 1000. Divide by 1000 to get the value in units."
    ::= { bwDXSSystemInternalQueueEntry 10 }

  bwDXSSystemInternalQueueTimeMaxTimestampMSB OBJECT-TYPE
    SYNTAX      Gauge32
    MAX-ACCESS  read-only
    STATUS      current
    DESCRIPTION 
        "The most significant part of the timestamp (4 most significant bytes) of when bwDXSSystemInternalQueueTimeMax was obtained."
    ::= { bwDXSSystemInternalQueueEntry 12 }

  bwDXSSystemInternalQueueLengthMaxTimestampMSB OBJECT-TYPE
    SYNTAX      Gauge32
    MAX-ACCESS  read-only
    STATUS      current
    DESCRIPTION 
        "The most significant part of the timestamp (4 most significant bytes) of when bwDXSSystemInternalQueueLengthMax was obtained."
    ::= { bwDXSSystemInternalQueueEntry 13 }

  bwDXSSystemInternalQueueLengthMaxTimestampLSB OBJECT-TYPE
    SYNTAX      Gauge32
    MAX-ACCESS  read-only
    STATUS      current
    DESCRIPTION 
        "The least significant part of the timestamp (4 least significant bytes) of when bwDXSSystemInternalQueueLengthMax was obtained."
    ::= { bwDXSSystemInternalQueueEntry 14 }

  bwDXSSystemInternalQueueTimeMaxTimestampLSB OBJECT-TYPE
    SYNTAX      Gauge32
    MAX-ACCESS  read-only
    STATUS      current
    DESCRIPTION 
        "The least significant part of the timestamp (4 least significant bytes) of when bwDXSSystemInternalQueueTimeMax was obtained."
    ::= { bwDXSSystemInternalQueueEntry 15 }

overloadStats OBJECT IDENTIFIER
    ::= { systemModule 3 }

  bwDXSCurrentCallOverloadZone OBJECT-TYPE
    SYNTAX      DisplayString
    MAX-ACCESS  read-only
    STATUS      current
    DESCRIPTION 
        "The current call related overload zone. Value is a string indicating Green, Yellow, or Red."
    ::= { overloadStats 4 }

  bwDXSNumCallYellowZoneOverloadTrans OBJECT-TYPE
    SYNTAX      Counter32
    MAX-ACCESS  read-write
    STATUS      current
    DESCRIPTION 
        "The number of times that the server has transitioned to the call related yellow overload zone."
    ::= { overloadStats 5 }

  bwDXSNumCallRedZoneOverloadTrans OBJECT-TYPE
    SYNTAX      Counter32
    MAX-ACCESS  read-write
    STATUS      current
    DESCRIPTION 
        "The number of times that the server has transitioned to the call related red overload zone."
    ::= { overloadStats 6 }

  bwDXSCurrentNonCallOverloadZone OBJECT-TYPE
    SYNTAX      DisplayString
    MAX-ACCESS  read-only
    STATUS      current
    DESCRIPTION 
        "The current non-call related overload zone. Value is a string indicating Green, Yellow, or Red."
    ::= { overloadStats 7 }

  bwDXSNumNonCallYellowZoneOverloadTrans OBJECT-TYPE
    SYNTAX      Counter32
    MAX-ACCESS  read-write
    STATUS      current
    DESCRIPTION 
        "The number of times that the server has transitioned to the non-call related yellow overload zone."
    ::= { overloadStats 8 }

  bwDXSNumNonCallRedZoneOverloadTrans OBJECT-TYPE
    SYNTAX      Counter32
    MAX-ACCESS  read-write
    STATUS      current
    DESCRIPTION 
        "The number of times that the server has transitioned to the non-call related red overload zone."
    ::= { overloadStats 9 }

  bwDXSNumDiscardedMessage OBJECT-TYPE
    SYNTAX      Counter32
    MAX-ACCESS  read-write
    STATUS      current
    DESCRIPTION 
        "The number of messages that were dropped from the SIP or MGCP decoder queues."
    ::= { overloadStats 10 }

  bwDXSTimeLastDiscardedMessage OBJECT-TYPE
    SYNTAX      DisplayString
    MAX-ACCESS  read-write
    STATUS      current
    DESCRIPTION 
        "The last time a message was dropped from the SIP or MGCP decoded queues."
    ::= { overloadStats 11 }

  bwDXSMemoryHighWaterMark OBJECT-TYPE
    SYNTAX      Gauge32
    MAX-ACCESS  read-only
    STATUS      current
    DESCRIPTION 
        "The high water mark for the heap size."
    ::= { overloadStats 12 }

  bwDXSMemoryHighWaterMarkTimeMSB OBJECT-TYPE
    SYNTAX      Gauge32
    MAX-ACCESS  read-only
    STATUS      current
    DESCRIPTION 
        "The most significant part of the timestamp (4 most significant bytes) of when bwDXSMemoryHighWaterMark was obtained."
    ::= { overloadStats 13 }

  bwDXSMemoryHighWaterMarkTimeLSB OBJECT-TYPE
    SYNTAX      Gauge32
    MAX-ACCESS  read-only
    STATUS      current
    DESCRIPTION 
        "The least significant part of the timestamp (4 least significant bytes) of when bwDXSMemoryHighWaterMark was obtained."
    ::= { overloadStats 14 }

  bwDXSOverloadStatsReset OBJECT-TYPE
    SYNTAX      Counter32
    MAX-ACCESS  read-write
    STATUS      current
    DESCRIPTION 
        "When set to a value other then 0, all the statistics stored under bwDXSOverloadSampledDelayTable are reset to 0."
    ::= { overloadStats 15 }

  bwDXSOverloadStatsTable  OBJECT-TYPE
    SYNTAX      SEQUENCE OF BwOverloadStatsEntry
    MAX-ACCESS  not-accessible
    STATUS      current
    DESCRIPTION 
        "This table contains statistics about overload"
    ::= { overloadStats 16 }

  bwDXSOverloadStatsEntry OBJECT-TYPE
    SYNTAX      BwOverloadStatsEntry
    MAX-ACCESS  not-accessible
    STATUS      current
    DESCRIPTION 
        "This row contains the statistics for a given overload sampled in the system"
    INDEX       { bwDXSOverloadSampledDataIndex }
    ::= { bwDXSOverloadStatsTable 1 }

  BwOverloadStatsEntry ::= SEQUENCE {
    bwDXSOverloadSampledDataIndex               Unsigned32,
    bwDXSOverloadSampledDataName                DisplayString,
    bwDXSOverloadSampledDelayMin                Gauge32,
    bwDXSOverloadSampledDelayAvg                Gauge32,
    bwDXSOverloadSampledDelayMax                Gauge32,
    bwDXSOverloadSampledDelayMaxTimeMSB         Gauge32,
    bwDXSOverloadSampledDelayMaxTimeLSB         Gauge32,
    bwDXSOverloadNumSamples                     Gauge32
  }

  bwDXSOverloadSampledDataIndex OBJECT-TYPE
    SYNTAX      Unsigned32
    MAX-ACCESS  read-only
    STATUS      current
    DESCRIPTION 
        "This integer represents an index to an overload sample in the system."
    ::= { bwDXSOverloadStatsEntry 1 }

  bwDXSOverloadSampledDataName OBJECT-TYPE
    SYNTAX      DisplayString
    MAX-ACCESS  read-only
    STATUS      current
    DESCRIPTION 
        "This string represents the name of an overload sample."
    ::= { bwDXSOverloadStatsEntry 2 }

  bwDXSOverloadSampledDelayMin OBJECT-TYPE
    SYNTAX      Gauge32
    MAX-ACCESS  read-only
    STATUS      current
    DESCRIPTION 
        "This is the minimum sampled delay in milliseconds."
    ::= { bwDXSOverloadStatsEntry 3 }

  bwDXSOverloadSampledDelayAvg OBJECT-TYPE
    SYNTAX      Gauge32
    MAX-ACCESS  read-only
    STATUS      current
    DESCRIPTION 
        "This is the average sampled delay in microseconds."
    ::= { bwDXSOverloadStatsEntry 4 }

  bwDXSOverloadSampledDelayMax OBJECT-TYPE
    SYNTAX      Gauge32
    MAX-ACCESS  read-only
    STATUS      current
    DESCRIPTION 
        "This is the maximum sampled delay in milliseconds."
    ::= { bwDXSOverloadStatsEntry 5 }

  bwDXSOverloadSampledDelayMaxTimeMSB OBJECT-TYPE
    SYNTAX      Gauge32
    MAX-ACCESS  read-only
    STATUS      current
    DESCRIPTION 
        "The most significant part of the timestamp (4 most significant bytes) of when bwDXSOverloadSampledDelayMax was obtained."
    ::= { bwDXSOverloadStatsEntry 6 }

  bwDXSOverloadSampledDelayMaxTimeLSB OBJECT-TYPE
    SYNTAX      Gauge32
    MAX-ACCESS  read-only
    STATUS      current
    DESCRIPTION 
        "The least significant part of the timestamp (4 least significant bytes) of when bwDXSOverloadSampledDelayMax was obtained."
    ::= { bwDXSOverloadStatsEntry 7 }

  bwDXSOverloadNumSamples OBJECT-TYPE
    SYNTAX      Gauge32
    MAX-ACCESS  read-only
    STATUS      current
    DESCRIPTION 
        "The total number of overload samples processed."
    ::= { bwDXSOverloadStatsEntry 8 }

-- Management module ...........................................

  resetAllCounters OBJECT-TYPE
    SYNTAX      Counter32
    MAX-ACCESS  read-write
    STATUS      current
    DESCRIPTION "When set to a value other then 0, all the counters in the system are reset to 0."
    ::= { management 1 }

-- Diameter .................

  bwDXSInternalXSTransactionTable OBJECT-TYPE
    SYNTAX      SEQUENCE OF BwInternalXSTransactionEntry
    MAX-ACCESS  not-accessible
    STATUS      current
    DESCRIPTION 
        "This table contains statistics about the Diameter Stack internal transactions."
    ::= { diameterStats 1 }

  bwDXSInternalXSTransactionEntry OBJECT-TYPE
    SYNTAX      BwInternalXSTransactionEntry
    MAX-ACCESS  not-accessible
    STATUS      current
    DESCRIPTION 
        "This row contains the statistics for a given internal Diameter transaction."
    INDEX       { bwDXSInternalXSDiameterCommandCode }
    ::= { bwDXSInternalXSTransactionTable 1 }

  BwInternalXSTransactionEntry ::= SEQUENCE {
    bwDXSInternalXSDiameterCommandCode             Unsigned32,
    bwDXSInternalXSDiameterRequestsOut             Counter32,
    bwDXSInternalXSDiameterInformationalAnswersIn  Counter32,
    bwDXSInternalXSDiameterSuccessAnswersIn        Counter32,
    bwDXSInternalXSDiameterFailureAnswersIn        Counter32,
    bwDXSInternalXSDiameterRequestTimeouts         Counter32,
    bwDXSInternalXSDiameterRequestsIn              Counter32,
    bwDXSInternalXSDiameterInformationalAnswersOut Counter32,
    bwDXSInternalXSDiameterSuccessAnswersOut       Counter32,
    bwDXSInternalXSDiameterFailureAnswersOut       Counter32
  }

  bwDXSInternalXSDiameterCommandCode OBJECT-TYPE
    SYNTAX      Unsigned32
    MAX-ACCESS  read-only
    STATUS      current
    DESCRIPTION 
        "This is the Diameter message's command-code which indexes this table."
    ::= { bwDXSInternalXSTransactionEntry 1 }

  bwDXSInternalXSDiameterRequestsOut OBJECT-TYPE
    SYNTAX      Counter32
    MAX-ACCESS  read-only
    STATUS      current
    DESCRIPTION 
        "This is the number of request sent by the Diameter Stack. This includes both initial transmissions and retransmissions of the same request."
    ::= { bwDXSInternalXSTransactionEntry 2 }

  bwDXSInternalXSDiameterInformationalAnswersIn OBJECT-TYPE
    SYNTAX      Counter32
    MAX-ACCESS  read-only
    STATUS      current
    DESCRIPTION 
        "This is the number of answers containing an informational Result-Code (value 1xxx)."
    ::= { bwDXSInternalXSTransactionEntry 3 }

  bwDXSInternalXSDiameterSuccessAnswersIn OBJECT-TYPE
    SYNTAX      Counter32
    MAX-ACCESS  read-only
    STATUS      current
    DESCRIPTION 
        "This is the number of answers containing a successful Result-Code (value 2xxx)."
    ::= { bwDXSInternalXSTransactionEntry 4 }

  bwDXSInternalXSDiameterFailureAnswersIn OBJECT-TYPE
    SYNTAX      Counter32
    MAX-ACCESS  read-only
    STATUS      current
    DESCRIPTION 
        "This is the number of answers containing a failure Result-Code or Experimental-Result (value >= 3000), malformed answers or answers not matching any outstanding request. Malformed answers have inappropriate Diameter message header values or do not contain any Result-Code or Experimental-Result AVPs."
    ::= { bwDXSInternalXSTransactionEntry 5 }

  bwDXSInternalXSDiameterRequestTimeouts OBJECT-TYPE
    SYNTAX      Counter32
    MAX-ACCESS  read-only
    STATUS      current
    DESCRIPTION 
        "This is the number of requests for which no response has been received within the specified timeout. The timeout value is application-dependent. If an answer is received afterward, it is treated as an unmatched answer and the bwDXSDiameterStatsFailureAnswersIn is incremented."
    ::= { bwDXSInternalXSTransactionEntry 6 }

  bwDXSInternalXSDiameterRequestsIn OBJECT-TYPE
    SYNTAX      Counter32
    MAX-ACCESS  read-only
    STATUS      current
    DESCRIPTION 
        "This is the number of received requests on the corresponding Diameter stack instance."
    ::= { bwDXSInternalXSTransactionEntry 7 }

  bwDXSInternalXSDiameterInformationalAnswersOut OBJECT-TYPE
    SYNTAX      Counter32
    MAX-ACCESS  read-only
    STATUS      current
    DESCRIPTION 
        "This is the number of informational answers (Result-Code value = 1xxx) sent by the corresponding Diameter stack instance."
    ::= { bwDXSInternalXSTransactionEntry 8 }

  bwDXSInternalXSDiameterSuccessAnswersOut OBJECT-TYPE
    SYNTAX      Counter32
    MAX-ACCESS  read-only
    STATUS      current
    DESCRIPTION 
        "This is the number of successful answers (Result-Code value = 2xxx) sent by the corresponding Diameter stack instance."
    ::= { bwDXSInternalXSTransactionEntry 9 }

  bwDXSInternalXSDiameterFailureAnswersOut OBJECT-TYPE
    SYNTAX      Counter32
    MAX-ACCESS  read-only
    STATUS      current
    DESCRIPTION 
        "This is the number of failure answers (Result-Code/Experimental-Result-Code value >= 3000) sent by the corresponding Diameter stack instance."
    ::= { bwDXSInternalXSTransactionEntry 10 }

  bwDXSExternalXSTransactionTable OBJECT-TYPE
    SYNTAX      SEQUENCE OF BwExternalXSTransactionEntry
    MAX-ACCESS  not-accessible
    STATUS      current
    DESCRIPTION 
        "This table contains statistics about the Diameter Stack external transactions."
    ::= { diameterStats 2 }

  bwDXSExternalXSTransactionEntry OBJECT-TYPE
    SYNTAX      BwExternalXSTransactionEntry
    MAX-ACCESS  not-accessible
    STATUS      current
    DESCRIPTION 
        "This row contains the statistics for a given external Diameter transaction."
    INDEX       { bwDXSExternalXSDiameterCommandCode }
    ::= { bwDXSExternalXSTransactionTable 1 }

  BwExternalXSTransactionEntry ::= SEQUENCE {
    bwDXSExternalXSDiameterCommandCode             Unsigned32,
    bwDXSExternalXSDiameterRequestsOut             Counter32,
    bwDXSExternalXSDiameterInformationalAnswersIn  Counter32,
    bwDXSExternalXSDiameterSuccessAnswersIn        Counter32,
    bwDXSExternalXSDiameterFailureAnswersIn        Counter32,
    bwDXSExternalXSDiameterRequestTimeouts         Counter32,
    bwDXSExternalXSDiameterRequestsIn              Counter32,
    bwDXSExternalXSDiameterInformationalAnswersOut Counter32,
    bwDXSExternalXSDiameterSuccessAnswersOut       Counter32,
    bwDXSExternalXSDiameterFailureAnswersOut       Counter32
  }

  bwDXSExternalXSDiameterCommandCode OBJECT-TYPE
    SYNTAX      Unsigned32
    MAX-ACCESS  read-only
    STATUS      current
    DESCRIPTION 
        "This is the Diameter message's command-code which indexes this table."
    ::= { bwDXSExternalXSTransactionEntry 1 }

  bwDXSExternalXSDiameterRequestsOut OBJECT-TYPE
    SYNTAX      Counter32
    MAX-ACCESS  read-only
    STATUS      current
    DESCRIPTION 
        "This is the number of request sent by the Diameter Stack. This includes both initial transmissions and retransmissions of the same request."
    ::= { bwDXSExternalXSTransactionEntry 2 }

  bwDXSExternalXSDiameterInformationalAnswersIn OBJECT-TYPE
    SYNTAX      Counter32
    MAX-ACCESS  read-only
    STATUS      current
    DESCRIPTION 
        "This is the number of answers containing an informational Result-Code (value 1xxx)."
    ::= { bwDXSExternalXSTransactionEntry 3 }

  bwDXSExternalXSDiameterSuccessAnswersIn OBJECT-TYPE
    SYNTAX      Counter32
    MAX-ACCESS  read-only
    STATUS      current
    DESCRIPTION 
        "This is the number of answers containing a successful Result-Code (value 2xxx)."
    ::= { bwDXSExternalXSTransactionEntry 4 }

  bwDXSExternalXSDiameterFailureAnswersIn OBJECT-TYPE
    SYNTAX      Counter32
    MAX-ACCESS  read-only
    STATUS      current
    DESCRIPTION 
        "This is the number of answers containing a failure Result-Code or Experimental-Result (value >= 3000), malformed answers or answers not matching any outstanding request. Malformed answers have inappropriate Diameter message header values or do not contain any Result-Code or Experimental-Result AVPs."
    ::= { bwDXSExternalXSTransactionEntry 5 }

  bwDXSExternalXSDiameterRequestTimeouts OBJECT-TYPE
    SYNTAX      Counter32
    MAX-ACCESS  read-only
    STATUS      current
    DESCRIPTION 
        "This is the number of requests for which no response has been received within the specified timeout. The timeout value is application-dependent. If an answer is received afterward, it is treated as an unmatched answer and the bwDXSDiameterStatsFailureAnswersIn is incremented."
    ::= { bwDXSExternalXSTransactionEntry 6 }

  bwDXSExternalXSDiameterRequestsIn OBJECT-TYPE
    SYNTAX      Counter32
    MAX-ACCESS  read-only
    STATUS      current
    DESCRIPTION 
        "This is the number of received requests on the corresponding Diameter stack instance."
    ::= { bwDXSExternalXSTransactionEntry 7 }

  bwDXSExternalXSDiameterInformationalAnswersOut OBJECT-TYPE
    SYNTAX      Counter32
    MAX-ACCESS  read-only
    STATUS      current
    DESCRIPTION 
        "This is the number of informational answers (Result-Code value = 1xxx) sent by the corresponding Diameter stack instance."
    ::= { bwDXSExternalXSTransactionEntry 8 }

  bwDXSExternalXSDiameterSuccessAnswersOut OBJECT-TYPE
    SYNTAX      Counter32
    MAX-ACCESS  read-only
    STATUS      current
    DESCRIPTION 
        "This is the number of successful answers (Result-Code value = 2xxx) sent by the corresponding Diameter stack instance."
    ::= { bwDXSExternalXSTransactionEntry 9 }

  bwDXSExternalXSDiameterFailureAnswersOut OBJECT-TYPE
    SYNTAX      Counter32
    MAX-ACCESS  read-only
    STATUS      current
    DESCRIPTION 
        "This is the number of failure answers (Result-Code/Experimental-Result-Code value >= 3000) sent by the corresponding Diameter stack instance."
    ::= { bwDXSExternalXSTransactionEntry 10 }

-- SH Relay Interface ......................

  bwDXSShRelayInterfaceServerUnreachable OBJECT-TYPE
    SYNTAX      Counter32
    MAX-ACCESS  read-only
    STATUS      current
    DESCRIPTION 
        "This is the number of Sh requests not sent by the XS Sh Relay because none of the HSSes or Diameter Agents is currently connected."
    ::= { shRelayInterfaceStats 1 }

-- SH Interface ......................

  bwDXShOperationMinTime OBJECT-TYPE
    SYNTAX      Gauge32
    MAX-ACCESS  read-only
    STATUS      current
    DESCRIPTION 
        "This is the minimum amount of time the Execution Server waited for a Sh operation to complete.  An operation can involve multiple Sh exchanges with the IMS Home Subscriber Server (HSS).  An operation is either a full profile read or write."
-- @feature:191447
    ::= { shStats 1 }

  bwDXShOperationMaxTime OBJECT-TYPE
    SYNTAX      Gauge32
    MAX-ACCESS  read-only
    STATUS      current
    DESCRIPTION 
        "This is the maximum amount of time the Execution Serverwaits for an Sh operation to complete.  An operation can involve multiple Sh exchanges with the IMS Home Subscriber Server (HSS).  An operation is either a full profile read or write."
-- @feature:191447
    ::= { shStats 2 }

  bwDXShOperationAverageTime OBJECT-TYPE
    SYNTAX      Gauge32
    MAX-ACCESS  read-only
    STATUS      current
    DESCRIPTION 
        "This is the average amount of time the Execution Server waits for an Sh operation to complete.  An operation can involve multiple Sh exchanges with the IMS Home Subscriber Server (HSS).  An operation is either a full profile read or write."
-- @feature:191447
    ::= { shStats 3 }

  bwDXShOperations OBJECT-TYPE
    SYNTAX      Counter32
    MAX-ACCESS  read-write
    STATUS      current
    DESCRIPTION 
        "This is the number of completed Sh operations."
-- @feature:191447
    ::= { shStats 4 }

-- Protocol :: CAP ...........................................

  bwDXSCAPStatsRegisterRequests OBJECT-TYPE
    SYNTAX      Counter32
    MAX-ACCESS  read-write
    STATUS      current
    DESCRIPTION 
        "This counter reflects the number of CAP registerRequest messages that have been received by the system."
    ::= { capStats 1 }

  bwDXSCAPStatsUnRegistersIn OBJECT-TYPE
    SYNTAX      Counter32
    MAX-ACCESS  read-write
    STATUS      current
    DESCRIPTION 
        "This counter reflects the number of CAP unRegister messages that have been received by the system."
    ::= { capStats 2 }

  bwDXSCAPStatsUnRegistersOut OBJECT-TYPE
    SYNTAX      Counter32
    MAX-ACCESS  read-write
    STATUS      current
    DESCRIPTION 
        "This counter reflects the number of CAP unRegister messages that have been sent out by the system."
    ::= { capStats 3 }

  bwDXSCAPStatsSessionUpdatesOut OBJECT-TYPE
    SYNTAX      Counter32
    MAX-ACCESS  read-write
    STATUS      current
    DESCRIPTION 
        "This counter reflects the number of CAP sessionUpdate messages that have been sent out by the system."
    ::= { capStats 4 }

  bwDXSCAPStatsProfileUpdatesOut OBJECT-TYPE
    SYNTAX      Counter32
    MAX-ACCESS  read-write
    STATUS      current
    DESCRIPTION 
        "This counter reflects the number of CAP profileUpdate messages that have been sent out by the system."
    ::= { capStats 5 }

  bwDXSCAPStatsCallUpdatesOut OBJECT-TYPE
    SYNTAX      Counter32
    MAX-ACCESS  read-write
    STATUS      current
    DESCRIPTION 
        "ThisThis counter reflects the number of CAP callUpdate messages that have been sent out by the system."
    ::= { capStats 6 }

  bwDXSCAPStatsCallActionsIn OBJECT-TYPE
    SYNTAX      Counter32
    MAX-ACCESS  read-write
    STATUS      current
    DESCRIPTION 
        "This counter reflects the number of CAP callAction messages that have been received by the system."
    ::= { capStats 7 }

  bwDXSCAPStatsAcknowledgementsIn OBJECT-TYPE
    SYNTAX      Counter32
    MAX-ACCESS  read-write
    STATUS      current
    DESCRIPTION 
        "This counter reflects the number of CAP acknowledgement messages that have been received by the system."
    ::= { capStats 8 }

  bwDXSCAPStatsAclViolations OBJECT-TYPE
    SYNTAX      Counter32
    MAX-ACCESS  read-write
    STATUS      current
    DESCRIPTION 
        "This counter reflects the number of incoming CAP connections that have been rejected because the connecting machine is not in the CAP access control list.  This counter causes an alarm to be generated when its threshold value is reached."
    ::= { capStats 10 }

  bwDXSCAPStatsUnsuccessfulRegisterResponses OBJECT-TYPE
    SYNTAX      Counter32
    MAX-ACCESS  read-write
    STATUS      current
    DESCRIPTION 
        "This counter reflects the number of unsuccessful CAP registerResponse messages that the system sends out.  This counter causes an alarm to be generated when its threshold value is reached."
    ::= { capStats 11 }

  bwDXSCAPStatsRegisterResponsesTable OBJECT-TYPE
    SYNTAX      SEQUENCE OF BwCAPStatsRegisterResponsesEntry
    MAX-ACCESS  not-accessible
    STATUS      current
    DESCRIPTION 
        "This table contains counters for the different types of CAP registerResponse messages sent by the system in response to a received CAP registerRequest message.  The following are the various types of registerResponse messages and an index value identifying each type: 1 - successful registerResponse, 2 - unsuccessful registerResponse (unknown user id), 3 - unsuccessful registerResponse (incorrect user credentials), 4 - unsuccessful registerResponse (feature unauthorized)."
    ::= { capStats 12 }

  bwDXSCAPStatsRegisterResponsesEntry OBJECT-TYPE
    SYNTAX      BwCAPStatsRegisterResponsesEntry
    MAX-ACCESS  not-accessible
    STATUS      current
    DESCRIPTION 
        "This row contains information on a particular CAP registerResponse type sent out by the system."
    INDEX       { bwDXSCAPStatsRegisterResponsesType }
    ::= { bwDXSCAPStatsRegisterResponsesTable 1 }

  BwCAPStatsRegisterResponsesEntry ::= SEQUENCE {
    bwDXSCAPStatsRegisterResponsesType     Unsigned32,
    bwDXSCAPStatsRegisterResponses         Counter32
  }

  bwDXSCAPStatsRegisterResponsesType OBJECT-TYPE
    SYNTAX      Unsigned32
    MAX-ACCESS  read-only
    STATUS      current
    DESCRIPTION 
        "This integer represents a registerResponse type.  This is also the index into the table."
    ::= { bwDXSCAPStatsRegisterResponsesEntry 1 }

  bwDXSCAPStatsRegisterResponses OBJECT-TYPE
    SYNTAX      Counter32
    MAX-ACCESS  read-write
    STATUS      current
    DESCRIPTION 
        "This counter reflects the number of CAP registerResponse messages that have been sent out by the system."
    ::= { bwDXSCAPStatsRegisterResponsesEntry 2 }

  bwDXSCAPStatsCallControlInfosOut OBJECT-TYPE
    SYNTAX      Counter32
    MAX-ACCESS  read-write
    STATUS      current
    DESCRIPTION 
        "This counter is incremented whenever a CAP callControlInfo message is sent out by the system"
    ::= { capStats 13 }

  bwDXSCAPStatsRegisterAuthentications OBJECT-TYPE
    SYNTAX      Counter32
    MAX-ACCESS  read-write
    STATUS      current
    DESCRIPTION 
        "This counter is incremented whenever the Execution Server receives a registerAuthentication CAP message"
    ::= { capStats 14 }

  bwDXSCAPStatsResponseAuthentications OBJECT-TYPE
    SYNTAX      Counter32
    MAX-ACCESS  read-write
    STATUS      current
    DESCRIPTION 
        "This counter is incremented whenever the Execution Server receives a responseAuthentication CAP message"
    ::= { capStats 15 }

  bwDXSCAPStatsInfoRequests OBJECT-TYPE
    SYNTAX      Counter32
    MAX-ACCESS  read-write
    STATUS      current
    DESCRIPTION 
        "This counter is incremented whenever the Execution Server receives a infoRequest CAP message"
    ::= { capStats 16 }

  bwDXSCAPStatsInfoResponses OBJECT-TYPE
    SYNTAX      Counter32
    MAX-ACCESS  read-write
    STATUS      current
    DESCRIPTION 
        "This counter is incremented whenever the Execution Server receives a infoResponse CAP message"
    ::= { capStats 17 }

  bwDXSCAPStatsExternalNotifies OBJECT-TYPE
    SYNTAX      Counter32
    MAX-ACCESS  read-write
    STATUS      current
    DESCRIPTION 
        "This counter is incremented whenever the Execution Server receives a externalNotify CAP message"
    ::= { capStats 18 }

  bwDXSCAPMonitoringUsersRequests OBJECT-TYPE
    SYNTAX      Counter32
    MAX-ACCESS  read-write
    STATUS      current
    DESCRIPTION 
        "The number of monitoringUsersRequest CAP messages received."
    ::= { capStats 19 }

  bwDXSCAPMonitoringUsersResponses OBJECT-TYPE
    SYNTAX      Counter32
    MAX-ACCESS  read-write
    STATUS      current
    DESCRIPTION 
        "The number of monitoringUsersResponse CAP messages sent."
    ::= { capStats 20 }

  bwDXSCAPStatsQueueUpdatesOut OBJECT-TYPE
    SYNTAX      Counter32
    MAX-ACCESS  read-write
    STATUS      current
    DESCRIPTION 
        "This counter reflects the number of CAP queueUpdate messages that have been sent out by the system."
    ::= { capStats 21 }

  bwDXSCAPStatsQueueActionsIn OBJECT-TYPE
    SYNTAX      Counter32
    MAX-ACCESS  read-write
    STATUS      current
    DESCRIPTION 
        "This counter reflects the number of CAP queueAction messages that have been received by the system."
    ::= { capStats 22 }

  bwDXSCAPStatsDatagramsIn OBJECT-TYPE
    SYNTAX      Counter32
    MAX-ACCESS  read-write
    STATUS      current
    DESCRIPTION 
        "This counter reflects the number of CAP datagram  commands  that have been received by the system."
    ::= { capStats 23 }

  bwDXSCAPStatsDatagramsOut OBJECT-TYPE
    SYNTAX      Counter32
    MAX-ACCESS  read-write
    STATUS      current
    DESCRIPTION 
        "This counter reflects the number of CAP datagram  commands  that have been sent by the system."
    ::= { capStats 24 }

  bwDXSCAPStatsTotalMsgs OBJECT-TYPE
    SYNTAX      Counter32
    MAX-ACCESS  read-write
    STATUS      current
    DESCRIPTION 
        "This counter cumulates the total number of CAP messages that have been handled by the system."
    ::= { capStats 25 }

  bwDXSCAPNumInboundDiscardedMessages OBJECT-TYPE
    SYNTAX      Counter32
    MAX-ACCESS  read-write
    STATUS      current
    DESCRIPTION 
        "This is the number of inbound messages that were discarded from the inbound queue."
    ::= { capStats 26 }

  bwDXSCAPNumOutboundDiscardedMessages OBJECT-TYPE
    SYNTAX      Counter32
    MAX-ACCESS  read-write
    STATUS      current
    DESCRIPTION 
        "This is the number of outbound messages that were discarded from the outbound queue."
    ::= { capStats 27 }

  bwDXSCAPNumConnections OBJECT-TYPE
    SYNTAX      Counter32
    MAX-ACCESS  read-write
    STATUS      current
    DESCRIPTION 
        "This is the number of connections that were created on the execution server for the CAP protocol."
    ::= { capStats 28 }

  bwDXSCAPNumDisconnections OBJECT-TYPE
    SYNTAX      Counter32
    MAX-ACCESS  read-write
    STATUS      current
    DESCRIPTION 
        "This is the number of disconnections that were performed on the execution server for the CAP protocol."
    ::= { capStats 29 }

  bwDXSCAPNumCCC2Connections OBJECT-TYPE
    SYNTAX      Counter32
    MAX-ACCESS  read-write
    STATUS      current
    DESCRIPTION 
        "This is the number of connections that were created on the execution server for the CCC2 protocol."
    ::= { capStats 30 }

  bwDXSCAPNumCCC2Disconnections OBJECT-TYPE
    SYNTAX      Counter32
    MAX-ACCESS  read-write
    STATUS      current
    DESCRIPTION 
        "This is the number of disconnections that were performed on the execution server for the CCC2 protocol."
    ::= { capStats 31 }

  bwDXSCAPNumCapSCallCenterConnections OBJECT-TYPE
    SYNTAX      Counter32
    MAX-ACCESS  read-write
    STATUS      current
    DESCRIPTION 
        "This is the number of connections that were created on the execution server for the CapSCallCenter protocol."
    ::= { capStats 32 }

  bwDXSCAPNumCapSCallCenterDisconnections OBJECT-TYPE
    SYNTAX      Counter32
    MAX-ACCESS  read-write
    STATUS      current
    DESCRIPTION 
        "This is the number of disconnections that were performed on the execution server for the CapSCallCenter protocol."
    ::= { capStats 33 }

-- Protocol :: SMDI ...........................................

  bwDXSSmdiNbOfActiveConnection OBJECT-TYPE
    SYNTAX      Gauge32
    MAX-ACCESS  read-only
    STATUS      current
    DESCRIPTION 
        "Counts the total number of currently active Terminal Server SMDI connections."
    ::= { smdiStats 1 }

  bwDXSSmdiNbOfOpenedConnection OBJECT-TYPE
    SYNTAX      Counter32
    MAX-ACCESS  read-write
    STATUS      current
    DESCRIPTION 
        "This counter gives the total number of SMDI connections that were opened since the last reboot of the system or reset of the PMs."
    ::= { smdiStats 2 }

  bwDXSSmdiIncomingMWIActivationRequests OBJECT-TYPE
    SYNTAX      Counter32
    MAX-ACCESS  read-write
    STATUS      current
    DESCRIPTION 
        "This counter reflects the number of SMDI MWI activation requests that were received and processed by the server."
    ::= { smdiStats 3 }

  bwDXSSmdiIncomingMWIDesactivationRequests OBJECT-TYPE
    SYNTAX      Counter32
    MAX-ACCESS  read-write
    STATUS      current
    DESCRIPTION 
        "This counter reflects the number of SMDI MWI desactivation requests that were received and processed by the server."
    ::= { smdiStats 4 }

  bwDXSSmdiInvalidRequestsReceived OBJECT-TYPE
    SYNTAX      Counter32
    MAX-ACCESS  read-write
    STATUS      current
    DESCRIPTION 
        "This counter reflects the number of invalid SMDI requests."
    ::= { smdiStats 5 }

  bwDXSSmdiBlockResponsesSent OBJECT-TYPE
    SYNTAX      Counter32
    MAX-ACCESS  read-write
    STATUS      current
    DESCRIPTION 
        "This counter reflects the number of SMDI MWI negative acknowledgement with a cause set to BLK."
    ::= { smdiStats 6 }

  bwDXSSmdiInvalidResponsesSent OBJECT-TYPE
    SYNTAX      Counter32
    MAX-ACCESS  read-write
    STATUS      current
    DESCRIPTION 
        "This counter reflects the number of SMDI MWI negative acknowledgement with a cause set to INV."
    ::= { smdiStats 7 }

  bwDXSSmdiOutgoingMWIActivationRequests OBJECT-TYPE
    SYNTAX      Counter32
    MAX-ACCESS  read-write
    STATUS      current
    DESCRIPTION 
        "This counter reflects the number of Number of outgoing SMDI MWI OP message."
    ::= { smdiStats 8 }

  bwDXSSmdiOutgoingMWIDeactivationRequests OBJECT-TYPE
    SYNTAX      Counter32
    MAX-ACCESS  read-write
    STATUS      current
    DESCRIPTION 
        "This counter reflects the number of Number of outgoing SMDI MWI RMV message."
    ::= { smdiStats 9 }

  bwDXSSmdiBlockResponsesReceived OBJECT-TYPE
    SYNTAX      Counter32
    MAX-ACCESS  read-write
    STATUS      current
    DESCRIPTION 
        "This counter reflects the number of SMDI MWI negative acknowledgement with a cause set to BLK received from a station host, i.e. a Class 5 End Office."
    ::= { smdiStats 10 }

  bwDXSSmdiInvalidResponsesReceived OBJECT-TYPE
    SYNTAX      Counter32
    MAX-ACCESS  read-write
    STATUS      current
    DESCRIPTION 
        "This counter reflects the number of SMDI MWI negative acknowledgement with a cause set to INV."
    ::= { smdiStats 11 }

  bwDXSSMDIMessageDeskMessageSent OBJECT-TYPE
    SYNTAX      Counter32
    MAX-ACCESS  read-write
    STATUS      current
    DESCRIPTION 
        "This counter reflects the number of outgoing SMDI MD messages sent by BroadWorks."
    ::= { smdiStats 12 }


-- Media management ...........................................

  bwDXSMediaCommandsTransmitted OBJECT-TYPE
    SYNTAX      Counter32
    MAX-ACCESS  read-write
    STATUS      current
    DESCRIPTION 
        "Contains the number of times a media command was transmitted, for the entire Application Server."
    ::= { mediaStats 1 }

  bwDXSMediaNotificationsReceived OBJECT-TYPE
    SYNTAX      Counter32
    MAX-ACCESS  read-write
    STATUS      current
    DESCRIPTION 
        "Contains the number of times a media notification was received, for the entire Application Server."
    ::= { mediaStats 2 }

  bwDXSMediaResourceAllocAttempts OBJECT-TYPE
    SYNTAX      Counter32
    MAX-ACCESS  read-write
    STATUS      current
    DESCRIPTION 
        "Contains the number of media resource allocation attempts, for the entire Application Server."
    ::= { mediaStats 3 }

  bwDXSMediaResourceAllocFailures OBJECT-TYPE
    SYNTAX      Counter32
    MAX-ACCESS  read-write
    STATUS      current
    DESCRIPTION 
        "Contains the number of times a media command was transmitted, for the entire Application Server."
    ::= { mediaStats 4 }
-- WholeSale Protocol management ...........................................

  bwDXSWSPStatsServiceRequestsIn OBJECT-TYPE
    SYNTAX      Counter32
    MAX-ACCESS  read-write
    STATUS      current
    DESCRIPTION 
        "This counter is incremented whenever a WSP ServiceRequest message is received."
    ::= { wspStats 1 }

  bwDXSWSPStatsServiceActionsOut OBJECT-TYPE
    SYNTAX      Counter32
    MAX-ACCESS  read-write
    STATUS      current
    DESCRIPTION 
        "This counter is incremented whenever a WSP ServiceAction message is transmitted."
    ::= { wspStats 2 }

  bwDXSWSPStatsServiceUpdatesIn OBJECT-TYPE
    SYNTAX      Counter32
    MAX-ACCESS  read-write
    STATUS      current
    DESCRIPTION 
        "This counter is incremented whenever a WSP ServiceUpdate message is received."
    ::= { wspStats 3 }

  bwDXSWSPStatsServiceAcknowledgementsOut OBJECT-TYPE
    SYNTAX      Counter32
    MAX-ACCESS  read-write
    STATUS      current
    DESCRIPTION 
        "This counter is incremented whenever a WSP ServiceAcknowledgement message is transmitted."
    ::= { wspStats 4 }

-- Realtime Accounting management ...........................................

  bwDXSRealtimeAccountingRequestsTransmitted OBJECT-TYPE
    SYNTAX      Counter32
    MAX-ACCESS  read-write
    STATUS      current
    DESCRIPTION 
        "Number of new Accounting Requests sent to a Radius Server. Incremented each time a new Accounting Request transmission is first attempted toward a Radius Server."
    ::= { realtimeAccountingStats 1 }

  bwDXSRealtimeAccountingRequestsRetransmitted OBJECT-TYPE
    SYNTAX      Counter32
    MAX-ACCESS  read-write
    STATUS      current
    DESCRIPTION 
        "Number of Accounting Requests sent to Radius Server(s) due to retransmissions to the same server. Incremented each time an Accounting Request transmission is retransmitted toward an Accounting Radius Server (be it to the same server as the one where the original request was sent, or to the alternate server)."
    ::= { realtimeAccountingStats 2 }

  bwDXSRealtimeAccountingRequestsDropped OBJECT-TYPE
    SYNTAX      Counter32
    MAX-ACCESS  read-write
    STATUS      current
    DESCRIPTION 
        "Number of Accounting Requests that were discarded due to the lack of a responsive Accounting Radius Server. Incremented each time an Accounting Request is dropped, after all transmissions attempts have failed."
    ::= { realtimeAccountingStats 3 }

-- External Call Logs management ...........................................

  bwDXSExternalCallLogsTransmitted OBJECT-TYPE
    SYNTAX      Counter32
    MAX-ACCESS  read-write
    STATUS      current
    DESCRIPTION 
        "Incremented each time a new external call log transmission is first attempted toward a Call detail server."
    ::= { externalCallLogsStats 1 }

  bwDXSExternalCallLogsRetransmitted OBJECT-TYPE
    SYNTAX      Counter32
    MAX-ACCESS  read-write
    STATUS      current
    DESCRIPTION 
        "Incremented each time a new external call log transmission is retransmitted towards a Call Detail Radius Server (be it to the same server as the one where the original call log was sent, or to the alternate server)."
    ::= { externalCallLogsStats 2 }

  bwDXSExternalCallLogsDropped OBJECT-TYPE
    SYNTAX      Counter32
    MAX-ACCESS  read-write
    STATUS      current
    DESCRIPTION 
        "Incremented each time a call log is dropped, after all transmissions attempts have failed."
    ::= { externalCallLogsStats 3 }

  bwDXSExternalCallLogsQueued OBJECT-TYPE
    SYNTAX      Counter32
    MAX-ACCESS  read-write
    STATUS      current
    DESCRIPTION 
        "Incremented each time a call log is written to the AS file-based queue, after all transmissions attempts have failed."
    ::= { externalCallLogsStats 4 }

  bwDXSExternalCallLogsTransmittedFromQueue OBJECT-TYPE
    SYNTAX      Counter32
    MAX-ACCESS  read-write
    STATUS      current
    DESCRIPTION 
        "Incremented on the first attempt to send to the call detail server a call log read from the file based queue."
    ::= { externalCallLogsStats 5 }

  bwDXSExternalCallLogsRetransmittedFromQueue OBJECT-TYPE
    SYNTAX      Counter32
    MAX-ACCESS  read-write
    STATUS      current
    DESCRIPTION 
        "Incremented on all attempts but the first one to send to the Call Detail Server a call log read from the file based queue."
    ::= { externalCallLogsStats 6 }

-- XS - BroadWorks Common Communication Protocol ........................

  bwDXSCommonCommXSStatsTable OBJECT-TYPE
    SYNTAX      SEQUENCE OF BwCommonCommXSStatsEntry
    MAX-ACCESS  not-accessible
    STATUS      current
    DESCRIPTION 
        "This table contains counters for BCCT for the XS process."
    ::= { commonCommStats 1 }

  bwDXSCommonCommXSStatsEntry OBJECT-TYPE
    SYNTAX      BwCommonCommXSStatsEntry
    MAX-ACCESS  not-accessible
    STATUS      current
    DESCRIPTION 
        "Definition of the entries for bwDXSCommonCommXSStatsTable."
    INDEX       { bwDXSCommonCommXSStatsIndex }
    ::= { bwDXSCommonCommXSStatsTable 1 }

  BwCommonCommXSStatsEntry ::= SEQUENCE {
    bwDXSCommonCommXSStatsIndex                    Unsigned32,
    bwDXSCommonCommXSHost                          DisplayString,
    bwDXSCommonCommXSInterface                     DisplayString,
    bwDXSCommonCommXSProtocol                      DisplayString,
    bwDXSCommonCommXSAcceptedOutboundConnections   Counter32,
    bwDXSCommonCommXSAcceptedInboundConnections    Counter32,
    bwDXSCommonCommXSRejectedOutboundConnections   Counter32,
    bwDXSCommonCommXSRejectedInboundConnections    Counter32,
    bwDXSCommonCommXSOutputMessagesProcessed       Counter32,
    bwDXSCommonCommXSInputMessagesProcessed        Counter32,
    bwDXSCommonCommXSOutputCommunicationErrors     Counter32,
    bwDXSCommonCommXSInputCommunicationErrors      Counter32
  }

  bwDXSCommonCommXSStatsIndex OBJECT-TYPE
    SYNTAX      Unsigned32
    MAX-ACCESS  read-only
    STATUS      current
    DESCRIPTION 
        "This integer represents an index in table bwDXSCommonCommXSStatsTable. The index represents a connection for a specific Host-Interfacece-Protocol combination."
    ::= { bwDXSCommonCommXSStatsEntry 1 }

  bwDXSCommonCommXSHost OBJECT-TYPE
    SYNTAX      DisplayString
    MAX-ACCESS  read-only
    STATUS      current
    DESCRIPTION 
        "The address of a host connected to the BroadWorks Common Communication Protocol."
    ::= { bwDXSCommonCommXSStatsEntry 2 }

  bwDXSCommonCommXSInterface OBJECT-TYPE
    SYNTAX      DisplayString
    MAX-ACCESS  read-only
    STATUS      current
    DESCRIPTION 
        "The IP address of a local interface that a protocol is bound to."
    ::= { bwDXSCommonCommXSStatsEntry 3 }

  bwDXSCommonCommXSProtocol OBJECT-TYPE
    SYNTAX      DisplayString
    MAX-ACCESS  read-only
    STATUS      current
    DESCRIPTION 
        "The name of a BroadWorks Common Communication Protocol client protocol, e.g. OCI or SyncApi."
    ::= { bwDXSCommonCommXSStatsEntry 4 }

  bwDXSCommonCommXSAcceptedOutboundConnections OBJECT-TYPE
    SYNTAX      Counter32
    MAX-ACCESS  read-write
    STATUS      current
    DESCRIPTION 
        "This counter is incremented whenever a client in this process connects to the framework to a remote host, using the interface and protocol."
    ::= { bwDXSCommonCommXSStatsEntry 5 }

  bwDXSCommonCommXSAcceptedInboundConnections OBJECT-TYPE
    SYNTAX      Counter32
    MAX-ACCESS  read-write
    STATUS      current
    DESCRIPTION 
        "This counter is incremented whenever a client in this process connects to the framework from a remote host, using the interface and protocol."
    ::= { bwDXSCommonCommXSStatsEntry 6 }

  bwDXSCommonCommXSRejectedOutboundConnections OBJECT-TYPE
    SYNTAX      Counter32
    MAX-ACCESS  read-write
    STATUS      current
    DESCRIPTION 
        "This counter is incremented whenever a client connection request going from this process to a remote host and going through this interface has been rejected for a particular protocol."
    ::= { bwDXSCommonCommXSStatsEntry 7 }

  bwDXSCommonCommXSRejectedInboundConnections OBJECT-TYPE
    SYNTAX      Counter32
    MAX-ACCESS  read-write
    STATUS      current
    DESCRIPTION 
        "This counter is incremented whenever a client connection request coming to this host and going through this interface has been rejected by the framework for a particular protocol."
    ::= { bwDXSCommonCommXSStatsEntry 8 }

  bwDXSCommonCommXSOutputMessagesProcessed OBJECT-TYPE
    SYNTAX      Counter32
    MAX-ACCESS  read-write
    STATUS      current
    DESCRIPTION 
        "This counter is incremented whenever a message has been sent and processed for this host, interface and protocol."
    ::= { bwDXSCommonCommXSStatsEntry 9 }

  bwDXSCommonCommXSInputMessagesProcessed OBJECT-TYPE
    SYNTAX      Counter32
    MAX-ACCESS  read-write
    STATUS      current
    DESCRIPTION 
        "This counter is incremented whenever a message has been received and processed for this host, interface and protocol."
    ::= { bwDXSCommonCommXSStatsEntry 10 }

  bwDXSCommonCommXSOutputCommunicationErrors OBJECT-TYPE
    SYNTAX      Counter32
    MAX-ACCESS  read-write
    STATUS      current
    DESCRIPTION 
        "This counter is incremented whenever a message could not be read because the TCP stack returned an error."
    ::= { bwDXSCommonCommXSStatsEntry 11 }

  bwDXSCommonCommXSInputCommunicationErrors OBJECT-TYPE
    SYNTAX      Counter32
    MAX-ACCESS  read-write
    STATUS      current
    DESCRIPTION 
        "This counter is incremented whenever a message has been sent and processed for this host, interface and protocol."
    ::= { bwDXSCommonCommXSStatsEntry 12 }

-- XS - TCP Framework ........................

  bwDXSTcpServersStatsTable OBJECT-TYPE
    SYNTAX      SEQUENCE OF BwXSDTcpServersStatsEntry
    MAX-ACCESS  not-accessible
    STATUS      current
    DESCRIPTION 
        "This table contains counters for TCP underlying framework for the XS process."
    ::= { tcpStats 1 }

  bwDXSTcpServersStatsEntry OBJECT-TYPE
    SYNTAX      BwXSDTcpServersStatsEntry
    MAX-ACCESS  not-accessible
    STATUS      current
    DESCRIPTION 
        "Definition of the entries for bwDXSTcpServersStatsTable."
    INDEX       { bwDXSTcpServersStatsIndex }
    ::= { bwDXSTcpServersStatsTable 1 }

  BwXSDTcpServersStatsEntry ::= SEQUENCE {
    bwDXSTcpServersStatsIndex                Unsigned32,
    bwDXSTcpServersName                      DisplayString,
    bwDXSTcpServersNbConnectionsAccepted     Counter32,
    bwDXSTcpServersNbConnectionsRefused      Counter32,
    bwDXSTcpServersNbConnectionsInitiated    Counter32,
    bwDXSTcpServersNbConnectionsClosed       Counter32,
    bwDXSTcpServersNbBytesSent               Gauge32,
    bwDXSTcpServersNbBytesReceived           Gauge32,
    bwDXSTcpServersOutgoingQueueSize         Gauge32,
    bwDXSTcpServersIncomingQueueSize         Gauge32,
    bwDXSTcpServersNbBytesSentSecure         Gauge32,
    bwDXSTcpServersNbBytesReceivedSecure     Gauge32
  }

  bwDXSTcpServersStatsIndex OBJECT-TYPE
    SYNTAX      Unsigned32
    MAX-ACCESS  read-only
    STATUS      current
    DESCRIPTION 
        "This integer represents an index in table bwDXSTcpServersStatsTable. This is the index to a specific TCP server name."
    ::= { bwDXSTcpServersStatsEntry 1 }

  bwDXSTcpServersName OBJECT-TYPE
    SYNTAX      DisplayString
    MAX-ACCESS  read-only
    STATUS      current
    DESCRIPTION 
        "The name of TCP server - Names are internally defined at at the application level."
    ::= { bwDXSTcpServersStatsEntry 2 }

  bwDXSTcpServersNbConnectionsAccepted OBJECT-TYPE
    SYNTAX      Counter32
    MAX-ACCESS  read-write
    STATUS      current
    DESCRIPTION 
        "This counter represents the number of connections accepted by the TCP server."
    ::= { bwDXSTcpServersStatsEntry 3 }

  bwDXSTcpServersNbConnectionsRefused OBJECT-TYPE
    SYNTAX      Counter32
    MAX-ACCESS  read-write
    STATUS      current
    DESCRIPTION 
        "This counter represents the number of connections refused by the TCP server."
    ::= { bwDXSTcpServersStatsEntry 4 }

  bwDXSTcpServersNbConnectionsInitiated OBJECT-TYPE
    SYNTAX      Counter32
    MAX-ACCESS  read-write
    STATUS      current
    DESCRIPTION 
        "This counter represents the number of connections initiated by the TCP server."
    ::= { bwDXSTcpServersStatsEntry 5 }

  bwDXSTcpServersNbConnectionsClosed OBJECT-TYPE
    SYNTAX      Counter32
    MAX-ACCESS  read-write
    STATUS      current
    DESCRIPTION 
        "This counter represents the number of connections closed by the TCP server or remote hosts."
    ::= { bwDXSTcpServersStatsEntry 6 }

  bwDXSTcpServersNbBytesSent OBJECT-TYPE
    SYNTAX      Gauge32
    MAX-ACCESS  read-write
    STATUS      current
    DESCRIPTION 
        "This counter represents the number of bytes sent by the TCP server."
    ::= { bwDXSTcpServersStatsEntry 7 }

  bwDXSTcpServersNbBytesReceived OBJECT-TYPE
    SYNTAX      Gauge32
    MAX-ACCESS  read-write
    STATUS      current
    DESCRIPTION 
        "This counter represents the number of bytes received by the TCP server."
    ::= { bwDXSTcpServersStatsEntry 8 }

  bwDXSTcpServersOutgoingQueueSize OBJECT-TYPE
    SYNTAX      Gauge32
    MAX-ACCESS  read-only
    STATUS      current
    DESCRIPTION 
        "This counter represents the number of bytes in the outgoing queue."
    ::= { bwDXSTcpServersStatsEntry 9 }

  bwDXSTcpServersIncomingQueueSize OBJECT-TYPE
    SYNTAX      Gauge32
    MAX-ACCESS  read-only
    STATUS      current
    DESCRIPTION 
        "This counter represents the number of bytes in the incoming queue."
    ::= { bwDXSTcpServersStatsEntry 10 }

  bwDXSTcpServersNbBytesSentSecure OBJECT-TYPE
    SYNTAX      Gauge32
    MAX-ACCESS  read-write
    STATUS      current
    DESCRIPTION 
        "This counter represents the number of bytes sent by the TCP server over secure connections."
    ::= { bwDXSTcpServersStatsEntry 11 }

  bwDXSTcpServersNbBytesReceivedSecure OBJECT-TYPE
    SYNTAX      Gauge32
    MAX-ACCESS  read-write
    STATUS      current
    DESCRIPTION 
        "This counter represents the number of bytes received by the TCP server over secure connections."
    ::= { bwDXSTcpServersStatsEntry 12 }

-- XS - Concurrent Framework ........................

  bwDXSMonitoringExecutorTable OBJECT-TYPE
    SYNTAX      SEQUENCE OF BwXSMonitoringExecutorEntry
    MAX-ACCESS  not-accessible
    STATUS      current
    DESCRIPTION 
        "This table contains counters for the concurrent framework."
    ::= { concurrentStats 1 }

  bwDXSMonitoringExecutorEntry OBJECT-TYPE
    SYNTAX      BwXSMonitoringExecutorEntry
    MAX-ACCESS  not-accessible
    STATUS      current
    DESCRIPTION 
        "Definition of the entries for bwDXSMonitoringExecutorTable."
    INDEX       { bwDXSMonitoringExecutorIndex }
    ::= { bwDXSMonitoringExecutorTable 1 }

  BwXSMonitoringExecutorEntry ::= SEQUENCE {
    bwDXSMonitoringExecutorIndex             Unsigned32,
    bwDXSMonitoringExecutorName              DisplayString,
    bwDXSMonitoringExecutorCurrentPoolSize   Gauge32,
    bwDXSMonitoringExecutorMaxPoolSize       Gauge32,
    bwDXSMonitoringExecutorAvgActiveThreads  Gauge32,
    bwDXSMonitoringExecutorTaskQueueSize     Gauge32,
    bwDXSMonitoringExecutorNbTasksRun        Counter32,
    bwDXSMonitoringExecutorNbWarnings        Counter32,
    bwDXSMonitoringExecutorNbErrors          Counter32,
    bwDXSMonitoringExecutorLongestTaskMs     Gauge32,
    bwDXSMonitoringExecutorLongestTaskName   DisplayString
  }

  bwDXSMonitoringExecutorIndex OBJECT-TYPE
    SYNTAX      Unsigned32
    MAX-ACCESS  read-only
    STATUS      current
    DESCRIPTION 
        "This integer represents an index in table bwDXSMonitoringExecutorTable. This is the index to a specific Monitoring Executor name."
    ::= { bwDXSMonitoringExecutorEntry 1 }

  bwDXSMonitoringExecutorName OBJECT-TYPE
    SYNTAX      DisplayString
    MAX-ACCESS  read-only
    STATUS      current
    DESCRIPTION 
        "The name of the Monitoring Executor - Names are internally defined at the application level."
    ::= { bwDXSMonitoringExecutorEntry 2 }

  bwDXSMonitoringExecutorCurrentPoolSize OBJECT-TYPE
    SYNTAX      Gauge32
    MAX-ACCESS  read-only
    STATUS      current
    DESCRIPTION 
        "The current thread pool size"
    ::= { bwDXSMonitoringExecutorEntry 3 }

  bwDXSMonitoringExecutorMaxPoolSize OBJECT-TYPE
    SYNTAX      Gauge32
    MAX-ACCESS  read-only
    STATUS      current
    DESCRIPTION 
        "The maximum thread pool size"
    ::= { bwDXSMonitoringExecutorEntry 4 }

  bwDXSMonitoringExecutorAvgActiveThreads OBJECT-TYPE
    SYNTAX      Gauge32
    MAX-ACCESS  read-only
    STATUS      current
    DESCRIPTION 
        "The average number of active threads, rounded up"
    ::= { bwDXSMonitoringExecutorEntry 5 }

  bwDXSMonitoringExecutorTaskQueueSize OBJECT-TYPE
    SYNTAX      Gauge32
    MAX-ACCESS  read-only
    STATUS      current
    DESCRIPTION 
        "Number of tasks in the queue (includes scheduled and recurring tasks)"
    ::= { bwDXSMonitoringExecutorEntry 6 }

  bwDXSMonitoringExecutorNbTasksRun OBJECT-TYPE
    SYNTAX      Counter32
    MAX-ACCESS  read-write
    STATUS      current
    DESCRIPTION 
        "Number of tasks run"
    ::= { bwDXSMonitoringExecutorEntry 7 }

  bwDXSMonitoringExecutorNbWarnings OBJECT-TYPE
    SYNTAX      Counter32
    MAX-ACCESS  read-write
    STATUS      current
    DESCRIPTION 
        "Number of warnings that occured"
    ::= { bwDXSMonitoringExecutorEntry 8 }

  bwDXSMonitoringExecutorNbErrors OBJECT-TYPE
    SYNTAX      Counter32
    MAX-ACCESS  read-write
    STATUS      current
    DESCRIPTION 
        "Number of errors that occured"
    ::= { bwDXSMonitoringExecutorEntry 9 }

  bwDXSMonitoringExecutorLongestTaskMs OBJECT-TYPE
    SYNTAX      Gauge32
    MAX-ACCESS  read-only
    STATUS      current
    DESCRIPTION 
        "Longest completed task execution time in milliseconds"
    ::= { bwDXSMonitoringExecutorEntry 10 }

  bwDXSMonitoringExecutorLongestTaskName OBJECT-TYPE
    SYNTAX      DisplayString
    MAX-ACCESS  read-only
    STATUS      current
    DESCRIPTION 
        "Longest completed task name"
    ::= { bwDXSMonitoringExecutorEntry 11 }

-- XS - SOAP ........................

  bwDXSSOAPMaxSessions OBJECT-TYPE
    SYNTAX      Gauge32
    MAX-ACCESS  read-only
    STATUS      current
    DESCRIPTION 
        "Maximum number of incoming SOAP sessions simultaneously active since the system was started."
    ::= { soapStats 1 }

  bwDXSSOAPAvgSessions OBJECT-TYPE
    SYNTAX      Gauge32
    MAX-ACCESS  read-only
    STATUS      current
    DESCRIPTION 
        "Average number of incoming SOAP sessions simultaneously active, based on a rolling average over the last 100 sessions."
    ::= { soapStats 2 }

  bwDXSSOAPMaxThreads OBJECT-TYPE
    SYNTAX      Gauge32
    MAX-ACCESS  read-only
    STATUS      current
    DESCRIPTION 
        "This gauge measures the maximum percentage of SOAP processing threads simultaneously active since the system was started."
    ::= { soapStats 3 }

  bwDXSSOAPAvgThreads OBJECT-TYPE
    SYNTAX      Gauge32
    MAX-ACCESS  read-only
    STATUS      current
    DESCRIPTION 
        "Average percentage of SOAP threads simultaneously active, based on a rolling average over the last 100 sessions."
    ::= { soapStats 4 }

  bwDXSSOAPMaxServiceTime OBJECT-TYPE
    SYNTAX      Gauge32
    MAX-ACCESS  read-only
    STATUS      current
    DESCRIPTION 
        "Maximum time in milliseconds required to process an incoming SOAP request, since the system was started."
    ::= { soapStats 5 }

  bwDXSSOAPAvgServiceTime OBJECT-TYPE
    SYNTAX      Gauge32
    MAX-ACCESS  read-only
    STATUS      current
    DESCRIPTION 
        "Average time in milliseconds required to process an incoming SOAP request, based on a rolling average over the last 100 requests."
    ::= { soapStats 6 }

  bwDXSSOAPNumDroppedRequests OBJECT-TYPE
    SYNTAX      Counter32
    MAX-ACCESS  read-write
    STATUS      current
    DESCRIPTION 
        "Number of SOAP server requests dropped because the number of SOAP threads was too low."
    ::= { soapStats 7 }

-- XS - SMPP.................................................
  bwDXSSmppSubmitSMRequestsSent OBJECT-TYPE
    SYNTAX      Counter32
    MAX-ACCESS  read-write
    STATUS      current
    DESCRIPTION 
        "Number of outgoing SMPP submit_sm requests sent."
    ::= { smppStats 1 }

  bwDXSSmppInvalidSubmitSMResponsesReceived OBJECT-TYPE
    SYNTAX      Counter32
    MAX-ACCESS  read-write
    STATUS      current
    DESCRIPTION 
        "Count of invalid received submit_sm_resp"
    ::= { smppStats 2 }

  bwDXSSmppSubmitSMResponseTimeout OBJECT-TYPE
    SYNTAX      Counter32
    MAX-ACCESS  read-write
    STATUS      current
    DESCRIPTION 
        "Number of submit_sm requests timeouts detected."
    ::= { smppStats 3 }

-- dnsModule modules

  bwDXSDnsQueryTimeMax OBJECT-TYPE
    SYNTAX      Gauge32
    MAX-ACCESS  read-write
    STATUS      current
    DESCRIPTION 
        "This gauge reports the maximum query time in milliseconds."
    ::= { dnsStats 1 }

  bwDXSDnsQueryTimeMaxTimestampMSB OBJECT-TYPE
    SYNTAX      Gauge32
    MAX-ACCESS  read-write
    STATUS      current
    DESCRIPTION 
        "The gauge reports the most significant part of the timestamp (4 most significant bytes) of when bwDXSDnsQueryTimeMax was obtained."
    ::= { dnsStats 2 }

  bwDXSDnsQueryTimeMaxTimestampLSB OBJECT-TYPE
    SYNTAX      Gauge32
    MAX-ACCESS  read-write
    STATUS      current
    DESCRIPTION 
        "The gauge reports the least significant part of the timestamp (4 least significant bytes) of when bwDXSDnsQueryTimeMax was obtained."
    ::= { dnsStats 3 }

  bwDXSDnsQueryTimeAvg OBJECT-TYPE
    SYNTAX      Gauge32
    MAX-ACCESS  read-write
    STATUS      current
    DESCRIPTION 
        "This gauge reports the average query time in milliseconds."
    ::= { dnsStats 4 }

  bwDXSDnsStatsQueriesTable OBJECT-TYPE
    SYNTAX      SEQUENCE OF BwDnsStatsQueriesEntry
    MAX-ACCESS  not-accessible
    STATUS      current
    DESCRIPTION 
        "This table contains DNS statistics."
    ::= { dnsStats 5 }

  bwDXSDnsStatsQueriesEntry OBJECT-TYPE
    SYNTAX      BwDnsStatsQueriesEntry
    MAX-ACCESS  not-accessible
    STATUS      current
    DESCRIPTION 
        "This row contains information on a particular DNS query type."
    INDEX       { bwDXSDnsStatsQueryIndex }
    ::= { bwDXSDnsStatsQueriesTable 1 }

  BwDnsStatsQueriesEntry ::= SEQUENCE {
    bwDXSDnsStatsQueryIndex        Unsigned32,
    bwDXSDnsStatsQueryType         DisplayString,
    bwDXSDnsStatsQueries           Counter32,
    bwDXSDnsStatsQueryTimeouts     Counter32
  }

  bwDXSDnsStatsQueryIndex OBJECT-TYPE
    SYNTAX      Unsigned32
    MAX-ACCESS  read-only
    STATUS      current
    DESCRIPTION 
        "This column is the index for the table."
    ::= { bwDXSDnsStatsQueriesEntry 1 }

  bwDXSDnsStatsQueryType OBJECT-TYPE
    SYNTAX      DisplayString
    MAX-ACCESS  read-only
    STATUS      current
    DESCRIPTION 
        "This column represents the DNS query type."
    ::= { bwDXSDnsStatsQueriesEntry 2 }

  bwDXSDnsStatsQueries OBJECT-TYPE
    SYNTAX      Counter32
    MAX-ACCESS  read-write
    STATUS      current
    DESCRIPTION 
        "This counter reflects the number of DNS queries for a given type."
    ::= { bwDXSDnsStatsQueriesEntry 3 }

  bwDXSDnsStatsQueryTimeouts OBJECT-TYPE
    SYNTAX      Counter32
    MAX-ACCESS  read-write
    STATUS      current
    DESCRIPTION 
        "This counter reflects the number of DNS queries timeouts for a given type."
    ::= { bwDXSDnsStatsQueriesEntry 4 }

-- Offline Charging Module
  bwDXSOfflineChargingACROut OBJECT-TYPE
    SYNTAX      Counter32
    MAX-ACCESS  read-write
    STATUS      obsolete
    DESCRIPTION 
        "This is the number of ACR unique requests sent by BroadWorks. If the request is transmitted multiple times, only the first transmission is counted."
    ::= { offlineChargingStats 1 }

  bwDXSOfflineChargingACASuccessIn OBJECT-TYPE
    SYNTAX      Counter32
    MAX-ACCESS  read-write
    STATUS      obsolete
    DESCRIPTION 
        "This is the number of ACA messages received indicating success."
    ::= { offlineChargingStats 2 }

  bwDXSOfflineChargingACAFailureIn OBJECT-TYPE
    SYNTAX      Counter32
    MAX-ACCESS  read-write
    STATUS      obsolete
    DESCRIPTION 
        "This is the number of ACA messages received indicating failure."
    ::= { offlineChargingStats 3 }

  bwDXSOfflineChargingACRTimeout OBJECT-TYPE
    SYNTAX      Counter32
    MAX-ACCESS  read-write
    STATUS      obsolete
    DESCRIPTION 
        "This is the number ACR messages for which an ACA message has not been received before timeout."
    ::= { offlineChargingStats 4 }

  bwDXSOfflineChargingUnknownServer OBJECT-TYPE
    SYNTAX      Counter32
    MAX-ACCESS  read-write
    STATUS      obsolete
    DESCRIPTION 
        "This is the number of ACR messages not sent because one or more specified offline charging servers are not configured within BroadWorks."
    ::= { offlineChargingStats 5 }

  bwDXSOfflineChargingInvalidServer OBJECT-TYPE
    SYNTAX      Counter32
    MAX-ACCESS  read-write
    STATUS      obsolete
    DESCRIPTION 
        "This is the number of ACR messages not sent because the redundancy configuration of one or more specified offline charging server is incompatible with the requested destination."
    ::= { offlineChargingStats 6 }

  bwDXSOfflineChargingServerUnreachable OBJECT-TYPE
    SYNTAX      Counter32
    MAX-ACCESS  read-write
    STATUS      current
    DESCRIPTION 
        "This is the number of ACR messages not sent because none of the destination offline charging servers is currently connected."
    ::= { offlineChargingStats 7 }

  bwDXSOfflineChargingDFNDown OBJECT-TYPE
    SYNTAX      Counter32
    MAX-ACCESS  read-write
    STATUS      obsolete
    DESCRIPTION 
        "This is the number of ACR messages not sent because of communication failure with the DFN process."
    ::= { offlineChargingStats 8 }

  bwDXSOfflineChargingAPNError OBJECT-TYPE
    SYNTAX      Counter32
    MAX-ACCESS  read-write
    STATUS      obsolete
    DESCRIPTION 
        "This is the number of ACR messages not sent because of an error in the APN."
    ::= { offlineChargingStats 9 }

  bwDXSOfflineChargingQueued OBJECT-TYPE
    SYNTAX      Counter32
    MAX-ACCESS  read-write
    STATUS      current
    DESCRIPTION 
        "This is the number of offline charging requests that were written to the Application Server file-based queued due to the lack of a responsive offline charging server."
    ::= { offlineChargingStats 10 }

  bwDXSOfflineChargingTransmittedFromQueue OBJECT-TYPE
    SYNTAX      Counter32
    MAX-ACCESS  read-write
    STATUS      current
    DESCRIPTION 
        "This is the number of offline charging requests read from the Application Server file-based queue."
    ::= { offlineChargingStats 11 }

  bwDXSOfflineChargingRetransmittedFromQueue OBJECT-TYPE
    SYNTAX      Counter32
    MAX-ACCESS  read-write
    STATUS      current
    DESCRIPTION 
        "This is the number of retransmissions of offline charging request read from the Application Server file-based queue to an external offline charging server."
    ::= { offlineChargingStats 12 }

-- OCI-C Module ............................................
  bwDXSOCICNumOutgoingOverloadDiscard OBJECT-TYPE
    SYNTAX      Counter32
    MAX-ACCESS  read-write
    STATUS      current
    DESCRIPTION 
        "This is the number of retransmissions of offline charging request read from the Application Server file-based queue to an external offline charging server."
    ::= { ocicStats 1 }

  bwDXSOcicStatsTable OBJECT-TYPE
    SYNTAX      SEQUENCE OF BwOcicStatsEntry
    MAX-ACCESS  not-accessible
    STATUS      current
    DESCRIPTION 
        "This table contains OCI-C statistics."
    ::= { ocicStats 2 }

  bwDXSOcicStatsEntry OBJECT-TYPE
    SYNTAX      BwOcicStatsEntry
    MAX-ACCESS  not-accessible
    STATUS      current
    DESCRIPTION 
        "This row contains information on a particular OCI-C statistics table entry."
    INDEX       { bwDXSOCICStatsEntryIndex }
    ::= { bwDXSOcicStatsTable 1 }

  BwOcicStatsEntry ::= SEQUENCE {
    bwDXSOCICStatsEntryIndex               Unsigned32,
    bwDXSOCICApplicationId                 DisplayString,
    bwDXSOCICNumNoConnectionDiscard        Counter32,
    bwDXSOCICNumRouteExhaustionDiscard     Counter32,
    bwDXSOCICNumResponseTimeout            Counter32
  }

  bwDXSOCICStatsEntryIndex OBJECT-TYPE
    SYNTAX      Unsigned32
    MAX-ACCESS  read-only
    STATUS      current
    DESCRIPTION 
        "The index of an bwDXSOcicStatsEntry in the bwOcicStatsTable.  The index represents a specific OCI-C Application ID."
    ::= { bwDXSOcicStatsEntry 1 }

  bwDXSOCICApplicationId OBJECT-TYPE
    SYNTAX      DisplayString
    MAX-ACCESS  read-only
    STATUS      current
    DESCRIPTION 
        "The OCI-C Application ID for an bwDXSOcicStatsEntry in the bwOcicStatsTable."
    ::= { bwDXSOcicStatsEntry 2 }

  bwDXSOCICNumNoConnectionDiscard OBJECT-TYPE
    SYNTAX      Counter32
    MAX-ACCESS  read-write
    STATUS      current
    DESCRIPTION 
        "Number of outgoing OCI-C requests discarded because no connection was available."
    ::= { bwDXSOcicStatsEntry 3 }

  bwDXSOCICNumRouteExhaustionDiscard OBJECT-TYPE
    SYNTAX      Counter32
    MAX-ACCESS  read-write
    STATUS      current
    DESCRIPTION 
        "Number of outgoing OCI-C requests discarded due to route exhaustion."
    ::= { bwDXSOcicStatsEntry 4 }

  bwDXSOCICNumResponseTimeout OBJECT-TYPE
    SYNTAX      Counter32
    MAX-ACCESS  read-write
    STATUS      current
    DESCRIPTION 
        "Number of outgoing OCI-C requests discarded due to response timeout."
    ::= { bwDXSOcicStatsEntry 5 }

-- Online Charging Module ............................................
  bwDXSOnlineChargingCCROut OBJECT-TYPE
    SYNTAX      Counter32
    MAX-ACCESS  read-write
    STATUS      obsolete
    DESCRIPTION 
        "This is the number of CCR unique requests sent by BroadWorks.  If the request is transmitted multiple times, only the first transmission is counted."
    ::= { onlineChargingStats 1 }

  bwDXSOnlineChargingCCASuccessIn OBJECT-TYPE
    SYNTAX      Counter32
    MAX-ACCESS  read-write
    STATUS      obsolete
    DESCRIPTION 
        "This is the number of CCA messages received indicating success."
    ::= { onlineChargingStats 2 }

  bwDXSOnlineChargingCCAFailureIn OBJECT-TYPE
    SYNTAX      Counter32
    MAX-ACCESS  read-write
    STATUS      obsolete
    DESCRIPTION 
        "This is the number of CCA messages received indicating failure.  This does not include failure to grant credits, since this is a normal condition that does not indicate a problem with the system."
    ::= { onlineChargingStats 3 }

  bwDXSOnlineChargingCCRTimeout OBJECT-TYPE
    SYNTAX      Counter32
    MAX-ACCESS  read-write
    STATUS      obsolete
    DESCRIPTION 
        "This is the number of CCR messages for which a CCA message has not been received before timeout."
    ::= { onlineChargingStats 4 }

  bwDXSOnlineChargingUnknownServer OBJECT-TYPE
    SYNTAX      Counter32
    MAX-ACCESS  read-write
    STATUS      obsolete
    DESCRIPTION 
        "This is the number of CCR messages not sent because one or more specified online charging servers are not configured within BroadWorks."
    ::= { onlineChargingStats 5 }

  bwDXSOnlineChargingInvalidServer OBJECT-TYPE
    SYNTAX      Counter32
    MAX-ACCESS  read-write
    STATUS      obsolete
    DESCRIPTION 
        "This is the number of CCR messages not sent because the redundancy configuration of one or more specified online charging servers is incompatible with the requested destination."
    ::= { onlineChargingStats 6 }

  bwDXSOnlineChargingServerUnreachable OBJECT-TYPE
    SYNTAX      Counter32
    MAX-ACCESS  read-write
    STATUS      current
    DESCRIPTION 
        "This is the number of CCR messages not sent because none of the destination online charging servers is currently connected."
    ::= { onlineChargingStats 7 }

  bwDXSOnlineChargingDFNDown OBJECT-TYPE
    SYNTAX      Counter32
    MAX-ACCESS  read-write
    STATUS      obsolete
    DESCRIPTION 
        "This is the number of CCR messages not sent because of communication failure with the DFN process."
    ::= { onlineChargingStats 8 }

  bwDXSOnlineChargingAPNError OBJECT-TYPE
    SYNTAX      Counter32
    MAX-ACCESS  read-write
    STATUS      obsolete
    DESCRIPTION 
        "This is the number of CCR messages not sent because of an error in the APN."
    ::= { onlineChargingStats 9 }

-- BroadWorks Execution Server MIB Conformance Definition  ...........................................

  bwDXSExecutionMibGroups OBJECT IDENTIFIER 
    ::= { bwDXSExecutionMibConformance 1 }

  bwDXSExecutionMibCompliancy OBJECT IDENTIFIER
    ::= { bwDXSExecutionMibConformance 2 }

  bwDXSExecutionImsGroup OBJECT-GROUP
    OBJECTS     { bwDXSIMSSuccessfulConnectionAttempts, 
                  bwDXSIMSUnsuccessfulConnectionAttempts, 
                  bwDXSIMSSuccessfulDownLoadAttempts, 
                  bwDXSIMSUnsuccessfulDownLoadAttempts, bwDXSIMSMaxSessions, 
                  bwDXSIMSAvgSessions, bwDXSIMSMaxThreads, bwDXSIMSAvgThreads, 
                  bwDXSIMSMaxServiceTime, bwDXSIMSAvgServiceTime, 
                  bwDXSIMSNumKeepAlive, bwDXSIMSNumDroppedRequests }
    STATUS      current
    DESCRIPTION 
        "This group defines the statistics for the IMS protocol."
    ::= { bwDXSExecutionMibGroups 2 }

  bwDXSExecutionCapGroup OBJECT-GROUP
    OBJECTS     { bwDXSCAPStatsRegisterRequests, bwDXSCAPStatsUnRegistersIn, 
                  bwDXSCAPStatsUnRegistersOut, bwDXSCAPStatsSessionUpdatesOut, 
                  bwDXSCAPStatsProfileUpdatesOut, bwDXSCAPStatsCallUpdatesOut, 
                  bwDXSCAPStatsCallActionsIn, bwDXSCAPStatsAcknowledgementsIn, 
                  bwDXSCAPStatsAclViolations, 
                  bwDXSCAPStatsUnsuccessfulRegisterResponses, 
                  bwDXSCAPStatsCallControlInfosOut, 
                  bwDXSCAPStatsRegisterAuthentications, 
                  bwDXSCAPStatsResponseAuthentications, 
                  bwDXSCAPStatsInfoRequests, bwDXSCAPStatsInfoResponses, 
                  bwDXSCAPStatsExternalNotifies, 
                  bwDXSCAPMonitoringUsersRequests, 
                  bwDXSCAPMonitoringUsersResponses, 
                  bwDXSCAPStatsQueueUpdatesOut, bwDXSCAPStatsQueueActionsIn, 
                  bwDXSCAPStatsDatagramsIn, bwDXSCAPStatsDatagramsOut, 
                  bwDXSCAPStatsTotalMsgs, bwDXSCAPStatsRegisterResponsesType, 
                  bwDXSCAPStatsRegisterResponses, 
                  bwDXSCAPNumInboundDiscardedMessages, 
                  bwDXSCAPNumOutboundDiscardedMessages, bwDXSCAPNumConnections, 
                  bwDXSCAPNumDisconnections, bwDXSCAPNumCCC2Connections, 
                  bwDXSCAPNumCCC2Disconnections, 
                  bwDXSCAPNumCapSCallCenterConnections, 
                  bwDXSCAPNumCapSCallCenterDisconnections }
    STATUS      current
    DESCRIPTION 
        "This group defines the statistics for the CAP protocol."
    ::= { bwDXSExecutionMibGroups 3 }

  bwDXSExecutionSmdiGroup OBJECT-GROUP
    OBJECTS     { bwDXSSmdiNbOfActiveConnection, bwDXSSmdiNbOfOpenedConnection, 
                  bwDXSSmdiIncomingMWIActivationRequests, 
                  bwDXSSmdiIncomingMWIDesactivationRequests, 
                  bwDXSSmdiInvalidRequestsReceived, 
                  bwDXSSmdiBlockResponsesSent, bwDXSSmdiInvalidResponsesSent, 
                  bwDXSSmdiOutgoingMWIActivationRequests, 
                  bwDXSSmdiOutgoingMWIDeactivationRequests, 
                  bwDXSSmdiBlockResponsesReceived, 
                  bwDXSSmdiInvalidResponsesReceived, 
                  bwDXSSMDIMessageDeskMessageSent }
    STATUS      current
    DESCRIPTION 
        "This group defines the statistics for the SMDI protocol."
    ::= { bwDXSExecutionMibGroups 4 }

  bwDXSExecutionMediaResourceGroup OBJECT-GROUP
    OBJECTS     { bwDXSMediaCommandsTransmitted, 
                  bwDXSMediaNotificationsReceived, 
                  bwDXSMediaResourceAllocAttempts, 
                  bwDXSMediaResourceAllocFailures }
    STATUS      current
    DESCRIPTION 
        "This group defines the statistics for the Media Resource protocol."
    ::= { bwDXSExecutionMibGroups 5 }

  bwDXSExecutionWholeSalesGroup OBJECT-GROUP
    OBJECTS     { bwDXSWSPStatsServiceRequestsIn, 
                  bwDXSWSPStatsServiceActionsOut, 
                  bwDXSWSPStatsServiceUpdatesIn, 
                  bwDXSWSPStatsServiceAcknowledgementsOut }
    STATUS      current
    DESCRIPTION 
        "This group defines the statistics for the Whole Sales protocol."
    ::= { bwDXSExecutionMibGroups 6 }

  bwDXSExecutionRealTimeAccntGroup OBJECT-GROUP
    OBJECTS     { bwDXSRealtimeAccountingRequestsTransmitted, 
                  bwDXSRealtimeAccountingRequestsRetransmitted, 
                  bwDXSRealtimeAccountingRequestsDropped }
    STATUS      current
    DESCRIPTION 
        "This group defines the statistics for the Real Time Accounting protocol."
    ::= { bwDXSExecutionMibGroups 7 }

  bwDXSExecutionExtCallLogsGroup OBJECT-GROUP
    OBJECTS     { bwDXSExternalCallLogsTransmitted, 
                  bwDXSExternalCallLogsRetransmitted, 
                  bwDXSExternalCallLogsDropped, bwDXSExternalCallLogsQueued, 
                  bwDXSExternalCallLogsTransmittedFromQueue, 
                  bwDXSExternalCallLogsRetransmittedFromQueue }
    STATUS      current
    DESCRIPTION 
        "This group defines the statistics for the External Call Logs protocol."
    ::= { bwDXSExecutionMibGroups 8 }

  bwDXSExecutionXsBcctGroup OBJECT-GROUP
    OBJECTS     { bwDXSCommonCommXSStatsIndex, bwDXSCommonCommXSHost, 
                  bwDXSCommonCommXSInterface, bwDXSCommonCommXSProtocol, 
                  bwDXSCommonCommXSAcceptedOutboundConnections, 
                  bwDXSCommonCommXSAcceptedInboundConnections, 
                  bwDXSCommonCommXSRejectedOutboundConnections, 
                  bwDXSCommonCommXSRejectedInboundConnections, 
                  bwDXSCommonCommXSOutputMessagesProcessed, 
                  bwDXSCommonCommXSInputMessagesProcessed, 
                  bwDXSCommonCommXSOutputCommunicationErrors, 
                  bwDXSCommonCommXSInputCommunicationErrors }
    STATUS      current
    DESCRIPTION 
        "This group defines the statistics for the BCCT protocol for the Application Server Execution Server process."
    ::= { bwDXSExecutionMibGroups 9 }

  bwDXSExecutionCallpGroup OBJECT-GROUP
    OBJECTS     { bwDXSCallpNetworkOriginationAttempts, 
                  bwDXSCallpNetworkTerminationAttempts, 
                  bwDXSCallpNetworkTerminationsAnswered, 
                  bwDXSCallpUserOriginationAttempts, 
                  bwDXSCallpUserTerminationAttempts, 
                  bwDXSCallpUserTerminationsAnswered, 
                  bwDXSCallpEmergencyCallAttempts, 
                  bwDXSCallpEmergencyCallAlarms, bwDXSCallpActiveCalls, 
                  bwDXSCallpCallsPerSecond, 
                  bwDXSCallpMaximumNumberofSimCallsExceeded, 
                  bwDXSCallpMaximumCallTimeforAnsweredCallsExceeded, 
                  bwDXSCallpMaximumCallTimeforUnansweredCallsExceeded, 
                  bwDXSCallpActiveCallsAsPercentOfLicense, 
                  bwDXSCallpMaximumNumberofSimVideoCallsExceeded, 
                  bwDXSCallpMediaTypeNotSupported, 
                  bwDXSCallpRemoteOfficeEmergencyCallsBlocked,
                  bwDXSStateReplicationMessageSent,
                  bwDXSStateReplicationMessageReceived,
                  bwDXSStateReplicationOwnershipTaken,
                  bwDXSStateReplicationOwnershipGranted,
                  bwDXSStateReplicationRemoteLockTaken,
                  bwDXSStateReplicationRemoteLockGranted,
                  bwDXSCallpGETSOrigSessionCount,
                  bwDXSCallpGETSTermSessionCount,
                  bwDXSCallpInvalidGETSCount, bwDXSCallpE911PSAPCallBackAttempts,
                  bwDXSCallpSPIndex, bwDXSCallpSPID, 
                  bwDXSCallpSPUserOriginationAttempts, 
                  bwDXSCallpSPUserTerminationAttempts, 
                  bwDXSCallpSPUserTerminationsAnswered, 
                  bwDXSCallpSPEmergencyCallAttempts, 
                  bwDXSCallpSPMaximumNumberofSimCallsExceeded, 
                  bwDXSCallpSPMaximumCallTimeforAnsweredCallsExceeded, 
                  bwDXSCallpSPMaximumCallTimeforUnansweredCallsExceeded, 
                  bwDXSCallpSPMaximumNumberofSimVideoCallsExceeded, 
                  bwDXSCallpSPMediaTypeNotSupported, 
                  bwDXSCallpSPGETSOrigSessionCount,
                  bwDXSCallpSPGETSTermSessionCount, bwDXSCallpSPE911PSAPCallBackAttempts,
                  bwDXSCallpGroupIndex, bwDXSCallpGroupID, 
                  bwDXSCallpGroupUserOriginationAttempts, 
                  bwDXSCallpGroupUserTerminationAttempts, 
                  bwDXSCallpGroupUserTerminationsAnswered, 
                  bwDXSCallpGroupEmergencyCallAttempts, 
                  bwDXSCallpGroupMaximumNumberofSimCallsExceeded, 
                  bwDXSCallpGroupMaximumCallTimeforAnsweredCallsExceeded, 
                  bwDXSCallpGroupMaximumCallTimeforUnansweredCallsExceeded, 
                  bwDXSCallpGroupMaximumNumberofSimVideoCallsExceeded, 
                  bwDXSCallpGroupMediaTypeNotSupported,
                  bwDXSCallpGroupGETSOrigSessionCount,
                  bwDXSCallpGroupGETSTermSessionCount, bwDXSCallpGroupE911PSAPCallBackAttempts
                   }
    STATUS      current
    DESCRIPTION 
        "This group defines the statistics for call processing."
    ::= { bwDXSExecutionMibGroups 10 }

  bwDXSExecutionSmtpGroup OBJECT-GROUP
    OBJECTS     { bwDXSSMTPTotalPrimaryEmailSendAttempts, 
                  bwDXSSMTPTotalSecondaryEmailSendAttempts, 
                  bwDXSSMTPPrimaryUnSuccessfulEmailSendAttempts, 
                  bwDXSSMTPSecondaryUnSuccessfulEmailSendAttempts }
    STATUS      current
    DESCRIPTION 
        "This group defines the statistics for the SMTP protocol."
    ::= { bwDXSExecutionMibGroups 11 }

  bwDXSExecutionSipGroup OBJECT-GROUP
    OBJECTS     { bwDXSSipSummaryTotalTransactions, bwDXSSipStatsInviteIns, 
                  bwDXSSipStatsInviteOuts, bwDXSSipStatsAckIns, 
                  bwDXSSipStatsAckOuts, bwDXSSipStatsByeIns, bwDXSSipStatsByeOuts, 
                  bwDXSSipStatsCancelIns, bwDXSSipStatsCancelOuts, 
                  bwDXSSipStatsOptionsIns, bwDXSSipStatsOptionsOuts, 
                  bwDXSSipStatsRegisterIns, bwDXSSipStatsRegisterOuts, 
                  bwDXSSipStatsInfoIns, bwDXSSipStatsInfoOuts, 
                  bwDXSSipStatsNotifyIns, bwDXSSipStatsNotifyOuts, 
                  bwDXSSipStatsPrackIns, bwDXSSipStatsPrackOuts, 
                  bwDXSSipStatsOtherIns, bwDXSSipStatsOtherOuts, 
                  bwDXSSipStatsInviteResponseIns, 
                  bwDXSSipStatsInviteResponseOuts, bwDXSSipStatsByeResponseIns, 
                  bwDXSSipStatsByeResponseOuts, bwDXSSipStatsCancelResponseIns, 
                  bwDXSSipStatsCancelResponseOuts, 
                  bwDXSSipStatsOptionsResponseIns, 
                  bwDXSSipStatsOptionsResponseOuts, 
                  bwDXSSipStatsRegisterResponseIns, 
                  bwDXSSipStatsRegisterResponseOuts, 
                  bwDXSSipStatsPrackResponseIns, 
                  bwDXSSipStatsPrackResponseOuts, bwDXSSipStatsInfoResponseIns, 
                  bwDXSSipStatsInfoResponseOuts, 
                  bwDXSSipStatsNotifyResponseIns, 
                  bwDXSSipStatsNotifyResponseOuts, 
                  bwDXSSipStatsOtherResponseIns, 
                  bwDXSSipStatsOtherResponseOuts, bwDXSSipStatsRetryInvites, 
                  bwDXSSipStatsRetryByes, bwDXSSipStatsRetryCancels, 
                  bwDXSSipStatsRetryResponses, bwDXSSipStatsSubscribeIns, 
                  bwDXSSipStatsSubscribeOuts, bwDXSSipStatsMessageIns, 
                  bwDXSSipStatsMessageOuts, bwDXSSipStatsSubscribeResponseIns, 
                  bwDXSSipStatsSubscribeResponseOuts, 
                  bwDXSSipStatsMessageResponseIns, 
                  bwDXSSipStatsMessageResponseOuts, bwDXSSipStatsUpdateIns, 
                  bwDXSSipStatsUpdateOuts, bwDXSSipStatsUpdateResponseIns, 
                  bwDXSSipStatsUpdateResponseOuts, 
                  bwDXSSipStatsSetupSignalDelay, 
                  bwDXSSipStatsMinSetupSignalDelay, 
                  bwDXSSipStatsMaxSetupSignalDelay, 
                  bwDXSSipStatsAnswerSignalDelay, 
                  bwDXSSipStatsMinAnswerSignalDelay, 
                  bwDXSSipStatsMaxAnswerSignalDelay, 
                  bwDXSSipStatsRegistrationsPerMinute, 
                  bwDXSSipStatsMsgRetryPercentageToOther, 
                  bwDXSSipStatsMsgRetryToNeID, bwDXSSipStatsMsgRetryToNeAddr, 
                  bwDXSSipStatsMsgRetryToNePercentage, 
                  bwDXSSipStatsActiveTcpConnections, bwDXSSipStatsTcpIns, 
                  bwDXSSipStatsTcpOuts, bwDXSSipStatsTcpFailures, 
                  bwDXSSipStatsUdpIns, bwDXSSipStatsUdpOuts, 
                  bwDXSSIPReclaimedStaleTcpConnections, bwDXSSipStatsPublishIns,
                  bwDXSSipStatsPublishOuts, bwDXSSipStatsPublishResponseCodeValue,
                  bwDXSSipStatsPublishResponseIns, bwDXSSipStatsPublishResponseOuts }
    STATUS      current
    DESCRIPTION 
        "This group defines the statistics for the SIP protocol."
    ::= { bwDXSExecutionMibGroups 12 }

  bwDXSExecutionAccntCodeServiceGroup OBJECT-GROUP
    OBJECTS     { bwDXSAuthCodeNumAttempts, bwDXSAuthCodeNumValidations, 
                  bwDXSAccountCodeNumAttempts, 
                  bwDXSAccountCodeNumPerCallAttempts, bwDXSAccountCodesSPIndex, 
                  bwDXSAccountCodesSPID, bwDXSAuthCodeSPNumAttempts, 
                  bwDXSAuthCodeSPNumValidations, bwDXSAccountCodeSPNumAttempts, 
                  bwDXSAccountCodeSPNumPerCallAttempts, 
                  bwDXSAccountCodesGroupIndex, bwDXSAccountCodesGroupID, 
                  bwDXSAuthCodeGroupNumAttempts, 
                  bwDXSAuthCodeGroupNumValidations, 
                  bwDXSAccountCodeGroupNumAttempts, 
                  bwDXSAccountCodeGroupNumPerCallAttempts }
    STATUS      current
    DESCRIPTION 
        "This group defines the statistics for the Account Code Service."
    ::= { bwDXSExecutionMibGroups 13 }

  bwDXSExecutionAnonymousCallRejectionServiceGroup OBJECT-GROUP
    OBJECTS     { bwDXSAnonymousCallsNumRejected, 
                  bwDXSAnonymousCallRejectionSPIndex, 
                  bwDXSAnonymousCallRejectionSPID, 
                  bwDXSAnonymousCallsSPNumRejected, 
                  bwDXSAnonymousCallRejectionGroupIndex, 
                  bwDXSAnonymousCallRejectionGroupID, 
                  bwDXSAnonymousCallsGroupNumRejected }
    STATUS      current
    DESCRIPTION 
        "This group defines the statistics for the Anonymous Call Rejection Service."
    ::= { bwDXSExecutionMibGroups 14 }

  bwDXSExecutionAuthenticationServiceGroup OBJECT-GROUP
    OBJECTS     { bwDXSAuthenticationNumChallenges, 
                  bwDXSAuthenticationNumValidResponses, 
                  bwDXSAuthenticationSPIndex, bwDXSAuthenticationSPID, 
                  bwDXSAuthenticationSPNumChallenges, 
                  bwDXSAuthenticationSPNumValidResponses, 
                  bwDXSAuthenticationGroupIndex, bwDXSAuthenticationGroupID, 
                  bwDXSAuthenticationGroupNumChallenges, 
                  bwDXSAuthenticationGroupNumValidResponses }
    STATUS      current
    DESCRIPTION 
        "This group defines the statistics for the Authentication Service."
    ::= { bwDXSExecutionMibGroups 15 }

  bwDXSExecutionAutoAttendantServiceGroup OBJECT-GROUP
    OBJECTS     { bwDXSAutoAttendantNumAnswers, bwDXSAutoAttendantNumTransfers, 
                  bwDXSAutoAttendantSPIndex, bwDXSAutoAttendantSPID, 
                  bwDXSAutoAttendantSPNumAnswers, 
                  bwDXSAutoAttendantSPNumTransfers, 
                  bwDXSAutoAttendantGroupIndex, bwDXSAutoAttendantGroupID, 
                  bwDXSAutoAttendantGroupNumAnswers, 
                  bwDXSAutoAttendantGroupNumTransfers }
    STATUS      current
    DESCRIPTION 
        "This group defines the statistics for the Auto Attendant Service."
    ::= { bwDXSExecutionMibGroups 16 }

  bwDXSExecutionCallCapacityServiceGroup OBJECT-GROUP
    OBJECTS     { bwDXSCallCapacityNumCallsAttempted, 
                  bwDXSCallCapacityNumCallsBlocked, bwDXSCallCapacitySPIndex, 
                  bwDXSCallCapacitySPID, bwDXSCallCapacitySPNumCallsAttempted, 
                  bwDXSCallCapacitySPNumCallsBlocked, 
                  bwDXSCallCapacityGroupIndex, bwDXSCallCapacityGroupID, 
                  bwDXSCallCapacityGroupNumCallsAttempted, 
                  bwDXSCallCapacityGroupNumCallsBlocked }
    STATUS      current
    DESCRIPTION 
        "This group defines the statistics for the Call Capacity Service."
    ::= { bwDXSExecutionMibGroups 17 }

  bwDXSExecutionCFAlwaysServiceGroup OBJECT-GROUP
    OBJECTS     { bwDXSCFANumForwarded, bwDXSCFANumPhoneActivations, 
                  bwDXSCFANumPhoneDeactivations, bwDXSCFADestinationChanged, 
                  bwDXSCFANumPhoneInterrogation, 
                  bwDXSCallForwardingAlwaysSPIndex, 
                  bwDXSCallForwardingAlwaysSPID, bwDXSCFASPNumForwarded, 
                  bwDXSCFASPNumPhoneActivations, 
                  bwDXSCFASPNumPhoneDeactivations, 
                  bwDXSCFASPDestinationChanged, 
                  bwDXSCFASPNumPhoneInterrogation, 
                  bwDXSCallForwardingAlwaysGroupIndex, 
                  bwDXSCallForwardingAlwaysGroupID, bwDXSCFAGroupNumForwarded, 
                  bwDXSCFAGroupNumPhoneActivations, 
                  bwDXSCFAGroupNumPhoneDeactivations, 
                  bwDXSCFAGroupDestinationChanged, 
                  bwDXSCFAGroupNumPhoneInterrogation }
    STATUS      current
    DESCRIPTION 
        "This group defines the statistics for the Call Forward Always Service."
    ::= { bwDXSExecutionMibGroups 18 }

  bwDXSExecutionCFBusyServiceGroup OBJECT-GROUP
    OBJECTS     { bwDXSCFBNumForwarded, bwDXSCFBNumPhoneActivations, 
                  bwDXSCFBNumPhoneDeactivations, bwDXSCFBDestinationChanged, 
                  bwDXSCFBNumPhoneInterrogation, 
                  bwDXSCallForwardingBusySPIndex, bwDXSCallForwardingBusySPID, 
                  bwDXSCFBSPNumForwarded, bwDXSCFBSPNumPhoneActivations, 
                  bwDXSCFBSPNumPhoneDeactivations, 
                  bwDXSCFBSPDestinationChanged, 
                  bwDXSCFBSPNumPhoneInterrogation, 
                  bwDXSCallForwardingBusyGroupIndex, 
                  bwDXSCallForwardingBusyGroupID, bwDXSCFBGroupNumForwarded, 
                  bwDXSCFBGroupNumPhoneActivations, 
                  bwDXSCFBGroupNumPhoneDeactivations, 
                  bwDXSCFBGroupDestinationChanged, 
                  bwDXSCFBGroupNumPhoneInterrogation }
    STATUS      current
    DESCRIPTION 
        "This group defines the statistics for the Call Forward Busy Service."
    ::= { bwDXSExecutionMibGroups 19 }

  bwDXSExecutionCFNoAnswerServiceGroup OBJECT-GROUP
    OBJECTS     { bwDXSCFNANumForwarded, bwDXSCFNADestinationChanged, 
                  bwDXSCFNANumPhoneActivations, bwDXSCFNANumPhoneDeactivations, 
                  bwDXSCFNANumPhoneInterrogation, 
                  bwDXSCallForwardingNoAnswerSPIndex, 
                  bwDXSCallForwardingNoAnswerSPID, bwDXSCFNASPNumForwarded, 
                  bwDXSCFNASPDestinationChanged, 
                  bwDXSCFNASPNumPhoneActivations, 
                  bwDXSCFNASPNumPhoneDeactivations, 
                  bwDXSCFNASPNumPhoneInterrogation, 
                  bwDXSCallForwardingNoAnswerGroupIndex, 
                  bwDXSCallForwardingNoAnswerGroupID, 
                  bwDXSCFNAGroupNumForwarded, bwDXSCFNAGroupDestinationChanged, 
                  bwDXSCFNAGroupNumPhoneActivations, 
                  bwDXSCFNAGroupNumPhoneDeactivations, 
                  bwDXSCFNAGroupNumPhoneInterrogation }
    STATUS      current
    DESCRIPTION 
        "This group defines the statistics for the Call Forward No-Answer Service."
    ::= { bwDXSExecutionMibGroups 20 }

  bwDXSExecutionCallNotifyServiceGroup OBJECT-GROUP
    OBJECTS     { bwDXSCallNotifyNumNotifications, bwDXSCallNotifySPIndex, 
                  bwDXSCallNotifySPID, bwDXSCallNotifySPNumNotifications, 
                  bwDXSCallNotifyGroupIndex, bwDXSCallNotifyGroupID, 
                  bwDXSCallNotifyGroupNumNotifications }
    STATUS      current
    DESCRIPTION 
        "This group defines the statistics for the Call Notify Service."
    ::= { bwDXSExecutionMibGroups 21 }

  bwDXSExecutionCallParkServiceGroup OBJECT-GROUP
    OBJECTS     { bwDXSCallParkNumAttempts, bwDXSCallParkNumFailures, 
                  bwDXSCallParkNumRetrieveAttempts, 
                  bwDXSCallParkNumRetrieveFailures, bwDXSCallParkSPIndex, 
                  bwDXSCallParkSPID, bwDXSCallParkSPNumAttempts, 
                  bwDXSCallParkSPNumFailures, 
                  bwDXSCallParkSPNumRetrieveAttempts, 
                  bwDXSCallParkSPNumRetrieveFailures, bwDXSCallParkGroupIndex, 
                  bwDXSCallParkGroupID, bwDXSCallParkGroupNumAttempts, 
                  bwDXSCallParkGroupNumFailures, 
                  bwDXSCallParkGroupNumRetrieveAttempts, 
                  bwDXSCallParkGroupNumRetrieveFailures }
    STATUS      current
    DESCRIPTION 
        "This group defines the statistics for the Call Park Service."
    ::= { bwDXSExecutionMibGroups 22 }

  bwDXSExecutionCallPickupServiceGroup OBJECT-GROUP
    OBJECTS     { bwDXSCallPickupNumAttempts, bwDXSCallPickupNumFailures, 
                  bwDXSCallPickupSPIndex, bwDXSCallPickupSPID, 
                  bwDXSCallPickupSPNumAttempts, bwDXSCallPickupSPNumFailures, 
                  bwDXSCallPickupGroupIndex, bwDXSCallPickupGroupID, 
                  bwDXSCallPickupGroupNumAttempts, 
                  bwDXSCallPickupGroupNumFailures }
    STATUS      current
    DESCRIPTION 
        "This group defines the statistics for the Call Pickup Service."
    ::= { bwDXSExecutionMibGroups 23 }

  bwDXSExecutionCallReturnServiceGroup OBJECT-GROUP
    OBJECTS     { bwDXSCallReturnNumReturns, bwDXSCallReturnSPIndex, 
                  bwDXSCallReturnSPID, bwDXSCallReturnSPNumReturns, 
                  bwDXSCallReturnGroupIndex, bwDXSCallReturnGroupID, 
                  bwDXSCallReturnGroupNumReturns }
    STATUS      current
    DESCRIPTION 
        "This group defines the statistics for the Call Return Service."
    ::= { bwDXSExecutionMibGroups 24 }

  bwDXSExecutionCompilotCallMgrServiceGroup OBJECT-GROUP
    OBJECTS     { bwDXSCommPilotCallMgrNumDial, bwDXSCommPilotCallMgrNumAnswer, 
                  bwDXSCommPilotCallMgrNumRelease, 
                  bwDXSCommPilotCallMgrNumHold, 
                  bwDXSCommPilotCallMgrNumTransfer, 
                  bwDXSCommPilotCallMgrNumConference, 
                  bwDXSCommPilotCallMgrNumTransferVM, 
                  bwDXSCommPilotCallMgrNumConferenceAnswer, 
                  bwDXSCommPilotCallMgrNumConferenceHold, 
                  bwDXSCommPilotCallMgrNumConferenceRelease, 
                  bwDXSCommPilotCallMgrNumTransferCC, 
                  bwDXSCommPilotCallMgrNumConferenceAdd, 
                  bwDXSCommPilotCallManagerSPIndex, 
                  bwDXSCommPilotCallManagerSPID, 
                  bwDXSCommPilotCallMgrSPNumDial, 
                  bwDXSCommPilotCallMgrSPNumAnswer, 
                  bwDXSCommPilotCallMgrSPNumRelease, 
                  bwDXSCommPilotCallMgrSPNumHold, 
                  bwDXSCommPilotCallMgrSPNumTransfer, 
                  bwDXSCommPilotCallMgrSPNumConference, 
                  bwDXSCommPilotCallMgrSPNumTransferVM, 
                  bwDXSCommPilotCallMgrSPNumConferenceAnswer, 
                  bwDXSCommPilotCallMgrSPNumConferenceHold, 
                  bwDXSCommPilotCallMgrSPNumConferenceRelease, 
                  bwDXSCommPilotCallMgrSPNumTransferCC, 
                  bwDXSCommPilotCallMgrSPNumConferenceAdd, 
                  bwDXSCommPilotCallManagerGroupIndex, 
                  bwDXSCommPilotCallManagerGroupID, 
                  bwDXSCommPilotCallMgrGroupNumDial, 
                  bwDXSCommPilotCallMgrGroupNumAnswer, 
                  bwDXSCommPilotCallMgrGroupNumRelease, 
                  bwDXSCommPilotCallMgrGroupNumHold, 
                  bwDXSCommPilotCallMgrGroupNumTransfer, 
                  bwDXSCommPilotCallMgrGroupNumConference, 
                  bwDXSCommPilotCallMgrGroupNumTransferVM, 
                  bwDXSCommPilotCallMgrGroupNumConferenceAnswer, 
                  bwDXSCommPilotCallMgrGroupNumConferenceHold, 
                  bwDXSCommPilotCallMgrGroupNumConferenceRelease, 
                  bwDXSCommPilotCallMgrGroupNumTransferCC, 
                  bwDXSCommPilotCallMgrGroupNumConferenceAdd, 
                  bwDXSCommPilotCallMgrNumCallPark, 
                  bwDXSCommPilotCallMgrNumGroupCallPark, 
                  bwDXSCommPilotCallMgrNumCallParkRetrieve, 
                  bwDXSCommPilotCallMgrSPNumCallPark, 
                  bwDXSCommPilotCallMgrSPNumGroupCallPark, 
                  bwDXSCommPilotCallMgrSPNumCallParkRetrieve, 
                  bwDXSCommPilotCallMgrGroupNumCallPark, 
                  bwDXSCommPilotCallMgrGroupNumGroupCallPark, 
                  bwDXSCommPilotCallMgrGroupNumCallParkRetrieve }
    STATUS      current
    DESCRIPTION 
        "This group defines the statistics for the CommPilot Call Manager Service."
    ::= { bwDXSExecutionMibGroups 25 }

  bwDXSExecutionDoNotDisturbServiceGroup OBJECT-GROUP
    OBJECTS     { bwDXSDoNotDisturbNumInvoked, bwDXSDndPhoneActivations, 
                  bwDXSDndPhoneDeactivations, bwDXSDoNotDisturbSPIndex, 
                  bwDXSDoNotDisturbSPID, bwDXSDoNotDisturbSPNumInvoked, 
                  bwDXSDNDSPNumPhoneActivations, 
                  bwDXSDNDSPNumPhoneDeactivations, bwDXSDoNotDisturbGroupIndex, 
                  bwDXSDoNotDisturbGroupID, bwDXSDoNotDisturbGroupNumInvoked, 
                  bwDXSDNDGroupNumPhoneActivations, 
                  bwDXSDNDGroupNumPhoneDeactivations }
    STATUS      current
    DESCRIPTION 
        "This group defines the statistics for the Do Not Disturb Service."
    ::= { bwDXSExecutionMibGroups 26 }

  bwDXSExecutionFlashCallXferServiceGroup OBJECT-GROUP
    OBJECTS     { bwDXSFlashCallTransferNumTransfers, 
                  bwDXSFlashCallTransferSPIndex, bwDXSFlashCallTransferSPID, 
                  bwDXSFlashCallTransferSPNumTransfers, 
                  bwDXSFlashCallTransferGroupIndex, 
                  bwDXSFlashCallTransferGroupID, 
                  bwDXSFlashCallTransferGroupNumTransfers }
    STATUS      current
    DESCRIPTION 
        "This group defines the statistics for Flash Call Xfer Service."
    ::= { bwDXSExecutionMibGroups 27 }

  bwDXSExecutionFlashCallWaitingServiceGroup OBJECT-GROUP
    OBJECTS     { bwDXSFlashCallWaitingNumAnswers, 
                  bwDXSFlashCallWaitingSPIndex, bwDXSFlashCallWaitingSPID, 
                  bwDXSFlashCallWaitingSPNumAnswers, 
                  bwDXSFlashCallWaitingGroupIndex, 
                  bwDXSFlashCallWaitingGroupID, 
                  bwDXSFlashCallWaitingGroupNumAnswers }
    STATUS      current
    DESCRIPTION 
        "This group defines the statistics for Flash Call Waiting Service."
    ::= { bwDXSExecutionMibGroups 28 }

  bwDXSExecutionFlashConsultationServiceGroup OBJECT-GROUP
    OBJECTS     { bwDXSFlashConsultationNumCalls, 
                  bwDXSFlashConsultationSPIndex, bwDXSFlashConsultationSPID, 
                  bwDXSFlashConsultationSPNumCalls, 
                  bwDXSFlashConsultationGroupIndex, 
                  bwDXSFlashConsultationGroupID, 
                  bwDXSFlashConsultationGroupNumCalls }
    STATUS      current
    DESCRIPTION 
        "This group defines the statistics for Flash Consultation Service."
    ::= { bwDXSExecutionMibGroups 29 }

  bwDXSExecutionFlash3wcServiceGroup OBJECT-GROUP
    OBJECTS     { bwDXSFlashThreeWayCallNum3WC, bwDXSFlashThreeWayCallSPIndex, 
                  bwDXSFlashThreeWayCallSPID, bwDXSFlashThreeWayCallSPNum3WC, 
                  bwDXSFlashThreeWayCallGroupIndex, 
                  bwDXSFlashThreeWayCallGroupID, 
                  bwDXSFlashThreeWayCallGroupNum3WC }
    STATUS      current
    DESCRIPTION 
        "This group defines the statistics for Flash Three Way Calling Service."
    ::= { bwDXSExecutionMibGroups 30 }

  bwDXSExecutionHuntGroupServiceGroup OBJECT-GROUP
    OBJECTS     { bwDXSHuntGroupNumAttempts, bwDXSHuntGroupNumBusy, 
                  bwDXSHuntGroupsSPIndex, bwDXSHuntGroupsSPID, 
                  bwDXSHuntGroupSPNumAttempts, bwDXSHuntGroupSPNumBusy,
                  bwDXSHuntGroupsGroupIndex, bwDXSHuntGroupsGroupID, 
                  bwDXSHuntGroupsGroupNumAttempts, bwDXSHuntGroupsGroupNumBusy }
    STATUS      current
    DESCRIPTION 
        "This group defines the statistics for the Hunt Group Service."
    ::= { bwDXSExecutionMibGroups 31 }

  bwDXSExecutionIcpServiceGroup OBJECT-GROUP
    OBJECTS     { bwDXSICPNumInterGroupBlocks, bwDXSICPNumCollectCallBlocks, 
                  bwDXSICPNumIntraGroupBlocks, bwDXSICPNumOutsideCallerBlocks, 
                  bwDXSIncomingCallingPlanSPIndex, 
                  bwDXSIncomingCallingPlanSPID, bwDXSICPSPNumInterGroupBlocks, 
                  bwDXSICPSPNumCollectCallBlocks, 
                  bwDXSICPSPNumIntraGroupBlocks, 
                  bwDXSICPSPNumOutsideCallerBlocks, 
                  bwDXSIncomingCallingPlanGroupIndex, 
                  bwDXSIncomingCallingPlanGroupID, 
                  bwDXSICPGroupNumInterGroupBlocks, 
                  bwDXSICPGroupNumCollectCallBlocks, 
                  bwDXSICPGroupNumIntraGroupBlocks, 
                  bwDXSICPGroupNumOutsideCallerBlocks }
    STATUS      current
    DESCRIPTION 
        "This group defines the statistics for the Incoming Calling Plan Service."
    ::= { bwDXSExecutionMibGroups 32 }

  bwDXSExecutionIpPhoneServiceGroup OBJECT-GROUP
    OBJECTS     { bwDXSIPPhoneNumForwards, bwDXSIPPhoneSPIndex, bwDXSIPPhoneSPID, 
                  bwDXSIPPhoneSPNumForwards, bwDXSIPPhoneGroupIndex, 
                  bwDXSIPPhoneGroupID, bwDXSIPPhoneGroupNumForwards }
    STATUS      current
    DESCRIPTION 
        "This group defines the statistics for the IP Phone Service."
    ::= { bwDXSExecutionMibGroups 33 }

  bwDXSExecutionLastNumberRedialServiceGroup OBJECT-GROUP
    OBJECTS     { bwDXSLNRNumRedials, bwDXSLastNumberRedialSPIndex, 
                  bwDXSLastNumberRedialSPID, bwDXSLNRSPNumRedials, 
                  bwDXSLastNumberRedialGroupIndex, 
                  bwDXSLastNumberRedialGroupID, bwDXSLNRGroupNumRedials }
    STATUS      current
    DESCRIPTION 
        "This group defines the statistics for the Last Number Redial Service."
    ::= { bwDXSExecutionMibGroups 34 }

  bwDXSExecutionOcpServiceGroup OBJECT-GROUP
    OBJECTS     { bwDXSOCPNumGroupCallsBlocked, bwDXSOCPNumLocalCallsBlocked, 
                  bwDXSOCPNumTollFreeCallsBlocked, bwDXSOCPNumTollCallsBlocked, 
                  bwDXSOCPNumIntlCallsBlocked, 
                  bwDXSOCPNumOperatorAssistedCallsBlocked, 
                  bwDXSOCPNumChargeableDirAssistCallsBlocked, 
                  bwDXSOCPNumSpecialServices1CallsBlocked, 
                  bwDXSOCPNumSpecialServices2CallsBlocked, 
                  bwDXSOCPNumPremiumServices1CallsBlocked, 
                  bwDXSOCPNumPremiumServices2CallsBlocked, 
                  bwDXSOCPNumCasualCallsBlocked, 
                  bwDXSOCPNumURLDialingCallsBlocked, 
                  bwDXSOCPNumUnknownCallsBlocked, 
                  bwDXSOCPNumSuccessfulAuthorizations, 
                  bwDXSOCPNumUnsuccessfulAuthorizations, bwDXSOCPNumTransfers, 
                  bwDXSOCPSACNumSuccessfulLock, bwDXSOCPSACNumSuccessfulUnlock, 
                  bwDXSOCPSACNumUnsuccessfulLock, 
                  bwDXSOCPSACNumUnsuccessfulUnlock, 
                  bwDXSOCPSACNumUnsuccessfulCodeUsage, 
                  bwDXSOCPNumOutsideGroupTransferBlocks, 
                  bwDXSOutgoingCallingPlanSPIndex, 
                  bwDXSOutgoingCallingPlanSPID, bwDXSOCPSPNumGroupCallsBlocked, 
                  bwDXSOCPSPNumLocalCallsBlocked, 
                  bwDXSOCPSPNumTollFreeCallsBlocked, 
                  bwDXSOCPSPNumTollCallsBlocked, bwDXSOCPSPNumIntlCallsBlocked, 
                  bwDXSOCPSPNumOperatorAssistedCallsBlocked, 
                  bwDXSOCPSPNumChargeableDirAssistCallsBlocked, 
                  bwDXSOCPSPNumSpecialServices1CallsBlocked, 
                  bwDXSOCPSPNumSpecialServices2CallsBlocked, 
                  bwDXSOCPSPNumPremiumServices1CallsBlocked, 
                  bwDXSOCPSPNumPremiumServices2CallsBlocked, 
                  bwDXSOCPSPNumCasualCallsBlocked, 
                  bwDXSOCPSPNumURLDialingCallsBlocked, 
                  bwDXSOCPSPNumUnknownCallsBlocked, 
                  bwDXSOCPSPNumSuccessfulAuthorizations, 
                  bwDXSOCPSPNumUnsuccessfulAuthorizations, 
                  bwDXSOCPSPNumTransfers, bwDXSOCPSACSPNumSuccessfulLock, 
                  bwDXSOCPSACSPNumSuccessfulUnlock, 
                  bwDXSOCPSACSPNumUnsuccessfulLock, 
                  bwDXSOCPSACSPNumUnsuccessfulUnlock, 
                  bwDXSOCPSACSPNumUnsuccessfulCodeUsage, 
                  bwDXSOCPSPNumOutsideGroupTransferBlocks, 
                  bwDXSOutgoingCallingPlanGroupIndex, 
                  bwDXSOutgoingCallingPlanGroupID, 
                  bwDXSOCPGroupNumGroupCallsBlocked, 
                  bwDXSOCPGroupNumLocalCallsBlocked, 
                  bwDXSOCPGroupNumTollFreeCallsBlocked, 
                  bwDXSOCPGroupNumTollCallsBlocked, 
                  bwDXSOCPGroupNumIntlCallsBlocked, 
                  bwDXSOCPGroupNumOperatorAssistedCallsBlocked, 
                  bwDXSOCPGroupNumChargeableDirAssistCallsBlocked, 
                  bwDXSOCPGroupNumSpecialServices1CallsBlocked, 
                  bwDXSOCPGroupNumSpecialServices2CallsBlocked, 
                  bwDXSOCPGroupNumPremiumServices1CallsBlocked, 
                  bwDXSOCPGroupNumPremiumServices2CallsBlocked, 
                  bwDXSOCPGroupNumCasualCallsBlocked, 
                  bwDXSOCPGroupNumURLDialingCallsBlocked, 
                  bwDXSOCPGroupNumUnknownCallsBlocked, 
                  bwDXSOCPGroupNumSuccessfulAuthorizations, 
                  bwDXSOCPGroupNumUnsuccessfulAuthorizations, 
                  bwDXSOCPGroupNumTransfers, bwDXSOCPSACGroupNumSuccessfulLock, 
                  bwDXSOCPSACGroupNumSuccessfulUnlock, 
                  bwDXSOCPSACGroupNumUnsuccessfulLock, 
                  bwDXSOCPSACGroupNumUnsuccessfulUnlock, 
                  bwDXSOCPSACGroupNumUnsuccessfulCodeUsage, 
                  bwDXSOCPGroupNumOutsideGroupTransferBlocks }
    STATUS      current
    DESCRIPTION 
        "This group defines the statistics for the Outgoing Calling Plan Service."
    ::= { bwDXSExecutionMibGroups 35 }

  bwDXSExecutionPriorityAlertServiceGroup OBJECT-GROUP
    OBJECTS     { bwDXSPriorityAlertNumDistinctive, bwDXSPriorityAlertSPIndex, 
                  bwDXSPriorityAlertSPID, bwDXSPriorityAlertSPNumDistinctive, 
                  bwDXSPriorityAlertGroupIndex, bwDXSPriorityAlertGroupID, 
                  bwDXSPriorityAlertGroupNumDistinctive }
    STATUS      current
    DESCRIPTION 
        "This group defines the statistics for the Priority Alert Service."
    ::= { bwDXSExecutionMibGroups 36 }

  bwDXSExecutionSelectiveCallAcceptanceServiceGroup OBJECT-GROUP
    OBJECTS     { bwDXSSCANumAcceptances, bwDXSSelectiveCallAcceptanceSPIndex, 
                  bwDXSSelectiveCallAcceptanceSPID, bwDXSSCASPNumAcceptances, 
                  bwDXSSelectiveCallAcceptanceGroupIndex, 
                  bwDXSSelectiveCallAcceptanceGroupID, 
                  bwDXSSCAGroupNumAcceptances }
    STATUS      current
    DESCRIPTION 
        "This group defines the statistics for the Selective Call Acceptance Service."
    ::= { bwDXSExecutionMibGroups 37 }

  bwDXSExecutionSelectiveCallForwardServiceGroup OBJECT-GROUP
    OBJECTS     { bwDXSSCFNumForwards, bwDXSSCFNumPhoneActivations, 
                  bwDXSSCFNumPhoneDeactivations, 
                  bwDXSSelectiveCallForwardSPIndex, 
                  bwDXSSelectiveCallForwardSPID, bwDXSSCFSPNumForwards, 
                  bwDXSSCFSPNumPhoneActivations, 
                  bwDXSSCFSPNumPhoneDeactivations, 
                  bwDXSSelectiveCallForwardGroupIndex, 
                  bwDXSSelectiveCallForwardGroupID, bwDXSSCFGroupNumForwards, 
                  bwDXSSCFGroupNumPhoneActivations, 
                  bwDXSSCFGroupNumPhoneDeactivations }
    STATUS      current
    DESCRIPTION 
        "This group defines the statistics for the Selective Call Forward Service."
    ::= { bwDXSExecutionMibGroups 38 }

  bwDXSExecutionSelectiveCallRejectionServiceGroup OBJECT-GROUP
    OBJECTS     { bwDXSSCRNumRejects, bwDXSSelectiveCallRejectionSPIndex, 
                  bwDXSSelectiveCallRejectionSPID, bwDXSSCRSPNumRejects, 
                  bwDXSSelectiveCallRejectionGroupIndex, 
                  bwDXSSelectiveCallRejectionGroupID, bwDXSSCRGroupNumRejects }
    STATUS      current
    DESCRIPTION 
        "This group defines the statistics for the Selective Call Rejection Service."
    ::= { bwDXSExecutionMibGroups 39 }

  bwDXSExecutionSimRingServiceGroup OBJECT-GROUP
    OBJECTS     { bwDXSSimRingPersonalNumAttempts, bwDXSSimRingPersonalNumBusy, 
                  bwDXSSimRingPersonalSPIndex, bwDXSSimRingPersonalSPID, 
                  bwDXSSimRingPersonalSPNumAttempts, 
                  bwDXSSimRingPersonalSPNumBusy, 
                  bwDXSSimRingPersonalGroupIndex, bwDXSSimRingPersonalGroupID, 
                  bwDXSSimRingPersonalGroupNumAttempts, 
                  bwDXSSimRingPersonalGroupNumBusy }
    STATUS      current
    DESCRIPTION 
        "This group defines the statistics for the Simultaneous Ringing Service."
    ::= { bwDXSExecutionMibGroups 40 }

  bwDXSExecutionVoiceMessagingServiceGroup OBJECT-GROUP
    OBJECTS     { bwDXSVMNumBusyGreetingsPlayed, 
                  bwDXSVMNumNoAnswerGreetingsPlayed, bwDXSVMNumMessagesLeft, 
                  bwDXSVMRNumBusyGreetingsRecorded, 
                  bwDXSVMRNumNoAnswerGreetingsRecorded, 
                  bwDXSVMRNumPersonalizedNamesRecorded, 
                  bwDXSVMRNumLoginAttempts, bwDXSVMRNumLoginFailures, 
                  bwDXSVMRNumComposeSendAttempts, 
                  bwDXSVMRNumComposeSendGroupAttempts, 
                  bwDXSVMRNumForwardSendAttempts, 
                  bwDXSVMRNumForwardSendGroupAttempts, 
                  bwDXSVMRNumReplySendAttempts, bwDXSVMRNumSendFailed, 
                  bwDXSVMRNumSendGroupFailed, bwDXSVMRDeleteAllMsgsAttempts, 
                  bwDXSVMRCallBackAttempts, 
                  bwDXSVPNumAABusHoursGreetingRecorded, 
                  bwDXSVPNumAAAfterHoursGreetingRecorded, 
                  bwDXSVPNumCFADestinationChanged, bwDXSVPNumPasscodeChanged, 
                  bwDXSVMRNumComposeSendListAttempts, 
                  bwDXSVMRNumForwardSendListAttempts, 
                  bwDXSVMRNumSendListFailed, bwDXSVPGreetingRecorded, 
                  bwDXSVMGreetingRecorded, bwDXSVPCCall, 
                  bwDXSMultiMediaMsgDeposit, bwDXSVMMultiMediaGreetingRecorded, 
                  bwDXSAutoAttendantMultiMediaPromptRecorded, 
                  bwDXSVoiceMessagingSPIndex, bwDXSVoiceMessagingSPID, 
                  bwDXSVMSPNumBusyGreetingsPlayed, 
                  bwDXSVMSPNumNoAnswerGreetingsPlayed, 
                  bwDXSVMSPNumMessagesLeft, bwDXSVMRSPNumBusyGreetingsRecorded, 
                  bwDXSVMRSPNumNoAnswerGreetingsRecorded, 
                  bwDXSVMRSPNumPersonalizedNamesRecorded, 
                  bwDXSVMRSPNumLoginAttempts, bwDXSVMRSPNumLoginFailures, 
                  bwDXSVMRSPNumComposeSendAttempts, 
                  bwDXSVMRSPNumComposeSendGroupAttempts, 
                  bwDXSVMRSPNumForwardSendAttempts, 
                  bwDXSVMRSPNumForwardSendGroupAttempts, 
                  bwDXSVMRSPNumReplySendAttempts, bwDXSVMRSPNumSendFailed, 
                  bwDXSVMRSPNumSendGroupFailed, 
                  bwDXSVMRSPDeleteAllMsgsAttempts, bwDXSVMRSPCallBackAttempts, 
                  bwDXSVPSPNumAABusHoursGreetingRecorded, 
                  bwDXSVPSPNumAAAfterHoursGreetingRecorded, 
                  bwDXSVPSPNumCFADestinationChanged, 
                  bwDXSVPSPNumPasscodeChanged, 
                  bwDXSVMRSPNumComposeSendListAttempts, 
                  bwDXSVMRSPNumForwardSendListAttempts, 
                  bwDXSVMRSPNumSendListFailed, bwDXSVPSPGreetingRecorded, 
                  bwDXSVMSPGreetingRecorded, bwDXSVPCSPCall, 
                  bwDXSSPMultiMediaMsgDeposit, 
                  bwDXSVMSPMultiMediaGreetingRecorded, 
                  bwDXSAutoAttendantSPMultiMediaPromptRecorded, 
                  bwDXSVoiceMessagingGroupIndex, bwDXSVoiceMessagingGroupID, 
                  bwDXSVMGroupNumBusyGreetingsPlayed, 
                  bwDXSVMGroupNumNoAnswerGreetingsPlayed, 
                  bwDXSVMGroupNumMessagesLeft, 
                  bwDXSVMRGroupNumBusyGreetingsRecorded, 
                  bwDXSVMRGroupNumNoAnswerGreetingsRecorded, 
                  bwDXSVMRGroupNumPersonalizedNamesRecorded, 
                  bwDXSVMRGroupNumLoginAttempts, bwDXSVMRGroupNumLoginFailures, 
                  bwDXSVMRGroupNumComposeSendAttempts, 
                  bwDXSVMRGroupNumComposeSendGroupAttempts, 
                  bwDXSVMRGroupNumForwardSendAttempts, 
                  bwDXSVMRGroupNumForwardSendGroupAttempts, 
                  bwDXSVMRGroupNumReplySendAttempts, 
                  bwDXSVMRGroupNumSendFailed, bwDXSVMRGroupNumSendGroupFailed, 
                  bwDXSVMRGroupDeleteAllMsgsAttempts, 
                  bwDXSVMRGroupCallBackAttempts, 
                  bwDXSVPGroupNumAABusHoursGreetingRecorded, 
                  bwDXSVPGroupNumAAAfterHoursGreetingRecorded, 
                  bwDXSVPGroupNumCFADestinationChanged, 
                  bwDXSVPGroupNumPasscodeChanged, 
                  bwDXSVMRGroupNumComposeSendListAttempts, 
                  bwDXSVMRGroupNumForwardSendListAttempts, 
                  bwDXSVMRGroupNumSendListFailed, bwDXSVPGroupGreetingRecorded, 
                  bwDXSVMGroupGreetingRecorded, bwDXSVPCGroupCall, 
                  bwDXSGroupMultiMediaMsgDeposit, 
                  bwDXSVMGroupMultiMediaGreetingRecorded, 
                  bwDXSAutoAttendantGroupMultiMediaPromptRecorded, 
                  bwDXSMessagingQuery, bwDXSMessagingQueryNoUser, 
                  bwDXSMessagingQueryNoMailbox, bwDXSMessagingSPQuery, 
                  bwDXSMessagingSPQueryNoUser, bwDXSMessagingSPQueryNoMailbox, 
                  bwDXSMessagingGroupQuery, bwDXSMessagingGroupQueryNoUser, 
                  bwDXSMessagingGroupQueryNoMailbox }
    STATUS      current
    DESCRIPTION 
        "This group defines the statistics for the Voice Messaging Service."
    ::= { bwDXSExecutionMibGroups 41 }

  bwDXSExecutionInterceptServiceGroup OBJECT-GROUP
    OBJECTS     { bwDXSInterceptUserOriginationInvocations, 
                  bwDXSInterceptGroupOriginationInvocations, 
                  bwDXSInterceptUserTerminationInvocations, 
                  bwDXSInterceptGroupTerminationInvocations, 
                  bwDXSInterceptTransfers, bwDXSInterceptSPIndex, 
                  bwDXSInterceptSPID, 
                  bwDXSInterceptSPUserOriginationInvocations, 
                  bwDXSInterceptSPGroupOriginationInvocations, 
                  bwDXSInterceptSPUserTerminationInvocations, 
                  bwDXSInterceptSPGroupTerminationInvocations, 
                  bwDXSInterceptSPTransfers, bwDXSInterceptGroupIndex, 
                  bwDXSInterceptGroupID, 
                  bwDXSInterceptGroupUserOriginationInvocations, 
                  bwDXSInterceptGroupGroupOriginationInvocations, 
                  bwDXSInterceptGroupUserTerminationInvocations, 
                  bwDXSInterceptGroupGroupTerminationInvocations, 
                  bwDXSInterceptGroupTransfers }
    STATUS      current
    DESCRIPTION 
        "This group defines the statistics for the Intercept Service."
    ::= { bwDXSExecutionMibGroups 43 }

  bwDXSExecutionCallingLineIdBlockingServiceGroup OBJECT-GROUP
    OBJECTS     { bwDXSCallingLineIDDeliveryBlockPerCallBlocks, 
                  bwDXSCallingLineIDDeliveryPerCall, 
                  bwDXSCallingLineIDDeliveryBlockSPIndex, 
                  bwDXSCallingLineIDDeliveryBlockSPID, 
                  bwDXSCallingLineIDDeliveryBlockSPPerCallBlocks, 
                  bwDXSCallingLineIDDeliveryPerCallSP, 
                  bwDXSCallingLineIDDeliveryBlockGroupIndex, 
                  bwDXSCallingLineIDDeliveryBlockGroupID, 
                  bwDXSCallingLineIDDeliveryBlockGroupPerCallBlocks, 
                  bwDXSCallingLineIDDeliveryPerCallGroup }
    STATUS      current
    DESCRIPTION 
        "This group defines the statistics for the Calling Line ID Blocking Service."
    ::= { bwDXSExecutionMibGroups 45 }

  bwDXSExecutionSessionAuditServiceGroup OBJECT-GROUP
    OBJECTS     { bwDXSSessionAuditNumCallsAudited, 
                  bwDXSSessionAuditNumEndpointsAudited, 
                  bwDXSSessionAuditNumCallsFailedAudit, 
                  bwDXSSessionAuditNumEndpointsFailedAudit, 
                  bwDXSSessionAuditSPIndex, bwDXSSessionAuditSPID, 
                  bwDXSSessionAuditSPNumCallsAudited, 
                  bwDXSSessionAuditSPNumEndpointsAudited, 
                  bwDXSSessionAuditSPNumCallsFailedAudit, 
                  bwDXSSessionAuditSPNumEndpointsFailedAudit, 
                  bwDXSSessionAuditGroupIndex, bwDXSSessionAuditGroupID, 
                  bwDXSSessionAuditGroupNumCallsAudited, 
                  bwDXSSessionAuditGroupNumEndpointsAudited, 
                  bwDXSSessionAuditGroupNumCallsFailedAudit, 
                  bwDXSSessionAuditGroupNumEndpointsFailedAudit }
    STATUS      current
    DESCRIPTION 
        "This group defines the statistics for the Session Audit Service."
    ::= { bwDXSExecutionMibGroups 46 }

  bwDXSExecutionCalWaitingServiceGroup OBJECT-GROUP
    OBJECTS     { bwDXSCWNumPhoneCancellations, bwDXSCallWaitingSPIndex, 
                  bwDXSCallWaitingSPID, bwDXSCWSPNumPhoneCancellations, 
                  bwDXSCallWaitingGroupIndex, bwDXSCallWaitingGroupID, 
                  bwDXSCWGroupNumPhoneCancellations }
    STATUS      current
    DESCRIPTION 
        "This group defines the statistics for the Call Waiting Service."
    ::= { bwDXSExecutionMibGroups 48 }

  bwDXSExecutionAlternateNumberServiceGroup OBJECT-GROUP
    OBJECTS     { bwDXSAlternateNumbersUsage, bwDXSAlternateNumbersSPIndex, 
                  bwDXSAlternateNumbersSPID, bwDXSAlternateNumbersSPUsage, 
                  bwDXSAlternateNumbersGroupIndex, 
                  bwDXSAlternateNumbersGroupID, 
                  bwDXSAlternateNumbersGroupUsage }
    STATUS      current
    DESCRIPTION 
        "This group defines the statistics for the Alternate Number Service."
    ::= { bwDXSExecutionMibGroups 49 }

  bwDXSExecutionCustomerOriginatedTraceServiceGroup OBJECT-GROUP
    OBJECTS     { bwDXSCotActivation, bwDXSCotFailureNoId, bwDXSMidCallCotActivation, 
                  bwDXSMidCallCotFailureNoId, bwDXSCotSPIndex, 
                  bwDXSCotSPID, bwDXSCotSPActivation, bwDXSCotSPFailureNoId, 
                  bwDXSMidCallCotSPActivation, bwDXSMidCallCotSPFailureNoId,
                  bwDXSCotGroupIndex, bwDXSCotGroupID, bwDXSCotGroupActivation, 
                  bwDXSCotGroupFailureNoId, bwDXSMidCallCotGroupActivation, 
                  bwDXSMidCallCotGroupFailureNoId }
    STATUS      current
    DESCRIPTION 
        "This group defines the statistics for the Customer Originated Trace Service."
    ::= { bwDXSExecutionMibGroups 50 }

  bwDXSExecutionSpeedDialing8ServiceGroup OBJECT-GROUP
    OBJECTS     { bwDXSSD8NumTimesDialed, bwDXSSD8NumTimesProgrammed, 
                  bwDXSSD8SPIndex, bwDXSSD8SPID, bwDXSSD8SPNumTimesDialed, 
                  bwDXSSD8SPNumTimesProgrammed, bwDXSSD8GroupIndex, 
                  bwDXSSD8GroupID, bwDXSSD8GroupNumTimesDialed, 
                  bwDXSSD8GroupNumTimesProgrammed }
    STATUS      current
    DESCRIPTION 
        "This group defines the statistics for the Speed Dialing 8 Service."
    ::= { bwDXSExecutionMibGroups 51 }

  bwDXSExecutionMusicOnHoldServiceGroup OBJECT-GROUP
    OBJECTS     { bwDXSMusicOnHoldNumUses, 
                  bwDXSMusicOnHoldExternalSourceNumFailures, 
                  bwDXSMusicOnHoldSPIndex, bwDXSMusicOnHoldSPID, 
                  bwDXSMusicOnHoldSPNumUses, 
                  bwDXSMusicOnHoldSPExternalSourceNumFailures, 
                  bwDXSMusicOnHoldGroupIndex, bwDXSMusicOnHoldGroupID, 
                  bwDXSMusicOnHoldGroupNumUses, 
                  bwDXSMusicOnHoldGroupExternalSourceNumFailures }
    STATUS      current
    DESCRIPTION 
        "This group defines the statistics for the Music On Hold Service."
    ::= { bwDXSExecutionMibGroups 52 }

  bwDXSExecutionThirdPartyMWIControlServiceGroup OBJECT-GROUP
    OBJECTS     { bwDXSThirdPartyMWIControlNotifyIns, 
                  bwDXSThirdPartyMWIControlNotifyFailures }
    STATUS      current
    DESCRIPTION 
        "This group defines the statistics for the Third Party Message Waiting Indicator Control Service."
    ::= { bwDXSExecutionMibGroups 54 }

  bwDXSExecutionCallForwardGroupNoAnswerServiceGroup OBJECT-GROUP
    OBJECTS     { bwDXSCFGNAForward, bwDXSCFGNAOverflowForward, 
                  bwDXSCFGNAOverflowNoForward, bwDXSCFGNAExternalForward, 
                  bwDXSCFGNAExternalNoForward, bwDXSCFGNASPIndex, bwDXSCFGNASPID, 
                  bwDXSCFGNASPForward, bwDXSCFGNASPOverflowForward, 
                  bwDXSCFGNASPOverflowNoForward, bwDXSCFGNASPExternalForward, 
                  bwDXSCFGNASPExternalNoForward, bwDXSCFGNAGroupIndex, 
                  bwDXSCFGNAGroupID, bwDXSCFGNAGroupForward, 
                  bwDXSCFGNAGroupOverflowForward, 
                  bwDXSCFGNAGroupOverflowNoForward, 
                  bwDXSCFGNAGroupExternalForward, 
                  bwDXSCFGNAGroupExternalNoForward }
    STATUS      current
    DESCRIPTION 
        "This group defines the statistics for the Call Forward Group No Answer Service."
    ::= { bwDXSExecutionMibGroups 56 }

  bwDXSExecutionSpeedDialing100ServiceGroup OBJECT-GROUP
    OBJECTS     { bwDXSSD100Program, bwDXSSD100Call, bwDXSSD100SPIndex, 
                  bwDXSSD100SPID, bwDXSSD100SPProgram, bwDXSSD100SPCall, 
                  bwDXSSD100GroupIndex, bwDXSSD100GroupID, bwDXSSD100GroupProgram, 
                  bwDXSSD100GroupCall }
    STATUS      current
    DESCRIPTION 
        "This group defines the statistics for the Speed Dialing 100 Service."
    ::= { bwDXSExecutionMibGroups 57 }

  bwDXSExecutionThirdPartyVoiceMailServiceGroup OBJECT-GROUP
    OBJECTS     { bwDXSThirdPartyVoiceMailNbOfCFWBusy, 
                  bwDXSThirdPartyVoiceMailNbOfCFWNoAnswer, 
                  bwDXSThirdPartyVMailSPIndex, bwDXSThirdPartyVMailSPID, 
                  bwDXSThirdPartyVoiceMailSPNbOfCFWBusy, 
                  bwDXSThirdPartyVoiceMailSPNbOfCFWNoAnswer, 
                  bwDXSThirdPartyVMailGroupIndex, bwDXSThirdPartyVMailGroupID, 
                  bwDXSThirdPartyVoiceMailGroupNbOfCFWBusy, 
                  bwDXSThirdPartyVoiceMailGroupNbOfCFWNoAnswer }
    STATUS      current
    DESCRIPTION 
        "This group defines the statistics for the Third Party Voice Mail Service."
    ::= { bwDXSExecutionMibGroups 58 }

  bwDXSExecutionDirectedCallPickupServiceGroup OBJECT-GROUP
    OBJECTS     { bwDXSDirectedCallPickupNumAttempts, 
                  bwDXSDirectedCallPickupNumFailures, 
                  bwDXSDirectedCallPickupSPIndex, bwDXSDirectedCallPickupSPID, 
                  bwDXSDirectedCallPickupSPNumAttempts, 
                  bwDXSDirectedCallPickupSPNumFailures, 
                  bwDXSDirectedCallPickupGroupIndex, 
                  bwDXSDirectedCallPickupGroupID, 
                  bwDXSDirectedCallPickupGroupNumAttempts, 
                  bwDXSDirectedCallPickupGroupNumFailures }
    STATUS      current
    DESCRIPTION 
        "This group defines the statistics for the Directed Call Pickup Service."
    ::= { bwDXSExecutionMibGroups 59 }

  bwDXSExecutionFlashCallHoldServiceGroup OBJECT-GROUP
    OBJECTS     { bwDXSFlashCallHoldNumActivations, bwDXSFlashCallHoldSPIndex, 
                  bwDXSFlashCallHoldSPID, bwDXSFlashCallHoldSPNumActivations, 
                  bwDXSFlashCallHoldGroupIndex, bwDXSFlashCallHoldGroupID, 
                  bwDXSFlashCallHoldGroupNumActivations }
    STATUS      current
    DESCRIPTION 
        "This group defines the statistics for the Flash Call Hold Service."
    ::= { bwDXSExecutionMibGroups 60 }

  bwDXSExecutionDirectedCallPickupWithBargeInServiceGroup OBJECT-GROUP
    OBJECTS     { bwDXSDPUBIAttempt, bwDXSDPUBIFailure, bwDXSDPUBIBargeIn, 
                  bwDXSDPUBIBargeInFailure, bwDXSDPUBIExempt, 
                  bwDXSDPUBINumSilentlyMonitoredCalls, bwDXSDPUBINumSilentlyMonitoredCallsFailure,
                  bwDXSDPUBISPIndex, bwDXSDPUBISPID, bwDXSDPUBISPAttempt, bwDXSDPUBISPFailure, 
                  bwDXSDPUBISPBargeIn, bwDXSDPUBISPBargeInFailure, 
                  bwDXSDPUBISPExempt, bwDXSDPUBISPNumSilentlyMonitoredCalls, 
                  bwDXSDPUBISPNumSilentlyMonitoredCallsFailure, bwDXSDPUBIGroupIndex, 
                  bwDXSDPUBIGroupID, bwDXSDPUBIGroupAttempt, bwDXSDPUBIGroupFailure, 
                  bwDXSDPUBIGroupBargeIn, bwDXSDPUBIGroupBargeInFailure, 
                  bwDXSDPUBIGroupExempt, bwDXSDPUBIGroupNumSilentlyMonitoredCalls, 
                  bwDXSDPUBIGroupNumSilentlyMonitoredCallsFailure }
    STATUS      current
    DESCRIPTION 
        "This group defines the statistics for the Directed Call Pickup With Barge In Service."
    ::= { bwDXSExecutionMibGroups 62 }

  bwDXSExecutionAutomaticCallBackServiceGroup OBJECT-GROUP
    OBJECTS     { bwDXSACBStarted, bwDXSACBExpired, 
                  bwDXSACBSPIndex, bwDXSACBSPID, bwDXSACBSPStarted, 
                  bwDXSACBSPExpired, bwDXSACBGroupIndex, 
                  bwDXSACBGroupID, bwDXSACBGroupStarted, 
                  bwDXSACBGroupExpired, bwDXSACBSPMaxOrigSession, 
                  bwDXSACBSPMaxTermSession, bwDXSACBGroupMaxOrigSession, 
                  bwDXSACBGroupMaxTermSession, bwDXSACBMaxOrigSession, 
                  bwDXSACBMaxTermSession, bwDXSLegacyACBSPOrigSession,
                  bwDXSLegacyACBSPOrigSuccessSession, bwDXSLegacyACBSPOrigFailedSession,
                  bwDXSLegacyACBSPTermSession, bwDXSLegacyACBSPTermSuccessSession,
                  bwDXSLegacyACBSPTermFailedSession, bwDXSLegacyACBGroupOrigSession,
                  bwDXSLegacyACBGroupOrigSuccessSession, bwDXSLegacyACBGroupOrigFailedSession,
                  bwDXSLegacyACBGroupTermSession, bwDXSLegacyACBGroupTermSuccessSession,
                  bwDXSLegacyACBGroupTermFailedSession, bwDXSLegacyACBGroupOrigSession,
                  bwDXSLegacyACBGroupOrigSuccessSession, bwDXSLegacyACBGroupOrigFailedSession,
                  bwDXSLegacyACBGroupTermSession, bwDXSLegacyACBGroupTermSuccessSession,
                  bwDXSLegacyACBGroupTermFailedSession, bwDXSLegacyACBOrigSession,
                  bwDXSLegacyACBOrigSuccessSession, bwDXSLegacyACBOrigFailedSession,
                  bwDXSLegacyACBTermSession, bwDXSLegacyACBTermSuccessSession,
                  bwDXSLegacyACBTermFailedSession }
    STATUS      current
    DESCRIPTION 
        "This group defines the statistics for the Automatic Call Back Service."
    ::= { bwDXSExecutionMibGroups 63 }

  bwDXSExecutionRingTimeoutServiceGroup OBJECT-GROUP
    OBJECTS     { bwDXSRingTimeoutNumExpires, bwDXSRingTimeoutSPIndex, 
                  bwDXSRingTimeoutSPID, bwDXSRingTimeoutSPNumExpires, 
                  bwDXSRingTimeoutGroupIndex, bwDXSRingTimeoutGroupID, 
                  bwDXSRingTimeoutGroupNumExpires }
    STATUS      current
    DESCRIPTION 
        "This group defines the statistics for the Ring Timeout Service."
    ::= { bwDXSExecutionMibGroups 64 }

  bwDXSExecutionSequentialRingServiceGroup OBJECT-GROUP
    OBJECTS     { bwDXSSequentialRingNumAttempts, 
                  bwDXSSequentialRingNumNoAnswer, 
                  bwDXSSequentialRingActivations, bwDXSSequentialRingAnswered, 
                  bwDXSSequentialRingAbandoned, bwDXSSequentialRingSPIndex, 
                  bwDXSSequentialRingSPID, bwDXSSequentialRingSPNumAttempts, 
                  bwDXSSequentialRingSPNumNoAnswer, 
                  bwDXSSequentialRingSPActivations, 
                  bwDXSSequentialRingSPAnswered, 
                  bwDXSSequentialRingSPAbandoned, 
                  bwDXSSequentialRingGroupIndex, bwDXSSequentialRingGroupID, 
                  bwDXSSequentialRingGroupNumAttempts, 
                  bwDXSSequentialRingGroupNumNoAnswer, 
                  bwDXSSequentialRingGroupActivations, 
                  bwDXSSequentialRingGroupAnswered, 
                  bwDXSSequentialRingGroupAbandoned }
    STATUS      current
    DESCRIPTION 
        "This group defines the statistics for the Sequential Ring Service."
    ::= { bwDXSExecutionMibGroups 65 }

  bwDXSExecutionMaliciousCallTraceServiceGroup OBJECT-GROUP
    OBJECTS     { bwDXSMaliciousCallTraceApplied,
                  bwDXSMaliciousCallTraceAnnouncement, 
                  bwDXSMaliciousCallTraceSPIndex, bwDXSMaliciousCallTraceSPID, 
                  bwDXSMaliciousCallTraceSPApplied, 
                  bwDXSMaliciousCallTraceSPAnnouncement,
                  bwDXSMaliciousCallTraceGroupIndex, 
                  bwDXSMaliciousCallTraceGroupID, 
                  bwDXSMaliciousCallTraceGroupApplied,
                  bwDXSMaliciousCallTraceGroupAnnouncement }
    STATUS      current
    DESCRIPTION 
        "This group defines the statistics for the Malicious Call Trace Service."
    ::= { bwDXSExecutionMibGroups 67 }

  bwDXSExecutionPreferredCarrierServiceGroup OBJECT-GROUP
    OBJECTS     { bwDXSSubscriptionUserPIC, bwDXSSubscriptionGroupPIC, 
                  bwDXSSubscriptionServiceProviderPIC, 
                  bwDXSSubscriptionDialedUserPIC, 
                  bwDXSSubscriptionDialedGroupPIC, 
                  bwDXSSubscriptionDialedServiceProviderPIC, 
                  bwDXSNonSubscriptionDialedUserPIC, 
                  bwDXSNonSubscriptionDialedGroupPIC, 
                  bwDXSNonSubscriptionDialedServiceProviderPIC, 
                  bwDXSNoIndicationUserPIC, bwDXSNoIndicationGroupPIC, 
                  bwDXSNoIndicationServiceProviderPIC, 
                  bwDXSPreferredCarrierSPIndex, bwDXSPreferredCarrierSPID, 
                  bwDXSSPSubscriptionUserPIC, bwDXSSPSubscriptionGroupPIC, 
                  bwDXSSPSubscriptionServiceProviderPIC, 
                  bwDXSSPSubscriptionDialedUserPIC, 
                  bwDXSSPSubscriptionDialedGroupPIC, 
                  bwDXSSPSubscriptionDialedServiceProviderPIC, 
                  bwDXSSPNonSubscriptionDialedUserPIC, 
                  bwDXSSPNonSubscriptionDialedGroupPIC, 
                  bwDXSSPNonSubscriptionDialedServiceProviderPIC, 
                  bwDXSSPNoIndicationUserPIC, bwDXSSPNoIndicationGroupPIC, 
                  bwDXSSPNoIndicationServiceProviderPIC, 
                  bwDXSPreferredCarrierGroupIndex, 
                  bwDXSPreferredCarrierGroupID, bwDXSGroupSubscriptionUserPIC, 
                  bwDXSGroupSubscriptionGroupPIC, 
                  bwDXSGroupSubscriptionServiceProviderPIC, 
                  bwDXSGroupSubscriptionDialedUserPIC, 
                  bwDXSGroupSubscriptionDialedGroupPIC, 
                  bwDXSGroupSubscriptionDialedServiceProviderPIC, 
                  bwDXSGroupNonSubscriptionDialedUserPIC, 
                  bwDXSGroupNonSubscriptionDialedGroupPIC, 
                  bwDXSGroupNonSubscriptionDialedServiceProviderPIC, 
                  bwDXSGroupNoIndicationUserPIC, 
                  bwDXSGroupNoIndicationGroupPIC, 
                  bwDXSGroupNoIndicationServiceProviderPIC }
    STATUS      current
    DESCRIPTION 
        "This group defines the statistics for the Preferred Carrier Service."
    ::= { bwDXSExecutionMibGroups 70 }

  bwDXSExecutionFamilySimRingServiceGroup OBJECT-GROUP
    OBJECTS     { bwDXSFamilySimRingNumAttempts, bwDXSFamilySimRingNumBusy, 
                  bwDXSFamilySimRingSPIndex, bwDXSFamilySimRingSPID, 
                  bwDXSFamilySimRingSPNumAttempts, bwDXSFamilySimRingSPNumBusy, 
                  bwDXSFamilySimRingGroupIndex, bwDXSFamilySimRingGroupID, 
                  bwDXSFamilySimRingGroupNumAttempts, 
                  bwDXSFamilySimRingGroupNumBusy }
    STATUS      current
    DESCRIPTION 
        "This group defines the statistics for the Family SimRing Service."
    ::= { bwDXSExecutionMibGroups 71 }

  bwDXSExecutionDiversionInhibitorServiceGroup OBJECT-GROUP
    OBJECTS     { bwDXSDiversionInhibited, bwDXSDiversionInhibitorSPIndex, 
                  bwDXSDiversionInhibitorSPID, bwDXSSPDiversionInhibited, 
                  bwDXSDiversionInhibitorGroupIndex, 
                  bwDXSDiversionInhibitorGroupID, bwDXSGroupDiversionInhibited }
    STATUS      current
    DESCRIPTION 
        "This group defines the statistics for the Diversion Inhibitor Service."
    ::= { bwDXSExecutionMibGroups 72 }

  bwDXSExecutionCustomRingbackServiceGroup OBJECT-GROUP
    OBJECTS     { bwDXSCustomRingbackUserAudioAttempts, 
                  bwDXSCustomRingbackUserVideoAttempts, 
                  bwDXSCustomRingbackUserAudioFailures, 
                  bwDXSCustomRingbackUserVideoFailures, 
                  bwDXSCustomRingbackGroupAudioAttempts, 
                  bwDXSCustomRingbackGroupVideoAttempts, 
                  bwDXSCustomRingbackGroupAudioFailures, 
                  bwDXSCustomRingbackGroupVideoFailures, 
                  bwDXSCustomRingbackSPIndex, bwDXSCustomRingbackSPID, 
                  bwDXSCustomRingbackUserAudioSPAttempts, 
                  bwDXSCustomRingbackUserVideoSPAttempts, 
                  bwDXSCustomRingbackUserAudioSPFailures, 
                  bwDXSCustomRingbackUserVideoSPFailures, 
                  bwDXSCustomRingbackGroupAudioSPAttempts, 
                  bwDXSCustomRingbackGroupVideoSPAttempts, 
                  bwDXSCustomRingbackGroupAudioSPFailures, 
                  bwDXSCustomRingbackGroupVideoSPFailures, 
                  bwDXSCustomRingbackGroupIndex, bwDXSCustomRingbackGroupID, 
                  bwDXSCustomRingbackUserAudioGroupAttempts, 
                  bwDXSCustomRingbackUserVideoGroupAttempts, 
                  bwDXSCustomRingbackUserAudioGroupFailures, 
                  bwDXSCustomRingbackUserVideoGroupFailures, 
                  bwDXSCustomRingbackGroupAudioGroupAttempts, 
                  bwDXSCustomRingbackGroupVideoGroupAttempts, 
                  bwDXSCustomRingbackGroupAudioGroupFailures, 
                  bwDXSCustomRingbackGroupVideoGroupFailures, 
                  bwDXSCustomRingbackUserVideoCWSPAttempts, 
                  bwDXSCustomRingbackUserAudioCWSPAttempts, 
                  bwDXSCustomRingbackUserAudioCWSPFailures, 
                  bwDXSCustomRingbackUserVideoCWSPFailures, 
                  bwDXSCustomRingbackUserAudioCWGroupAttempts, 
                  bwDXSCustomRingbackUserVideoCWGroupAttempts, 
                  bwDXSCustomRingbackUserAudioCWGroupFailures, 
                  bwDXSCustomRingbackUserVideoCWGroupFailures, 
                  bwDXSCustomRingbackUserAudioCWAttempts, 
                  bwDXSCustomRingbackUserVideoCWAttempts, 
                  bwDXSCustomRingbackUserAudioCWFailures, 
                  bwDXSCustomRingbackUserVideoCWFailures }
    STATUS      current
    DESCRIPTION 
        "This group defines the statistics for the Custom Ringback Service."
    ::= { bwDXSExecutionMibGroups 76 }

  bwDXSExecutionMssGroup OBJECT-GROUP
    OBJECTS     { bwDXSNSqueryRequestsTransmitted, bwDXSNSqueryCommFailures }
    STATUS      current
    DESCRIPTION 
        "This group defines the statistics for the Media Server Selection."
    ::= { bwDXSExecutionMibGroups 77 }

  bwDXSExecutionNrsGroup OBJECT-GROUP
    OBJECTS     { bwDXSNbInvalidMessagesReceived, bwDXSNbRequestsReceived, 
                  bwDXSNbResponsesReceived, bwDXSNbErrorsReceived, 
                  bwDXSNbRequestsSent, bwDXSNbResponsesSent, bwDXSNbErrorsSent, 
                  bwDXSNbRequestsResent, bwDXSNbResponsesResent, 
                  bwDXSNbRequestsUnanswered, bwDXSNRSStatsTableProtocolName, 
                  bwDXSNRSStatsTableNbRequestsReceived, 
                  bwDXSNRSStatsTableNbResponsesReceived, 
                  bwDXSNRSStatsTableNbErrorsReceived, 
                  bwDXSNRSStatsTableNbRequestsSent, 
                  bwDXSNRSStatsTableNbResponsesSent, 
                  bwDXSNRSStatsTableNbErrorsSent, 
                  bwDXSNRSStatsTableNbRequestsResent, 
                  bwDXSNRSStatsTableNbResponsesResent, 
                  bwDXSNRSStatsTableNbRequestsUnanswered }
    STATUS      current
    DESCRIPTION 
        "This group defines the statistics for the NRS based protocols."
    ::= { bwDXSExecutionMibGroups 78 }

  bwDXSExecutionProtocolMonitorGroup OBJECT-GROUP
    OBJECTS     { bwDXSPMTNumMonitorsCreated, bwDXSPMTNumMonitorsOpen, 
                  bwDXSPMTNumLoggerCreated, bwDXSPMTNumLoggerOpen }
    STATUS      current
    DESCRIPTION 
        "This group defines the statistics for the Protocol Monitor."
    ::= { bwDXSExecutionMibGroups 80 }

--  bwDXSExecutionSystemStatsGroup OBJECT-GROUP
--    OBJECTS     {  }
--    STATUS      current
--    DESCRIPTION 
--        "This group defines the system level statistics for the Application Server."
--    ::= { bwDXSExecutionMibGroups 81 }

  bwDXSExecutionQueueStatsGroup OBJECT-GROUP
    OBJECTS     { bwDXSSystemInternalQueueResets, 
                  bwDXSSystemInternalQueueIndex, bwDXSSystemInternalQueueName, 
                  bwDXSSystemInternalQueueSize, 
                  bwDXSSystemInternalQueueTimeAvg, 
                  bwDXSSystemInternalQueueTimeMin, 
                  bwDXSSystemInternalQueueTimeMax, 
                  bwDXSSystemInternalQueueTimeMaxTimestampMSB, 
                  bwDXSSystemInternalQueueLengthCurrent, 
                  bwDXSSystemInternalQueueLengthAvg, 
                  bwDXSSystemInternalQueueLengthMax, 
                  bwDXSSystemInternalQueueLengthMaxTimestampMSB, 
                  bwDXSSystemInternalQueueLengthMaxTimestampLSB, 
                  bwDXSSystemInternalQueueTimeMaxTimestampLSB }
    STATUS      current
    DESCRIPTION 
        "This group defines the statistics for the Application Server processing internal queues."
    ::= { bwDXSExecutionMibGroups 82 }

  bwDXSExecutionOverloadControlStatsGroup OBJECT-GROUP
    OBJECTS     { bwDXSCurrentCallOverloadZone, 
                  bwDXSNumCallYellowZoneOverloadTrans, 
                  bwDXSNumCallRedZoneOverloadTrans, 
                  bwDXSCurrentNonCallOverloadZone, 
                  bwDXSNumNonCallYellowZoneOverloadTrans, 
                  bwDXSNumNonCallRedZoneOverloadTrans, 
                  bwDXSNumDiscardedMessage, bwDXSTimeLastDiscardedMessage,
                  bwDXSMemoryHighWaterMark, bwDXSMemoryHighWaterMarkTimeMSB,
                  bwDXSMemoryHighWaterMarkTimeLSB, bwDXSOverloadStatsReset,
                  bwDXSOverloadSampledDataIndex, bwDXSOverloadSampledDataName,
                  bwDXSOverloadSampledDelayMin, bwDXSOverloadSampledDelayAvg,
                  bwDXSOverloadSampledDelayMax, bwDXSOverloadSampledDelayMaxTimeMSB,
                  bwDXSOverloadSampledDelayMaxTimeLSB, bwDXSOverloadNumSamples }
    STATUS      current
    DESCRIPTION 
        "This group defines the statistics for the Overload Control feature on the Application Server."
    ::= { bwDXSExecutionMibGroups 83 }

  bwDXSExecutionCongestionManagementGroup OBJECT-GROUP
    OBJECTS     { bwDXSCongestionManagementNeighborIndex, 
                  bwDXSCongestionManagementNeighborIpAddress, 
                  bwDXSCongestionManagementNeighborInviteIn, 
                  bwDXSCongestionManagementNeighborInviteOut, 
                  bwDXSCongestionManagementNeighborRegisterIn, 
                  bwDXSCongestionManagementNeighborOptionsIn, 
                  bwDXSCongestionManagementNeighborOptionsOut, 
                  bwDXSCongestionManagementNeighborSubscribeNotifyIn, 
                  bwDXSCongestionManagementNeighborSubscribeNotifyOut, 
                  bwDXSCongestionManagementNeighbor5xxIn, 
                  bwDXSCongestionManagementNeighborCallpMessageInRate, 
                  bwDXSCongestionManagementNeighborCallpMessageOutRate, 
                  bwDXSCongestionManagementNeighborCallpRequestInRate, 
                  bwDXSCongestionManagementNeighborNonCallpMessageInRate, 
                  bwDXSCongestionManagementNeighborNonCallpMessageOutRate, 
                  bwDXSCongestionManagementNeighborNonCallpRequestInRate, 
                  bwDXSCongestionManagementNeighborState, 
                  bwDXSCongestionManagementNeighborCapability }
    STATUS      current
    DESCRIPTION 
        "This group defines the statistics for Congestion Management."
    ::= { bwDXSExecutionMibGroups 86 }

  bwDXSExecutionFaxMessagingServiceGroup OBJECT-GROUP
    OBJECTS     { bwDXSFaxMessagingReceived, bwDXSFaxMessagingReceptionFailure, 
                  bwDXSFaxMessagingPrinted, bwDXSFaxMessagingPrintingFailure, 
                  bwDXSFaxMessagingSPIndex, bwDXSFaxMessagingSPID, 
                  bwDXSFaxMessagingSPReceived, 
                  bwDXSFaxMessagingSPReceptionFailure, 
                  bwDXSFaxMessagingSPPrinted, 
                  bwDXSFaxMessagingSPPrintingFailure, 
                  bwDXSFaxMessagingGroupIndex, bwDXSFaxMessagingGroupID, 
                  bwDXSFaxMessagingGroupReceived, 
                  bwDXSFaxMessagingGroupReceptionFailure, 
                  bwDXSFaxMessagingGroupPrinted, 
                  bwDXSFaxMessagingGroupPrintingFailure }
    STATUS      current
    DESCRIPTION 
        "This group defines the statistics for the Fax Messaging Service."
    ::= { bwDXSExecutionMibGroups 88 }

  bwDXSExecutionCallForwardingNotReachableGroup OBJECT-GROUP
    OBJECTS     { bwDXSCFNRcNumForwarded, bwDXSCFNRcNumPhoneActivations, 
                  bwDXSCFNRcNumPhoneDeactivations, 
                  bwDXSCFNRcDestinationChanged, bwDXSCFNRcSPIndex, bwDXSCFNRcSPID, 
                  bwDXSCFNRcSPNumForwarded, bwDXSCFNRcSPNumPhoneActivations, 
                  bwDXSCFNRcSPNumPhoneDeactivations, 
                  bwDXSCFNRcSPDestinationChanged, bwDXSCFNRcGroupIndex, 
                  bwDXSCFNRcGroupID, bwDXSCFNRcGroupNumForwarded, 
                  bwDXSCFNRcGroupNumPhoneActivations, 
                  bwDXSCFNRcGroupNumPhoneDeactivations, 
                  bwDXSCFNRcGroupDestinationChanged,
                  bwDXSCFNRcNumPhoneInterrogation,
                  bwDXSCFNRcSPNumPhoneInterrogation,
                  bwDXSCFNRcGroupNumPhoneInterrogation }
    STATUS      current
    DESCRIPTION 
        "This group defines the statistics for Call Forwarding Not Reachable."
    ::= { bwDXSExecutionMibGroups 90 }

  bwDXSExecutionExtEmergencyRtgStatsGroup OBJECT-GROUP
    OBJECTS     { bwDXSExtEmergencyRtgQuerySent, 
                  bwDXSExtEmergencyRtgQueryFailure, 
                  bwDXSExtEmergencyRtgENServerTimeout }
    STATUS      current
    DESCRIPTION 
        "This group defines the statistics for the Automatic Hold And Retrieve Service."
    ::= { bwDXSExecutionMibGroups 91 }

  bwDXSExecutionSoapGroup OBJECT-GROUP
    OBJECTS     { bwDXSSOAPMaxSessions, bwDXSSOAPAvgSessions, bwDXSSOAPMaxThreads, 
                  bwDXSSOAPAvgThreads, bwDXSSOAPMaxServiceTime, 
                  bwDXSSOAPAvgServiceTime, bwDXSSOAPNumDroppedRequests }
    STATUS      current
    DESCRIPTION 
        "This group defines the statistics for SOAP."
    ::= { bwDXSExecutionMibGroups 92 }

  bwDXSExecutionLocationControlGroup OBJECT-GROUP
    OBJECTS     { bwDXSLocationControlActivationSuccess, 
                  bwDXSLocationControlDeactivationSuccess, 
                  bwDXSLocationControlSPIndex, bwDXSLocationControlSPID, 
                  bwDXSLocationControlSPActivationSuccess, 
                  bwDXSLocationControlSPDeactivationSuccess, 
                  bwDXSLocationControlGroupIndex, bwDXSLocationControlGroupID, 
                  bwDXSLocationControlGroupActivationSuccess, 
                  bwDXSLocationControlGroupDeactivationSuccess }
    STATUS      current
    DESCRIPTION 
        "This group defines the location control service."
    ::= { bwDXSExecutionMibGroups 97 }

  bwDXSExecutionCallRetrieveGroup OBJECT-GROUP
    OBJECTS     { bwDXSCallRetrieveSuccess, bwDXSCallRetrieveSPIndex, 
                  bwDXSCallRetrieveSPID, bwDXSCallRetrieveSPSuccess, 
                  bwDXSCallRetrieveGroupIndex, bwDXSCallRetrieveGroupID, 
                  bwDXSCallRetrieveGroupSuccess }
    STATUS      current
    DESCRIPTION 
        "This group defines the call retrieve service."
    ::= { bwDXSExecutionMibGroups 98 }

  bwDXSExecutionBroadworksAnywhereGroup OBJECT-GROUP
    OBJECTS     { bwDXSBACallOriginations, bwDXSBACallTerminations, 
                  bwDXSBroadWorksAnywhereSPIndex, bwDXSBroadWorksAnywhereSPID, 
                  bwDXSBASPCallOriginations, bwDXSBASPCallTerminations, 
                  bwDXSBroadWorksAnywhereGroupIndex, 
                  bwDXSBroadWorksAnywhereGroupID, bwDXSBAGroupCallOriginations, 
                  bwDXSBAGroupCallTerminations }
    STATUS      current
    DESCRIPTION 
        "This group defines the BroadWorks Anywhere service."
    ::= { bwDXSExecutionMibGroups 99 }

  bwDXSExecutionOfflineChargingGroup OBJECT-GROUP
    OBJECTS     { bwDXSOfflineChargingACROut, bwDXSOfflineChargingACASuccessIn, 
                  bwDXSOfflineChargingACAFailureIn, 
                  bwDXSOfflineChargingACRTimeout, 
                  bwDXSOfflineChargingUnknownServer, 
                  bwDXSOfflineChargingInvalidServer, 
                  bwDXSOfflineChargingServerUnreachable, 
                  bwDXSOfflineChargingDFNDown, bwDXSOfflineChargingAPNError, 
                  bwDXSOfflineChargingQueued, 
                  bwDXSOfflineChargingTransmittedFromQueue, 
                  bwDXSOfflineChargingRetransmittedFromQueue }
    STATUS      current
    DESCRIPTION 
        "This group defins the Offline Charging service."
    ::= { bwDXSExecutionMibGroups 101 }

  bwDXSExecutionSmppGroup OBJECT-GROUP
    OBJECTS     { bwDXSSmppSubmitSMRequestsSent, 
                  bwDXSSmppInvalidSubmitSMResponsesReceived, 
                  bwDXSSmppSubmitSMResponseTimeout }
    STATUS      current
    DESCRIPTION 
        "This group defines the statistics for SMPP."
    ::= { bwDXSExecutionMibGroups 102 }

  bwDXSExecutionExpensiveCallNotificationGroup OBJECT-GROUP
    OBJECTS     { bwDXSECNWarningAnnouncementAttempts, 
                  bwDXSECNExpensiveCallReleased }
    STATUS      current
    DESCRIPTION 
        "This group defines the statistics for expensive call notification."
    ::= { bwDXSExecutionMibGroups 103 }

  bwDXSExecutionCommunicationBarringGroup OBJECT-GROUP
    OBJECTS     { bwDXSCommunicationBarringBlockedTreatment, bwDXSCommunicationBarringBlockedTransfer, 
                  bwDXSCommunicationBarringPromptedPIN, bwDXSCommunicationBarringFailedPIN,
                  bwDXSCommunicationBarringCallDurationExceeded, bwDXSCommunicationBarringPhoneActivations, 
                  bwDXSCommunicationBarringPhoneDeactivations, bwDXSCommunicationBarringPhoneQueries, 
                  bwDXSCommunicationBarringErroneousPinAttempts, bwDXSCommunicationBarringLockouts, 
                  bwDXSCommunicationBarringSPIndex, bwDXSCommunicationBarringSPID, 
                  bwDXSCommunicationBarringSPBlockedTreatment, bwDXSCommunicationBarringSPBlockedTransfer, 
                  bwDXSCommunicationBarringSPPromptedPIN, bwDXSCommunicationBarringSPFailedPIN, 
                  bwDXSCommunicationBarringSPCallDurationExceeded, bwDXSCommunicationBarringSPPhoneActivations, 
                  bwDXSCommunicationBarringSPPhoneDeactivations, bwDXSCommunicationBarringSPPhoneQueries, 
                  bwDXSCommunicationBarringSPErroneousPinAttempts, bwDXSCommunicationBarringSPLockouts, 
                  bwDXSCommunicationBarringGroupIndex, bwDXSCommunicationBarringGroupID, 
                  bwDXSCommunicationBarringGroupBlockedTreatment, bwDXSCommunicationBarringGroupBlockedTransfer,
                  bwDXSCommunicationBarringGroupPromptedPIN, bwDXSCommunicationBarringGroupFailedPIN, 
                  bwDXSCommunicationBarringGroupCallDurationExceeded, bwDXSCommunicationBarringGroupPhoneActivations,
                  bwDXSCommunicationBarringGroupPhoneDeactivations, bwDXSCommunicationBarringGroupPhoneQueries,
                  bwDXSCommunicationBarringGroupErroneousPinAttempts, bwDXSCommunicationBarringGroupLockouts }
    STATUS      current
    DESCRIPTION 
        "This group defines the Communication Barring service."
    ::= { bwDXSExecutionMibGroups 104 }

  bwDXSExecutionOcicStatsGroup OBJECT-GROUP
    OBJECTS     { bwDXSOCICNumOutgoingOverloadDiscard, 
                  bwDXSOCICStatsEntryIndex, bwDXSOCICApplicationId, 
                  bwDXSOCICNumNoConnectionDiscard, 
                  bwDXSOCICNumRouteExhaustionDiscard, 
                  bwDXSOCICNumResponseTimeout }
    STATUS      current
    DESCRIPTION 
        "This group defines the OCI-C statistics."
    ::= { bwDXSExecutionMibGroups 105 }

  bwDXSExecutionOnlineChargingStatsGroup OBJECT-GROUP
    OBJECTS     { bwDXSOnlineChargingCCROut, bwDXSOnlineChargingCCASuccessIn, 
                  bwDXSOnlineChargingCCAFailureIn, 
                  bwDXSOnlineChargingCCRTimeout, 
                  bwDXSOnlineChargingUnknownServer, 
                  bwDXSOnlineChargingInvalidServer, 
                  bwDXSOnlineChargingServerUnreachable, 
                  bwDXSOnlineChargingDFNDown, bwDXSOnlineChargingAPNError }
    STATUS      current
    DESCRIPTION 
        "This group defines the Online Charging statistics."
    ::= { bwDXSExecutionMibGroups 106 }

  bwDXSExecutionCallBridgeGroup OBJECT-GROUP
    OBJECTS     { bwDXSCallBridgeSuccess, bwDXSCallBridgeSPIndex, 
                  bwDXSCallBridgeSPID, bwDXSCallBridgeSPSuccess, 
                  bwDXSCallBridgeGroupIndex, bwDXSCallBridgeGroupID, 
                  bwDXSCallBridgeGroupSuccess }
    STATUS      current
    DESCRIPTION 
        "This group defines the Call Bridge statistics."
    ::= { bwDXSExecutionMibGroups 107 }

  bwDXSExecutionDirectoryNumberHuntingGroup OBJECT-GROUP
    OBJECTS     { bwDXSDirectoryNumberHuntingIncomingCalls, 
                  bwDXSDirectoryNumberHuntingSPIndex, 
                  bwDXSDirectoryNumberHuntingSPID, 
                  bwDXSDirectoryNumberHuntingSPIncomingCalls, 
                  bwDXSDirectoryNumberHuntingGroupIndex, 
                  bwDXSDirectoryNumberHuntingGroupID, 
                  bwDXSDirectoryNumberHuntingGroupIncomingCalls }
    STATUS      current
    DESCRIPTION 
        "This group defines the Directory Number Hunting statistics."
    ::= { bwDXSExecutionMibGroups 108 }

  bwDXSExecutionAoCGroup OBJECT-GROUP
    OBJECTS     { bwDXSAoCIncompatibleTariff, bwDXSAoCIncompatibleAoC, 
                  bwDXSAoCUnsupportedCostUnit, bwDXSAoCActivation, 
                  bwDXSAoCSPIncompatibleTariff, bwDXSAoCSPIncompatibleAoC, 
                  bwDXSAoCSPActivation, bwDXSAoCGroupIncompatibleTariff, 
                  bwDXSAoCGroupIncompatibleAoC, bwDXSAoCGroupActivation, 
                  bwDXSAoCSPIndex, bwDXSAoCSPID, bwDXSAoCGroupIndex, bwDXSAoCGroupID }
    STATUS      current
    DESCRIPTION 
        "This group defines the AoC statistics."
    ::= { bwDXSExecutionMibGroups 109 }

  bwDXSExecutionTcpStatsGroup OBJECT-GROUP
    OBJECTS     { bwDXSTcpServersStatsIndex, bwDXSTcpServersName, 
                  bwDXSTcpServersNbConnectionsAccepted, 
                  bwDXSTcpServersNbConnectionsRefused, 
                  bwDXSTcpServersNbConnectionsClosed, 
                  bwDXSTcpServersOutgoingQueueSize, 
                  bwDXSTcpServersIncomingQueueSize, 
                  bwDXSTcpServersNbBytesSentSecure, 
                  bwDXSTcpServersNbBytesReceivedSecure, 
                  bwDXSTcpServersNbConnectionsInitiated, 
                  bwDXSTcpServersNbBytesSent, 
                  bwDXSTcpServersNbBytesReceived }
    STATUS      current
    DESCRIPTION 
        "This group defines the statistics for the TCP server."
    ::= { bwDXSExecutionMibGroups 110 }

  bwDXSExecutionConcurrentFrameworkStatsGroup OBJECT-GROUP
    OBJECTS     { bwDXSMonitoringExecutorIndex, 
                  bwDXSMonitoringExecutorName, 
                  bwDXSMonitoringExecutorCurrentPoolSize, 
                  bwDXSMonitoringExecutorMaxPoolSize, 
                  bwDXSMonitoringExecutorAvgActiveThreads, 
                  bwDXSMonitoringExecutorTaskQueueSize, 
                  bwDXSMonitoringExecutorNbTasksRun, 
                  bwDXSMonitoringExecutorNbWarnings, 
                  bwDXSMonitoringExecutorNbErrors, 
                  bwDXSMonitoringExecutorLongestTaskMs, 
                  bwDXSMonitoringExecutorLongestTaskName }
    STATUS      current
    DESCRIPTION 
        "This group defines the statistics for the Concurrent Framework."
    ::= { bwDXSExecutionMibGroups 111 }

  bwDXSExecutionDnsQueryGroup OBJECT-GROUP
    OBJECTS     { bwDXSDnsQueryTimeMax, bwDXSDnsQueryTimeMaxTimestampMSB, 
                  bwDXSDnsQueryTimeMaxTimestampLSB, bwDXSDnsQueryTimeAvg, 
                  bwDXSDnsStatsQueryIndex, bwDXSDnsStatsQueryType, 
                  bwDXSDnsStatsQueries, bwDXSDnsStatsQueryTimeouts }
    STATUS      current
    DESCRIPTION 
        "This group defines the statistics for DNS query."
    ::= { bwDXSExecutionMibGroups 112 }

  bwDXSExecutionMoCountersGroup OBJECT-GROUP
    OBJECTS     { resetAllCounters }
    STATUS      current
    DESCRIPTION 
        "This group defines statistics to perform managed object work for the Execution Server."
    ::= { bwDXSExecutionMibGroups 113 }

  bwDXSExecutionDiameterGroup OBJECT-GROUP
    OBJECTS { bwDXSInternalXSDiameterCommandCode,
              bwDXSInternalXSDiameterRequestsOut,
              bwDXSInternalXSDiameterInformationalAnswersIn,
              bwDXSInternalXSDiameterSuccessAnswersIn,
              bwDXSInternalXSDiameterFailureAnswersIn,
              bwDXSInternalXSDiameterRequestTimeouts,
              bwDXSInternalXSDiameterRequestsIn,
              bwDXSInternalXSDiameterInformationalAnswersOut,
              bwDXSInternalXSDiameterSuccessAnswersOut,
              bwDXSInternalXSDiameterFailureAnswersOut,
              bwDXSExternalXSDiameterCommandCode,
              bwDXSExternalXSDiameterRequestsOut,
              bwDXSExternalXSDiameterInformationalAnswersIn,
              bwDXSExternalXSDiameterSuccessAnswersIn,
              bwDXSExternalXSDiameterFailureAnswersIn,
              bwDXSExternalXSDiameterRequestTimeouts,
              bwDXSExternalXSDiameterRequestsIn,
              bwDXSExternalXSDiameterInformationalAnswersOut,
              bwDXSExternalXSDiameterSuccessAnswersOut,
              bwDXSExternalXSDiameterFailureAnswersOut, 
              bwDXSShRelayInterfaceServerUnreachable }
    STATUS current
    DESCRIPTION 
        "This group defines the Diameter statistics."
    ::= { bwDXSExecutionMibGroups 115 }

  bwDXSExecutionProfileLoadingGroup OBJECT-GROUP
    OBJECTS     { bwDXSProfileLoadingCallNumRequests, bwDXSProfileLoadingCallMinDelay,
                  bwDXSProfileLoadingCallMaxDelay, bwDXSProfileLoadingCallAvgDelay,
                  bwDXSProfileLoadingNonCallNumRequests, bwDXSProfileLoadingNonCallMinDelay,
                  bwDXSProfileLoadingNonCallMaxDelay, bwDXSProfileLoadingNonCallAvgDelay,
                  bwDXSProfileLoadingMidCallNumRequests, bwDXSProfileLoadingMidCallMinDelay,
                  bwDXSProfileLoadingMidCallMaxDelay, bwDXSProfileLoadingMidCallAvgDelay,
                  bwDXSProfileLoadingCallPoolMaxThreads, bwDXSProfileLoadingCallPoolAvgThreads,
                  bwDXSProfileLoadingNonCallPoolMaxThreads, bwDXSProfileLoadingNonCallPoolAvgThreads,
                  bwDXSUserProfilesRegisteredInCache, bwDXSGroupProfilesRegisteredInCache,
                  bwDXSServiceProviderProfilesRegisteredInCache }
    STATUS      current
    DESCRIPTION 
        "This group defines the statistics for the callP Profile Loading stats."
    ::= { bwDXSExecutionMibGroups 116 }

  bwDXSServiceCentralizationContinuityGroup OBJECT-GROUP
    OBJECTS     { bwDXSSCCCentralization, bwDXSSCCContinuity, bwDXSSCCASPSIDNAllocationFailures,
                  bwDXSSCCTimeOuts, bwDXSSCCASPSIDNMaxUsed, bwDXSSCCASPSIDNInUse,
                  bwDXSSCCASPSIDNMaxHoldTime, bwDXSSCCASPSIDNAvgHoldTime,
                  bwDXSSCCIMRNCentralization, bwDXSSCCCSRNCentralization,
                  bwDXSSCCSTNSRContinuity, bwDXSSCCATUSTIContinuity,
                  bwDXSSCCIMRNAllocationFailures, bwDXSSCCIMRNTimeOuts,
                  bwDXSSCCIMRNMaxUsed, bwDXSSCCIMRNInUse, 
                  bwDXSSCCIMRNMaxHoldTime, bwDXSSCCIMRNAvgHoldTime,
                  bwDXSSCCEarlyReleaseTimeOut }
    STATUS      current
    DESCRIPTION 
        "This group defines the statistics for the Service Centralization Continuity stats."
    ::= { bwDXSExecutionMibGroups 117 }

   bwDXSCallLogStatisticStatsGroup OBJECT-GROUP
     OBJECTS { bwDXSCallLogSchemaInstanceIndex, bwDXSCallLogSchemaInstanceName,
               bwDXSCallLogEventsReported, bwDXSCallLogEventsIgnored,
               bwDXSCallLogEventsFailed, bwDXSCallLogDatabaseInserts,
               bwDXSCallLogDatabaseUpdates, bwDXSCallLogDatabaseQueries, 
               bwDXSCallLogDatabaseDeletes, bwDXSCallLogDatabaseFailures,
               bwDXSCallLogEventResets, bwDXSCallLogEventIndex,
               bwDXSCallLogSchemaName, bwDXSCallLogEventName, bwDXSCallLogEventCount,
               bwDXSCallLogProcessorResets, bwDXSCallLogProcessorIndex,
               bwDXSCallLogProcessorSchemaName, bwDXSCallLogProcessorId, 
               bwDXSCallLogProcessorEventCount }
     STATUS current
     DESCRIPTION 
         "This group defines the Call Log statistics."
     ::= { bwDXSExecutionMibGroups 118 }

   bwDXSExternalCustomRingbackStatisticStatsGroup OBJECT-GROUP
     OBJECTS { bwDXSExternalCustomRingbackAttempts, bwDXSExternalCustomRingbackFailures,
               bwDXSExternalCustomRingbackSPIndex, bwDXSExternalCustomRingbackSPID,
               bwDXSExternalCustomRingbackSPAttempts, bwDXSExternalCustomRingbackSPFailures,
               bwDXSExternalCustomRingbackGroupIndex, bwDXSExternalCustomRingbackGroupID,
               bwDXSExternalCustomRingbackGroupAttempts, bwDXSExternalCustomRingbackGroupFailures }
     STATUS current
     DESCRIPTION 
         "This group defines the Call Log statistics."
     ::= { bwDXSExecutionMibGroups 119 }

   bwDXSCFGNRcStatisticStatsGroup  OBJECT-GROUP
     OBJECTS { bwDXSCFGNRcForward, bwDXSCFGNRcNoForward, bwDXSCFGNRcSPIndex,
               bwDXSCFGNRcSPID, bwDXSCFGNRcSPForward, bwDXSCFGNRcSPNoForward,
               bwDXSCFGNRcGroupIndex, bwDXSCFGNRcGroupID, bwDXSCFGNRcGroupForward,
               bwDXSCFGNRcGroupNoForward }
     STATUS current
     DESCRIPTION 
         "This group defines the Call Forwarding Group Not Reachable statistics."
     ::= { bwDXSExecutionMibGroups 120 }

   bwDXSSHStatisticStatsGroup  OBJECT-GROUP
     OBJECTS { bwDXShOperationMinTime, bwDXShOperationMaxTime, bwDXShOperationAverageTime, bwDXShOperations }
     STATUS current
     DESCRIPTION 
         "This group defines the Call Forwarding Group Not Reachable statistics."
     ::= { bwDXSExecutionMibGroups 121 }

  bwDXSExecutionGroupNightForwardingServiceGroup OBJECT-GROUP
    OBJECTS     { bwDXSGroupNightForwardingNumInvocations, bwDXSGroupNightForwardingSPIndex,
                  bwDXSGroupNightForwardingSPID, bwDXSGroupNightForwardingSPNumInvocations,
                  bwDXSGroupNightForwardingGroupIndex, bwDXSGroupNightForwardingGroupID,
                  bwDXSGroupNightForwardingGroupNumInvocations }
    STATUS      current
    DESCRIPTION 
        "This group defines the statistics for the Group Night Forwarding Service."
    ::= { bwDXSExecutionMibGroups 122 }

  bwDXSExecutionPreAlertingAnnouncementServiceGroup OBJECT-GROUP
    OBJECTS     { bwDXSPreAlertingAnnouncementNumAttempts, bwDXSPreAlertingAnnouncementSPIndex,
                  bwDXSPreAlertingAnnouncementSPID, bwDXSPreAlertingAnnouncementSPNumAttempts,
                  bwDXSPreAlertingAnnouncementGroupIndex, bwDXSPreAlertingAnnouncementGroupID,
                  bwDXSPreAlertingAnnouncementGroupNumAttempts }
    STATUS      current
    DESCRIPTION 
        "This group defines the statistics for the Pre Alerting Announcement Service."
    ::= { bwDXSExecutionMibGroups 123 }

  bwDXSExecutionHotelingServiceGroup OBJECT-GROUP
    OBJECTS     { bwDXSHotelingAssociate, bwDXSHotelingDisassociate,
                  bwDXSHotelingTimeout, bwDXSHotelingSPIndex,
                  bwDXSHotelingSPID, bwDXSHotelingSPAssociate,
                  bwDXSHotelingSPDisassociate, bwDXSHotelingSPTimeout,
                  bwDXSHotelingGroupIndex, bwDXSHotelingGroupID,
                  bwDXSHotelingGroupAssociate, bwDXSHotelingGroupDisassociate,
                  bwDXSHotelingGroupTimeout }
    STATUS      current
    DESCRIPTION 
        "This group defines the statistics for the Hoteling Service."
    ::= { bwDXSExecutionMibGroups 124 }

  bwDXSExecutionBasicCompliance MODULE-COMPLIANCE
    STATUS      current
    DESCRIPTION 
        "BroadWorks Execution MIB compliance"

    MODULE      -- this module

        MANDATORY-GROUPS        {  
                  bwDXSExecutionImsGroup, bwDXSExecutionCapGroup, 
                  bwDXSExecutionSmdiGroup, bwDXSExecutionMediaResourceGroup, 
                  bwDXSExecutionWholeSalesGroup, 
                  bwDXSExecutionRealTimeAccntGroup, 
                  bwDXSExecutionExtCallLogsGroup, bwDXSExecutionXsBcctGroup, 
                  bwDXSExecutionCallpGroup, bwDXSExecutionSmtpGroup, 
                  bwDXSExecutionSipGroup, bwDXSExecutionAccntCodeServiceGroup, 
                  bwDXSExecutionAnonymousCallRejectionServiceGroup, 
                  bwDXSExecutionAuthenticationServiceGroup, 
                  bwDXSExecutionAutoAttendantServiceGroup, 
                  bwDXSExecutionCallCapacityServiceGroup, 
                  bwDXSExecutionCFAlwaysServiceGroup, 
                  bwDXSExecutionCFBusyServiceGroup, 
                  bwDXSExecutionCFNoAnswerServiceGroup, 
                  bwDXSExecutionCallNotifyServiceGroup, 
                  bwDXSExecutionCallParkServiceGroup, 
                  bwDXSExecutionCallPickupServiceGroup, 
                  bwDXSExecutionCallReturnServiceGroup, 
                  bwDXSExecutionCompilotCallMgrServiceGroup, 
                  bwDXSExecutionDoNotDisturbServiceGroup, 
                  bwDXSExecutionFlashCallXferServiceGroup, 
                  bwDXSExecutionFlashCallWaitingServiceGroup, 
                  bwDXSExecutionFlashConsultationServiceGroup, 
                  bwDXSExecutionFlash3wcServiceGroup, 
                  bwDXSExecutionHuntGroupServiceGroup, 
                  bwDXSExecutionIcpServiceGroup, 
                  bwDXSExecutionIpPhoneServiceGroup, 
                  bwDXSExecutionLastNumberRedialServiceGroup, 
                  bwDXSExecutionOcpServiceGroup, 
                  bwDXSExecutionPriorityAlertServiceGroup, 
                  bwDXSExecutionSelectiveCallAcceptanceServiceGroup, 
                  bwDXSExecutionSelectiveCallForwardServiceGroup, 
                  bwDXSExecutionSelectiveCallRejectionServiceGroup, 
                  bwDXSExecutionSimRingServiceGroup, 
                  bwDXSExecutionVoiceMessagingServiceGroup, 
                  bwDXSExecutionInterceptServiceGroup, 
                  bwDXSExecutionCallingLineIdBlockingServiceGroup, 
                  bwDXSExecutionSessionAuditServiceGroup, 
                  bwDXSExecutionCalWaitingServiceGroup, 
                  bwDXSExecutionAlternateNumberServiceGroup, 
                  bwDXSExecutionCustomerOriginatedTraceServiceGroup, 
                  bwDXSExecutionSpeedDialing8ServiceGroup, 
                  bwDXSExecutionMusicOnHoldServiceGroup, 
                  bwDXSExecutionThirdPartyMWIControlServiceGroup,
                  bwDXSExecutionCallForwardGroupNoAnswerServiceGroup, 
                  bwDXSExecutionSpeedDialing100ServiceGroup, 
                  bwDXSExecutionThirdPartyVoiceMailServiceGroup, 
                  bwDXSExecutionDirectedCallPickupServiceGroup, 
                  bwDXSExecutionFlashCallHoldServiceGroup, 
                  bwDXSExecutionDirectedCallPickupWithBargeInServiceGroup, 
                  bwDXSExecutionAutomaticCallBackServiceGroup, 
                  bwDXSExecutionRingTimeoutServiceGroup, 
                  bwDXSExecutionSequentialRingServiceGroup, 
                  bwDXSExecutionMaliciousCallTraceServiceGroup, 
                  bwDXSExecutionPreferredCarrierServiceGroup, 
                  bwDXSExecutionFamilySimRingServiceGroup, 
                  bwDXSExecutionDiversionInhibitorServiceGroup, 
                  bwDXSExecutionCustomRingbackServiceGroup, 
                  bwDXSExecutionMssGroup, bwDXSExecutionNrsGroup, 
                  bwDXSExecutionProtocolMonitorGroup, 
                  bwDXSExecutionQueueStatsGroup, 
                  bwDXSExecutionOverloadControlStatsGroup, 
                  bwDXSExecutionMoCountersGroup, 
                  bwDXSExecutionFaxMessagingServiceGroup, 
                  bwDXSExecutionTcpStatsGroup, 
                  bwDXSExecutionConcurrentFrameworkStatsGroup, 
                  bwDXSExecutionExtEmergencyRtgStatsGroup, 
                  bwDXSExecutionSoapGroup, 
                  bwDXSExecutionCallForwardingNotReachableGroup, 
                  bwDXSExecutionCongestionManagementGroup, 
                  bwDXSExecutionDnsQueryGroup, 
                  bwDXSExecutionExpensiveCallNotificationGroup, 
                  bwDXSExecutionLocationControlGroup, 
                  bwDXSExecutionCallRetrieveGroup, 
                  bwDXSExecutionBroadworksAnywhereGroup, 
                  bwDXSExecutionOfflineChargingGroup, bwDXSExecutionSmppGroup, 
                  bwDXSExecutionOcicStatsGroup, 
                  bwDXSExecutionCommunicationBarringGroup, 
                  bwDXSExecutionOnlineChargingStatsGroup, 
                  bwDXSExecutionCallBridgeGroup, 
                  bwDXSExecutionDirectoryNumberHuntingGroup, 
                  bwDXSExecutionAoCGroup,
                  bwDXSExecutionDiameterGroup,
                  bwDXSExecutionProfileLoadingGroup,
                  bwDXSCallLogStatisticStatsGroup,
                  bwDXSExternalCustomRingbackStatisticStatsGroup,
                  bwDXSCFGNRcStatisticStatsGroup,
                  bwDXSSHStatisticStatsGroup,
                  bwDXSExecutionGroupNightForwardingServiceGroup,
                  bwDXSExecutionPreAlertingAnnouncementServiceGroup,
                  bwDXSExecutionHotelingServiceGroup }

    ::= { bwDXSExecutionMibCompliancy 1 }
END

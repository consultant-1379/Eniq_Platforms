-- File Name : BW-IS41StackFault.mib

BW-IS41StackFault DEFINITIONS ::= BEGIN
  IMPORTS
    enterprises, MODULE-IDENTITY, NOTIFICATION-TYPE
      FROM SNMPv2-SMI
    alarmName, alarmState, common, component, correlationParameter, faultFields, identifier, npSS7SubsystemNumber, problemText, recommendedActionsText, severity, subcomponent, systemName, timeStamp, mapTierLevel, mapInstId, mapErrorCode, mapInfoLen, mapInfoStr, mapStatus, mapInstanceType, mapVariant, mapIp, mapPort, mapEmStatus, mapEmInfoAddr, mapEmInfoServerPort, mapEmInfoMinClientPort, mapEmInfoMaxClientPort
      FROM BroadworksFault;

  broadsoft MODULE-IDENTITY
    LAST-UPDATED  "201103240000Z"
    ORGANIZATION  "Broadsoft, Inc"
    CONTACT-INFO  "Broadsoft, Inc.
220 Perry Parkway
Gaithersburg, MD  20877
301-977-9440"
    DESCRIPTION
        "This MIB defines management information that is common to all elements in a Broadworks system."
    REVISION    "201103240000Z"
                DESCRIPTION     "Creating the mib."
    ::=  {  enterprises  6431  }

  broadworks  OBJECT IDENTIFIER
    ::=  {  broadsoft  1  }

  common  OBJECT IDENTIFIER
    ::=  {  broadworks  1  }

  systemFaults  OBJECT IDENTIFIER
    ::=  {  common  1  }

  bwPMemSS7IS41Launched  NOTIFICATION-TYPE
    OBJECTS     { identifier, timeStamp, alarmName, systemName, severity, component, subcomponent, problemText, recommendedActionsText }
    STATUS      current
    DESCRIPTION
        "This notification indicates that the emSS7IS41 process has been started.
@severity:informational
@subcomponent:processmonitor
@correlationrules:bwPMemSS7IS41Launched, bwPMemSS7IS41ShutDown, bwPMemSS7IS41Started, and bwPMemSS7IS41Death can be correlated into a single notification.  These events have to be considered as a transition of the state machine for the management of the emSS7IS41 process running on some of the BroadWorks servers."
-- @feature:158606
    ::=  {  systemFaults 12401  }

  bwPMemSS7IS41ShutDown  NOTIFICATION-TYPE
    OBJECTS     { identifier, timeStamp, alarmName, systemName, severity, component, subcomponent, problemText, recommendedActionsText }
    STATUS      current
    DESCRIPTION
        "This notification indicates that the emSS7IS41 process has been manually shut down.
@severity:informational
@subcomponent:processmonitor
@correlationrules:bwPMemSS7IS41Launched, bwPMemSS7IS41ShutDown, bwPMemSS7IS41Started, and bwPMemSS7IS41Death can be correlated into a single notification.  These events have to be considered as a transition of the state machine for the management of the emSS7IS41 process running on some of the BroadWorks servers."
-- @feature:158606
    ::=  {  systemFaults 12402  }

  bwPMemSS7IS41Restarted  NOTIFICATION-TYPE
    OBJECTS     { identifier, timeStamp, alarmName, systemName, severity, component, subcomponent, problemText, recommendedActionsText }
    STATUS      current
    DESCRIPTION
        "This notification provides the date and time of the emSS7IS41 process restart.
@severity:informational
@subcomponent:processmonitor
@correlationrules:bwPMemSS7IS41Launched, bwPMemSS7IS41ShutDown, bwPMemSS7IS41Started, and bwPMemSS7IS41Death can be correlated into a single notification.  These events have to be considered as a transition of the state machine for the management of the emSS7IS41 process running on some of the BroadWorks servers."
-- @feature:158606
    ::=  {  systemFaults 12403  }

  bwPMemSS7IS41Death  NOTIFICATION-TYPE
    OBJECTS     { identifier, timeStamp, alarmName, systemName, severity, component, subcomponent, problemText, recommendedActionsText }
    STATUS      current
    DESCRIPTION
        "This notification provides the date and time of the emSS7IS41 process death.
@severity:critical
@subcomponent:processmonitor
@correlationrules:bwPMemSS7IS41Launched, bwPMemSS7IS41ShutDown, bwPMemSS7IS41Started, and bwPMemSS7IS41Death can be correlated into a single notification.  These events have to be considered as a transition of the state machine for the management of the emSS7IS41 process running on some of the BroadWorks servers."
-- @feature:158606
    ::=  {  systemFaults 12404  }

  bwPMss7IS41Launched  NOTIFICATION-TYPE
    OBJECTS     { identifier, timeStamp, alarmName, systemName, severity, component, subcomponent, problemText, recommendedActionsText }
    STATUS      current
    DESCRIPTION
        "This notification indicates that the ss7IS41 process has been started.
@severity:informational
@subcomponent:processmonitor
@correlationrules:bwPMss7IS41Launched, bwPMss7IS41ShutDown, bwPMss7IS41Started, and bwPMss7IS41Death can be correlated into a single notification.  These events have to be considered as a transition of the state machine for the management of the ss7IS41 process running on some of the BroadWorks servers."
-- @feature:158606
    ::=  {  systemFaults 12405  }

  bwPMss7IS41ShutDown  NOTIFICATION-TYPE
    OBJECTS     { identifier, timeStamp, alarmName, systemName, severity, component, subcomponent, problemText, recommendedActionsText }
    STATUS      current
    DESCRIPTION
        "This notification indicates that the ss7IS41 process has been manually shut down.
@severity:informational
@subcomponent:processmonitor
@correlationrules:bwPMss7IS41Launched, bwPMss7IS41ShutDown, bwPMss7IS41Started, and bwPMss7IS41Death can be correlated into a single notification.  These events have to be considered as a transition of the state machine for the management of the ss7IS41 process running on some of the BroadWorks servers."
-- @feature:158606
    ::=  {  systemFaults 12406  }

  bwPMss7IS41Restarted  NOTIFICATION-TYPE
    OBJECTS     { identifier, timeStamp, alarmName, systemName, severity, component, subcomponent, problemText, recommendedActionsText }
    STATUS      current
    DESCRIPTION
        "This notification provides the date and time of the ss7IS41 process restart.
@severity:informational
@subcomponent:processmonitor
@correlationrules:bwPMss7IS41Launched, bwPMss7IS41ShutDown, bwPMss7IS41Started, and bwPMss7IS41Death can be correlated into a single notification.  These events have to be considered as a transition of the state machine for the management of the ss7IS41 process running on some of the BroadWorks servers."
-- @feature:158606
    ::=  {  systemFaults 12407  }

  bwPMss7IS41Death  NOTIFICATION-TYPE
    OBJECTS     { identifier, timeStamp, alarmName, systemName, severity, component, subcomponent, problemText, recommendedActionsText }
    STATUS      current
    DESCRIPTION
        "This notification provides the date and time of the ss7IS41 process death.
@severity:critical
@subcomponent:processmonitor
@correlationrules:bwPMss7IS41Launched, bwPMss7IS41ShutDown, bwPMss7IS41Started, and bwPMss7IS41Death can be correlated into a single notification.  These events have to be considered as a transition of the state machine for the management of the ss7IS41 process running on some of the BroadWorks servers."
-- @feature:158606
    ::=  {  systemFaults 12408  }

  bwPMss7IS41BridgeLaunched  NOTIFICATION-TYPE
    OBJECTS     { identifier, timeStamp, alarmName, systemName, severity, component, subcomponent, problemText, recommendedActionsText }
    STATUS      current
    DESCRIPTION
        "This notification indicates that the ss7IS41Bridge process has been started.
@severity:informational
@subcomponent:processmonitor
@correlationrules:bwPMss7IS41BridgeLaunched, bwPMss7IS41BridgeShutDown, bwPMss7IS41BridgeStarted, and bwPMss7IS41BridgeDeath can be correlated into a single notification.  These events have to be considered as a transition of the state machine for the management of the ss7IS41Bridge process running on some of the BroadWorks servers."
-- @feature:158606
    ::=  {  systemFaults 12409  }

  bwPMss7CAPBridgeShutDown  NOTIFICATION-TYPE
    OBJECTS     { identifier, timeStamp, alarmName, systemName, severity, component, subcomponent, problemText, recommendedActionsText }
    STATUS      current
    DESCRIPTION
        "This notification indicates that the ss7CAPBridge process has been manually shut down.
@severity:informational
@subcomponent:processmonitor
@correlationrules:bwPMss7IS41BridgeLaunched, bwPMss7IS41BridgeShutDown, bwPMss7IS41BridgeStarted, and bwPMss7IS41BridgeDeath can be correlated into a single notification.  These events have to be considered as a transition of the state machine for the management of the ss7IS41Bridge process running on some of the BroadWorks servers."
-- @feature:158606
    ::=  {  systemFaults 12410  }

  bwPMss7IS41BridgeRestarted  NOTIFICATION-TYPE
    OBJECTS     { identifier, timeStamp, alarmName, systemName, severity, component, subcomponent, problemText, recommendedActionsText }
    STATUS      current
    DESCRIPTION
        "This notification provides the date and time of the ss7IS41Bridge process restart.
@severity:informational
@subcomponent:processmonitor
@correlationrules:bwPMss7IS41BridgeLaunched, bwPMss7IS41BridgeShutDown, bwPMss7IS41BridgeStarted, and bwPMss7IS41BridgeDeath can be correlated into a single notification.  These events have to be considered as a transition of the state machine for the management of the ss7IS41Bridge process running on some of the BroadWorks servers."
-- @feature:158606
    ::=  {  systemFaults 12411  }

  bwPMss7IS41BridgeDeath  NOTIFICATION-TYPE
    OBJECTS     { identifier, timeStamp, alarmName, systemName, severity, component, subcomponent, problemText, recommendedActionsText }
    STATUS      current
    DESCRIPTION
        "This notification provides the date and time of the ss7CAPBridge process death.
@severity:critical
@subcomponent:processmonitor
@correlationrules:bwPMss7IS41BridgeLaunched, bwPMss7IS41BridgeShutDown, bwPMss7IS41BridgeStarted, and bwPMss7IS41BridgeDeath can be correlated into a single notification.  These events have to be considered as a transition of the state machine for the management of the ss7IS41Bridge process running on some of the BroadWorks servers."
-- @feature:158606
    ::=  {  systemFaults 12412  }
      
  bwPMss7IS41OAMBridgeLaunched  NOTIFICATION-TYPE
    OBJECTS     { identifier, timeStamp, alarmName, systemName, severity, component, subcomponent, problemText, recommendedActionsText }
    STATUS      current
    DESCRIPTION
        "This notification indicates that the ss7IS41OAMBridge process has been started.
@severity:informational
@subcomponent:processmonitor
@correlationrules:bwPMss7IS41OAMBridgeLaunched, bwPMss7IS41OAMBridgeShutDown, bwPMss7IS41OAMBridgeStarted, and bwPMss7IS41OAMBridgeDeath can be correlated into a single notification.  These events have to be considered as a transition of the state machine for the management of the ss7IS41OAMBridge process running on some of the BroadWorks servers."
-- @feature:177227
    ::=  {  systemFaults 12413  }

  bwPMss7IS41OAMBridgeShutDown  NOTIFICATION-TYPE
    OBJECTS     { identifier, timeStamp, alarmName, systemName, severity, component, subcomponent, problemText, recommendedActionsText }
    STATUS      current
    DESCRIPTION
        "This notification indicates that the ss7IS41OAMBridge process has been manually shut down.
@severity:informational
@subcomponent:processmonitor
@correlationrules:bwPMss7IS41OAMBridgeLaunched, bwPMss7IS41OAMBridgeShutDown, bwPMss7IS41OAMBridgeStarted, and bwPMss7IS41OAMBridgeDeath can be correlated into a single notification.  These events have to be considered as a transition of the state machine for the management of the ss7IS41OAMBridge process running on some of the BroadWorks servers."
-- @feature:177227
    ::=  {  systemFaults 12414  }

  bwPMss7IS41OAMBridgeRestarted  NOTIFICATION-TYPE
    OBJECTS     { identifier, timeStamp, alarmName, systemName, severity, component, subcomponent, problemText, recommendedActionsText }
    STATUS      current
    DESCRIPTION
        "This notification provides the date and time of the ss7IS41OAMBridge process restart.
@severity:informational
@subcomponent:processmonitor
@correlationrules:bwPMss7IS41OAMBridgeLaunched, bwPMss7IS41OAMBridgeShutDown, bwPMss7IS41OAMBridgeStarted, and bwPMss7IS41OAMBridgeDeath can be correlated into a single notification.  These events have to be considered as a transition of the state machine for the management of the ss7IS41OAMBridge process running on some of the BroadWorks servers."
-- @feature:177227
    ::=  {  systemFaults 12415  }

  bwPMss7IS41OAMBridgeDeath  NOTIFICATION-TYPE
    OBJECTS     { identifier, timeStamp, alarmName, systemName, severity, component, subcomponent, problemText, recommendedActionsText }
    STATUS      current
    DESCRIPTION
        "This notification provides the date and time of the ss7IS41OAMBridge process death.
@severity:critical
@subcomponent:processmonitor
@correlationrules:bwPMss7IS41OAMBridgeLaunched, bwPMss7IS41OAMBridgeShutDown, bwPMss7IS41OAMBridgeStarted, and bwPMss7IS41OAMBridgeDeath can be correlated into a single notification.  These events have to be considered as a transition of the state machine for the management of the ss7IS41OAMBridge process running on some of the BroadWorks servers."
-- @feature:177227
    ::=  {  systemFaults 12416  }
    
  bwSS7Is41SubsystemDown  NOTIFICATION-TYPE
    OBJECTS     { identifier, timeStamp, alarmName, systemName, severity, alarmState, component, subcomponent, problemText, recommendedActionsText, correlationParameter, npSS7SubsystemNumber }
    STATUS      current
    DESCRIPTION
        "A required IS41 subsystem is not available for use.
@severity:high
@subcomponent:ss7Is41"
-- @feature:177227
    ::=  {  systemFaults 12417  }

  bwSS7StackIs41NotifyError  NOTIFICATION-TYPE
    OBJECTS     { identifier, timeStamp, alarmName, systemName, severity, component, subcomponent, problemText, recommendedActionsText, mapTierLevel, mapInstId, mapErrorCode, mapInfoLen, mapInfoStr }
    STATUS      current
    DESCRIPTION
        "This notification provides information about IS41 error.
@severity:high
@subcomponent:map"
-- @feature:PR-49155
    ::=  {  systemFaults 12418  }

  bwSS7StackIs41InstanceStatusInd  NOTIFICATION-TYPE
    OBJECTS     { identifier, timeStamp, alarmName, systemName, severity, component, subcomponent, problemText, recommendedActionsText, mapStatus, mapTierLevel, mapInstanceType, mapInstId, mapVariant, mapIp, mapPort }
    STATUS      current
    DESCRIPTION
        "This notification provides information about IS41 instance status indication..
@severity:low
@subcomponent:map"
-- @feature:PR-49155
    ::=  {  systemFaults 12419  }

  bwSS7StackIs41ClibEmStatus  NOTIFICATION-TYPE
    OBJECTS     { identifier, timeStamp, alarmName, systemName, severity, component, subcomponent, problemText, recommendedActionsText, mapEmStatus, mapEmInfoAddr, mapEmInfoServerPort, mapEmInfoMinClientPort, mapEmInfoMaxClientPort }
    STATUS      current
    DESCRIPTION
        "This notification provides information about status of the IS41 EM.
@severity:low
@subcomponent:map"
-- @feature:PR-49155
    ::=  {  systemFaults 12420  }
END

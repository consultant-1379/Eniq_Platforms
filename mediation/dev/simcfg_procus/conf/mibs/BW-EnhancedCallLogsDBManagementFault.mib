-- File Name : BW-EnhancedCallLogsDBManagementFault.mib
BW-EnhancedCallLogsDBManagementFault DEFINITIONS ::= BEGIN
  IMPORTS
    NOTIFICATION-TYPE, MODULE-IDENTITY
      FROM SNMPv2-SMI
    common, identifier, timeStamp, alarmName, systemName, severity, alarmState, component, subcomponent, problemText, recommendedActionsText
      FROM BroadworksFault;

  systemFaults MODULE-IDENTITY
    LAST-UPDATED  "201206010000Z"
    ORGANIZATION  "Broadsoft, Inc"
    CONTACT-INFO  "Broadsoft, Inc.
9737 Washingtonian Blvd
Suite 350
Gaithersburg , MD 20878
Tel: +1-301-977-9440"
    DESCRIPTION
        "This MIB defines the faults for the BroadWorks EnhancedCallLogsDBManagement Application."
    REVISION    "201206010000Z"
                DESCRIPTION     "Creation of the Fault MIB."
    ::=  {  common  1  }

  bwPMenhancedCallLogsDBManagementLaunched  NOTIFICATION-TYPE
    OBJECTS     { identifier, timeStamp, alarmName, systemName, severity, component, subcomponent, problemText, recommendedActionsText }
    STATUS      current
    DESCRIPTION
        "This notification indicates that the ECL DB Management application has been started.
@severity:informational
@subcomponent:processmonitor
@correlationrules:bwPMenhancedCallLogsDBManagementLaunched, bwPMenhancedCallLogsDBManagementShutDown, bwPMenhancedCallLogsDBManagementRestarted, bwPMenhancedCallLogsDBManagementDeath and bwPMenhancedCallLogsDBManagementOutOfMemory can be correlated into a single alarm.  These events have to be considered as a transition of the state machine for the management of the enhancedCallLogsDBManagement process"
-- @feature:165352
    ::=  {  systemFaults 11201  }

  bwPMenhancedCallLogsDBManagementShutDown  NOTIFICATION-TYPE
    OBJECTS     { identifier, timeStamp, alarmName, systemName, severity, component, subcomponent, problemText, recommendedActionsText }
    STATUS      current
    DESCRIPTION
        "This notification indicates that the ECL DB Management application has been manually shut down.
@severity:informational
@subcomponent:processmonitor
@correlationrules:bwPMenhancedCallLogsDBManagementLaunched, bwPMenhancedCallLogsDBManagementShutDown, bwPMenhancedCallLogsDBManagementRestarted, bwPMenhancedCallLogsDBManagementDeath and bwPMenhancedCallLogsDBManagementOutOfMemory can be correlated into a single alarm.  These events have to be considered as a transition of the state machine for the management of the enhancedCallLogsDBManagement process"
-- @feature:165352
    ::=  {  systemFaults 11202  }

  bwPMenhancedCallLogsDBManagementRestarted  NOTIFICATION-TYPE
    OBJECTS     { identifier, timeStamp, alarmName, systemName, severity, component, subcomponent, problemText, recommendedActionsText }
    STATUS      current
    DESCRIPTION
        "This notification provides the date and time of the ECL DB Management application restart.
@severity:informational
@subcomponent:processmonitor
@correlationrules:bwPMenhancedCallLogsDBManagementLaunched, bwPMenhancedCallLogsDBManagementShutDown, bwPMenhancedCallLogsDBManagementRestarted, bwPMenhancedCallLogsDBManagementDeath and bwPMenhancedCallLogsDBManagementOutOfMemory can be correlated into a single alarm.  These events have to be considered as a transition of the state machine for the management of the enhancedCallLogsDBManagement process"
-- @feature:165352
    ::=  {  systemFaults 11203  }

  bwPMenhancedCallLogsDBManagementDeath  NOTIFICATION-TYPE
    OBJECTS     { identifier, timeStamp, alarmName, systemName, severity, component, subcomponent, problemText, recommendedActionsText }
    STATUS      current
    DESCRIPTION
        "This notification provides the date and time of the ECL DB Management application death.
@severity:critical
@subcomponent:processmonitor
@correlationrules:bwPMenhancedCallLogsDBManagementLaunched, bwPMenhancedCallLogsDBManagementShutDown, bwPMenhancedCallLogsDBManagementRestarted, bwPMenhancedCallLogsDBManagementDeath and bwPMenhancedCallLogsDBManagementOutOfMemory can be correlated into a single alarm.  These events have to be considered as a transition of the state machine for the management of the enhancedCallLogsDBManagement process"
-- @feature:165352
    ::=  {  systemFaults 11204  }
    
bwPMenhancedCallLogsDBManagementOutOfMemory  NOTIFICATION-TYPE
     OBJECTS     { identifier, timeStamp, alarmName, systemName, severity, component, subcomponent, problemText, recommendedActionsText }
     STATUS      current
     DESCRIPTION
         "This notification provides the date and time when the ECL DB Management application ran out of memory.
 @severity:high
 @subcomponent:processmonitor
 @correlationrules:bwPMenhancedCallLogsDBManagementLaunched, bwPMenhancedCallLogsDBManagementShutDown, bwPMenhancedCallLogsDBManagementRestarted, bwPMenhancedCallLogsDBManagementDeath, and bwPMenhancedCallLogsDBManagementOutOfMemory can be correlated into a single alarm.  These events have to be considered as a transition of the state machine for the management of the enhancedCallLogsDBManagement process"
-- @feature:165352
    ::=  {  systemFaults 11205  }  

END

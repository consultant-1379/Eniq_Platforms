--===============================================================
-- File Name : BW-FileRepos.mib
-- Date      : 05/08/2013
-- Author    : BroadSoft Inc.
--===============================================================

BW-FileRepos DEFINITIONS ::= BEGIN
  IMPORTS
    DisplayString
      FROM SNMPv2-TC
    MODULE-COMPLIANCE, OBJECT-GROUP          
      FROM SNMPv2-CONF
    enterprises, MODULE-IDENTITY, NOTIFICATION-TYPE, OBJECT-TYPE, Gauge32, Counter32, Integer32, Unsigned32
      FROM SNMPv2-SMI;
  
  broadsoft  MODULE-IDENTITY
    LAST-UPDATED  "201305080000Z"
    ORGANIZATION  "Broadsoft, Inc"
    CONTACT-INFO  "Broadsoft, Inc.
9737 Washingtonian Blvd
Suite 350
Gaithersburg , MD 20878
Tel: +1-301-977-9440"
    DESCRIPTION    
        "This MIB contains the performance measurements related to the BroadWorks
         FileRepos application."
    REVISION    "201305080000Z"
      DESCRIPTION "Creation of the MIB"
    ::=  {  enterprises  6431  }

  broadworks  OBJECT IDENTIFIER
    ::=  {  broadsoft  1  }

  fileRepos  OBJECT IDENTIFIER
    ::=  {  broadworks  35  }

  repository  OBJECT IDENTIFIER
    ::=  {  fileRepos  1  }

  replication  OBJECT IDENTIFIER
    ::=  {  fileRepos  2  }

  bwFileReposMibConformance  OBJECT IDENTIFIER
    ::=  {  fileRepos  1000  }

-- repository modules  ...........................................

  bwFileReposCacheIndexedDirectories  OBJECT-TYPE  
    SYNTAX      Gauge32
    MAX-ACCESS  read-only
    STATUS      current
    DESCRIPTION    
        "This is the number of indexed cached directories."
-- @feature:154396
    ::=  {  repository  1  }

  bwFileReposCacheSize  OBJECT-TYPE  
    SYNTAX      Gauge32
    MAX-ACCESS  read-only
    STATUS      current
    DESCRIPTION    
        "This is the size of the look up table."
-- @feature:154396
    ::=  {  repository  2  }

  bwFileReposCacheCapacity  OBJECT-TYPE  
    SYNTAX      Gauge32
    MAX-ACCESS  read-only
    STATUS      current
    DESCRIPTION    
        "This is the look up table capacity."
-- @feature:154396
    ::=  {  repository  3  }

  bwFileReposCacheLookUpCount  OBJECT-TYPE  
    SYNTAX      Counter32
    MAX-ACCESS  read-write
    STATUS      current
    DESCRIPTION    
        "This is the number of look up performed."
-- @feature:154396
    ::=  {  repository  4  }

  bwFileReposCacheLookUpHits  OBJECT-TYPE  
    SYNTAX      Counter32
    MAX-ACCESS  read-write
    STATUS      current
    DESCRIPTION    
        "This is the number of look up which returned a match."
-- @feature:154396
    ::=  {  repository  5  }

  bwFileReposCacheEvictions  OBJECT-TYPE  
    SYNTAX      Counter32
    MAX-ACCESS  read-write
    STATUS      current
    DESCRIPTION    
        "This is the number of entries that were evicted from the cache."
-- @feature:154396
    ::=  {  repository  6  }

-- Replication modules  ...........................................

  bwFileReposReplicationStatsTable  OBJECT-TYPE
    SYNTAX    SEQUENCE  OF  BwFileReposReplicationStatsEntry
    MAX-ACCESS  not-accessible
    STATUS    current
    DESCRIPTION
      "This table contains counters for FileRepos replication."
    ::=  { replication  1 }

  bwFileReposReplicationStatsEntry  OBJECT-TYPE
    SYNTAX    BwFileReposReplicationStatsEntry
    MAX-ACCESS  not-accessible
    STATUS    current
    DESCRIPTION
      "Definition of the entries for bwFileReposReplicationStatsTable."
    INDEX    {  bwFileReposReplicationStatsIndex  }
    ::=  { bwFileReposReplicationStatsTable 1 }

  BwFileReposReplicationStatsEntry  ::=  SEQUENCE {
    bwFileReposReplicationStatsIndex    Unsigned32,
    bwFileReposReplicationPeer          DisplayString,
    bwFileReposReplicationRxSuccessful  Counter32,
    bwFileReposReplicationRxFailed      Counter32,
    bwFileReposReplicationTxSuccessful  Counter32,
    bwFileReposReplicationTxFailed      Counter32
    }

  bwFileReposReplicationStatsIndex  OBJECT-TYPE
    SYNTAX      Unsigned32
    MAX-ACCESS  read-only
    STATUS      current
    DESCRIPTION
        "This integer represents an index in table bwFileReposReplicationStatsTable. The index represents a peer entry in the table."
-- @feature:154396
    ::=  {  bwFileReposReplicationStatsEntry  1  }

  bwFileReposReplicationPeer  OBJECT-TYPE  
    SYNTAX      DisplayString
    MAX-ACCESS  read-only
    STATUS      current
    DESCRIPTION    
        "This is the peer IP."
-- @feature:154396
    ::=  {  bwFileReposReplicationStatsEntry  2  }

  bwFileReposReplicationRxSuccessful  OBJECT-TYPE  
    SYNTAX      Counter32
    MAX-ACCESS  read-write
    STATUS      current
    DESCRIPTION    
        "This is the number of successful replication request."
-- @feature:154396
    ::=  {  bwFileReposReplicationStatsEntry  3  }

  bwFileReposReplicationRxFailed  OBJECT-TYPE  
    SYNTAX      Counter32
    MAX-ACCESS  read-write
    STATUS      current
    DESCRIPTION    
        "This is the number of failed replication request."
-- @feature:154396
    ::=  {  bwFileReposReplicationStatsEntry  4  }

  bwFileReposReplicationTxSuccessful  OBJECT-TYPE  
    SYNTAX      Counter32
    MAX-ACCESS  read-write
    STATUS      current
    DESCRIPTION    
        "This is the number of successful replication attempts."
-- @feature:154396
    ::=  {  bwFileReposReplicationStatsEntry  5  }

  bwFileReposReplicationTxFailed  OBJECT-TYPE  
    SYNTAX      Counter32
    MAX-ACCESS  read-write
    STATUS      current
    DESCRIPTION    
        "This is the number of failed replication attempts."
-- @feature:154396
    ::=  {  bwFileReposReplicationStatsEntry  6  }

-- BroadWorks File Repos MIB Conformance Definition  

  bwFileReposMibGroups OBJECT IDENTIFIER 
    ::= { bwFileReposMibConformance 1 }

  bwFileReposMibCompliancy OBJECT IDENTIFIER
    ::= { bwFileReposMibConformance 2 }

  bwFileReposRepositoryGroup OBJECT-GROUP
    OBJECTS     { bwFileReposCacheIndexedDirectories, bwFileReposCacheSize,
                  bwFileReposCacheCapacity, bwFileReposCacheLookUpCount,
                  bwFileReposCacheLookUpHits, bwFileReposCacheEvictions
                }
    STATUS      current
    DESCRIPTION 
        "This group defines the statistics for the FileRepos Repository."
    ::= { bwFileReposMibGroups 1 }

  bwFileReposReplicationGroup OBJECT-GROUP
    OBJECTS     { bwFileReposReplicationStatsIndex, bwFileReposReplicationPeer,   
                  bwFileReposReplicationRxSuccessful, bwFileReposReplicationRxFailed,
                  bwFileReposReplicationTxSuccessful, bwFileReposReplicationTxFailed
                }
    STATUS      current
    DESCRIPTION 
        "This group defines the statistics for the FileRepos Replication."
    ::= { bwFileReposMibGroups 2 }

  bwProvisioningFileReposBasicCompliance MODULE-COMPLIANCE
    STATUS      current
    DESCRIPTION 
        "BroadWorks FileRepos MIB compliance"

    MODULE      -- this module

        MANDATORY-GROUPS        { bwFileReposRepositoryGroup,
                                  bwFileReposReplicationGroup }

    ::= { bwFileReposMibCompliancy 1 }

END

-- extracted from draft-ietf-pwe3-enet-mib-06.txt
-- at Fri Jul 22 06:35:26 2005

  PW-ENET-STD-MIB DEFINITIONS ::= BEGIN 
   
  IMPORTS 
      OBJECT-TYPE, MODULE-IDENTITY 
          FROM SNMPv2-SMI                    -- [RFC2578] 
       
      MODULE-COMPLIANCE, OBJECT-GROUP 
          FROM SNMPv2-CONF                   -- [RFC2580] 
       
      StorageType, RowStatus 
          FROM SNMPv2-TC                     -- [RFC2579] 
   
      InterfaceIndexOrZero 
          FROM IF-MIB                        -- [RFC2863]
   
      ZeroBasedCounter32 
          FROM RMON2-MIB                     -- [RFC2021]
   
      pwIndex
          FROM PW-STD-MIB                    -- [PWMIB]
                                    -- RFC Editor: Please replace 
                                    -- PWMIB with correct RFC #
       
      pwMIB, PwVlanCfg, PwIndexType 
          FROM PW-TC-STD-MIB;                -- [PWTC]
                                    -- RFC Editor: Please replace 
                                    -- PWTC with correct RFC #

           
  pwEnetStdMIB MODULE-IDENTITY 
      LAST-UPDATED "200406101200Z"  -- 10 June 2004 12:00:00 GMT 
      ORGANIZATION "IETF PWE3 Working group"  
      CONTACT-INFO 
           "David Zelig 
            E-mail: davidz@corrigent.com 
           
            Thomas D. Nadeau 
            Email:  tnadeau@cisco.com 
          " 
      DESCRIPTION  
          "This MIB module describes a model for managing Ethernet  
          point-to-point pseudo wire services over a Packet  
          Switched Network (PSN). 
           
          Copyright (C) The Internet Society (date).  This version 
          of this MIB module is part of RFC yyyy;  see the RFC 
          itself for full legal notices. 
     -- RFC Editor: replace yyyy with actual RFC number & remove this note 
          " 
   
     -- Revision history. 
     REVISION "200507121200Z"  -- 12 July 2005 12:00:00 GMT 
     DESCRIPTION "Initial version published as part of RFC XXXX."
        -- RFC Editor: Please replace XXXX with RFC number.
        ::= { pwMIB 8888 }  -- RFC Editor: please replace 
                            -- XXXX with IANA assigne value. 
                            -- See IANA considerations sect.
   
  pwEnetObjects        OBJECT IDENTIFIER ::= { pwEnetStdMIB 1 } 
  pwEnetConformance    OBJECT IDENTIFIER ::= { pwEnetStdMIB 2 } 
   
  -- 
  -- Ethernet PW table 
  -- 
   
  pwEnetTable  OBJECT-TYPE 
      SYNTAX SEQUENCE OF PwEnetEntry 
      MAX-ACCESS  not-accessible 
      STATUS     current 
      DESCRIPTION  
          "This table contains the index to the Ethernet tables  
          associated with this ETH PW, the VLAN configuration and  
          VLAN mode." 
      ::= { pwEnetObjects 1 } 
   
  pwEnetEntry  OBJECT-TYPE 
      SYNTAX     PwEnetEntry 
      MAX-ACCESS  not-accessible 
      STATUS     current 
      DESCRIPTION  
          "This table is indexed by the same index that was created  
          for the associated entry in the PW generic table in the PW  
          MIB module. 
          The PwIndex and the pwEnetPwInstance are used as indexes  
          to allow multiple VLANs to exist on the same PW. 
                           
          An entry is created in this table by the agent for every  
          entry in the pwTable with a pwType of 'ethernetTagged' 
          or 'ethernet'. Additional rows may be created by the  
          operator or the agent if multiple entries are required for 
          the same PW. 
       
          The value of pwEnetPwInstance can be arbitrary selected 
          to make the row unique, however implementations that know 
          the VLAN field value when the row is created MAY use the  
          value of the VLAN itself for better readability and  
          backward compatibility with older versions of this MIB  
          module. 
   
          This table provides Ethernet port mapping and VLAN  
          configuration for each Ethernet PW." 
   
      INDEX { pwIndex, pwEnetPwInstance } 
      ::= { pwEnetTable 1 } 

  PwEnetEntry ::= SEQUENCE { 
         pwEnetPwInstance    PwIndexType, 
         pwEnetPwVlan        PwVlanCfg, 
         pwEnetVlanMode      INTEGER, 
         pwEnetPortVlan      PwVlanCfg, 
   
         pwEnetPortIfIndex   InterfaceIndexOrZero, 
         pwEnetVcIfIndex     InterfaceIndexOrZero, 
   
         pwEnetRowStatus     RowStatus, 
         pwEnetStorageType   StorageType 
     } 
   
  pwEnetPwInstance  OBJECT-TYPE 
      SYNTAX      PwIndexType 
      MAX-ACCESS  not-accessible 
      STATUS      current 
      DESCRIPTION  
          "If multiple rows are mapped to the same PW, this index is 
           used to uniquely identify the individual row. 
           If the value of the VLAN field is known at the time of   
           of row creation, the value of pwEnetPwVlan MAY be used  
           for better readability and backward compatibility with  
           older versions of this MIB module. Otherwise the value 
           of '1' SHOULD be set to the first row for each pwIndex 
           for better readability and in order that the management 
           application would know in advance how to access the  
           first row when it was created by the agent. 
          " 
      ::= { pwEnetEntry 1 } 
   
  pwEnetPwVlan  OBJECT-TYPE 
      SYNTAX      PwVlanCfg 
      MAX-ACCESS  read-create 
      STATUS      current 
      DESCRIPTION  
          "This Object defines the (service delimiting) VLAN field  
          value on the PW. The value of 4097 MUST be used if the  
          object is not applicable, for example when mapping all  
          packets from an Ethernet port to this PW (raw mode). 
          The value of 4096 MUST be set to indicate untagged frames  
          (from the PW point of view), i.e. when pwEnetVlanMode  
          equals 'noChange' and pwEnetPortVlan equals 4096." 
      ::= { pwEnetEntry 2 } 
   
  pwEnetVlanMode  OBJECT-TYPE 
      SYNTAX     INTEGER { 
                            other(0), 
                            portBased(1), 
                            noChange(2), 
                            changeVlan(3), 
                            addVlan(4), 
                            removeVlan(5) 
      } 
      MAX-ACCESS  read-create 
      STATUS     current 
      DESCRIPTION  
          "Indicates the mode of VLAN handling between the port  
           associated to the PW and the PW encapsulation. 

          - 'other' indicate operation that is not defined by 
            this MIB module. 
   
          - 'portBased' indicates that the forwarder will forward 
            packets between the port and the PW independent of their 
            structure (i.e. there is no service delimiting VLAN tags 
            from the PE standpoint).  
   
          - 'noChange' indicates that the PW contains the original 
             user VLAN, as specified in pwEnetPortVlan, i.e. the 
             VLAN on the PE-CE link is the service delimiting tag 
             and is kept as is on the PW. This is allowed only for 
             pwType equal 'ethernetTagged'.  
   
          - 'changeVlan' indicates that the VLAN field on the PW 
            may be different than the VLAN field on the user's  
            port. the VLAN on the PE-CE link is the service delimiting 
            tag but has a different value on the PW. 
   
          - 'removeVlan' indicates that the encapsulation on the  
            PW does not include the service delimiting VLAN field.  
            Note that PRI bits transparency is lost in this case. 
   
          - 'addVlan' indicate that a VLAN field will be added 
            on the PSN bound direction. pwEnetPwVlan indicates 
            the value that will be added.  
   
          - Implementation of 'portsbased', 'removeVlan', 'addVlan'  
            'other' and 'changeVlan' is OPTIONAL. 
          " 
      DEFVAL { noChange } 
      ::= { pwEnetEntry 3 } 
   
  pwEnetPortVlan  OBJECT-TYPE 
      SYNTAX     PwVlanCfg 
      MAX-ACCESS read-create 
      STATUS     current 
      DESCRIPTION  
          "This object defines the VLAN value on the physical port (or  
          VPLS virtual port) or a mapping of the whole port traffic  
          to the same PW. 
           
          The value of '4097' NUST be used if the whole port traffic 
          is mapped to the same PW. Note that a pwType of  
          'ethernetTagged' can still be used if service delimiting tag 
          is added on the PW (pwEnetVlanMode equals 'addVlan'). 
           
          It MUST be equal to pwEnetPwVlan if pwEnetVlanMode  
          equals'noChange'. 
           
          The value 4096 indicates that packet without a VLAN field  
          (i.e. untagged frames) on the port are associated to this  
          PW. This allows the same behaviors as assigning 'Default  
          VLAN' to un-tagged frames. 
          " 
      DEFVAL  { 4097 } 
      ::= { pwEnetEntry 4 } 
   
  pwEnetPortIfIndex  OBJECT-TYPE 
      SYNTAX      InterfaceIndexOrZero 
      MAX-ACCESS  read-create 
      STATUS      current 
      DESCRIPTION  
          "This object is used to specify the ifIndex of the Ethernet 
           port associated with this PW for point-to-point Ethernet  
           service, or the ifIndex of the virtual interface of the  
           VPLS instance associated with the PW if the service is  
           VPLS. Two rows in this table can point to the same ifIndex 
           only if: 
   
           1) It is required to support multiple COS on a MPLS PSN  
              for the same service (i.e.: a combination of ports and  
              VLANs) by the use of multiple PW, each with a different 
              COS. 
   
           2) There is no overlap of VLAN values specified in  
              pwEnetPortVlan that are associated with this port. 
   
           A value of zero indicates that association to an ifIndex is 
           not yet known." 
        
      ::= { pwEnetEntry 5 } 
   
  pwEnetVcIfIndex  OBJECT-TYPE 
      SYNTAX     InterfaceIndexOrZero 
      MAX-ACCESS read-create 
      STATUS     current 
      DESCRIPTION  
          "If the PW is modeled as an ifIndex in the ifTable, this 
           object indicates the value of the ifIndex representing the 
           Ethernet PW on the PSN side in the Etherlike-MIB. Note that 
           this value may be different from the value of pwIfIndex 
           that represent the ifIndex of the PW for ifType 'pw'." 
   
       DEFVAL { 0 } 
      ::= { pwEnetEntry 6 } 
   
  pwEnetRowStatus  OBJECT-TYPE 
      SYNTAX      RowStatus 
      MAX-ACCESS  read-create 
      STATUS      current 
      DESCRIPTION  
          "Enable creating, deleting and modifying this row." 
      ::= { pwEnetEntry 7 } 
   
  pwEnetStorageType  OBJECT-TYPE 
      SYNTAX      StorageType 
      MAX-ACCESS  read-create 
      STATUS      current 
      DESCRIPTION  
          "Indicates the storage type of this row." 
      ::= { pwEnetEntry 8 } 
   
  -- 
  -- Ethernet Priority Mapping Table 
  -- 
   
  pwEnetMplsPriMappingTable  OBJECT-TYPE 
      SYNTAX SEQUENCE OF PwEnetMplsPriMappingTableEntry 
      MAX-ACCESS  not-accessible 
      STATUS      current 
      DESCRIPTION  
          "This table may be used for MPLS PSNs if there is a need  
          to hold multiple PW, each with different COS, for the same 
          user service (port + PW VLAN). Such a need may arise if the 
          MPLS network is capable of L-LSP or E-LSP without multiple 
          COS capabilities.  Each row is indexed by the pwIndex  
          and indicate the PRI bits on the packet received from the  
          user port (or VPLS virtual port) that are 
          classified to this PW. Note that the EXP bit value of the  
          PW is configured in the PW MPLS MIB module." 
   
      ::= { pwEnetObjects 2 } 
   
  pwEnetMplsPriMappingTableEntry  OBJECT-TYPE 
      SYNTAX      PwEnetMplsPriMappingTableEntry 
      MAX-ACCESS  not-accessible 
      STATUS      current 
      DESCRIPTION  
          "Each entry is created by the operator or by the agent  
           based on local policy if special classification based on  
           the PRI bits is required for this PW." 
      INDEX { pwIndex } 
   
      ::= { pwEnetMplsPriMappingTable 1 } 
   
  PwEnetMplsPriMappingTableEntry ::= SEQUENCE { 
      pwEnetMplsPriMapping             BITS, 
      pwEnetMplsPriMappingRowStatus    RowStatus, 
      pwEnetMplsPriMappingStorageType  StorageType 
  } 
   
  pwEnetMplsPriMapping  OBJECT-TYPE 
      SYNTAX     BITS { 
                        pri000 (0), 
                        pri001 (1), 
                        pri010 (2), 
                        pri011 (3), 
                        pri100 (4), 
                        pri101 (5), 
                        pri110 (6), 
                        pri111 (7), 
                        untagged (8) 
      } 
      MAX-ACCESS  read-create 
      STATUS     current 
      DESCRIPTION  
          "This object defines the groups of user PRI mapped into 
          this PW. Each bit set indicates that this user priority  
          is assigned to this PW. 
           
          The value 'untagged' is used to indicate that untagged  
          frames are also associated to this PW. 
           
          This object allows the use of different PSN COS based on  
          user marking of PRI bits in MPLS PSN with L-LSP or  
          E-LSP without multiple COS support. In all other cases,  
          the default value MUST be used. 
           
          It is REQUIRED that there is no overlap on this object  
          between rows serving the same service (port+ PW VLAN). 
           
          In case of missing BIT configuration between rows to  
          the same service, incoming packets with PRI marking not  
          configured should be handled by the PW with the lowest  
          COS. 
          " 
      REFERENCE  
          "See appendix A of 'Encapsulation Methods for Transport of  
           Ethernet Frames Over IP/MPLS Networks' (work-in-progress) 
           for mapping rules of the PRI bits to PSN COS." 
   
      ::= { pwEnetMplsPriMappingTableEntry 1 } 
   
  pwEnetMplsPriMappingRowStatus  OBJECT-TYPE 
      SYNTAX      RowStatus 
      MAX-ACCESS  read-create 
      STATUS      current 
      DESCRIPTION  
          "Enable creating, deleting and modifying this row. 
           pwEnetMplsPriMapping may be changed when this object is 
           in the active(1) state, assuming the new value honors the 
           rules as described in the description clause of  
           pwEnetMplsPriMapping. Otherwise, the row status MUST be 
           set to notActive(3) before a change can be made to  
           pwEnetMplsPriMappingRowStatus." 
      ::= { pwEnetMplsPriMappingTableEntry 2 } 
   
  pwEnetMplsPriMappingStorageType  OBJECT-TYPE 
      SYNTAX      StorageType 
      MAX-ACCESS  read-create 
      STATUS      current 
      DESCRIPTION  
          "Indicates the storage type of this row." 
      ::= { pwEnetMplsPriMappingTableEntry 3 } 
   
  -- 
  -- Ethernet PW Statistics Table 
  -- 
   
  pwEnetStatsTable  OBJECT-TYPE 
      SYNTAX SEQUENCE OF PwEnetStatsEntry 
      MAX-ACCESS  not-accessible 
      STATUS      current 
      DESCRIPTION  
          "This table contains statistical counters specific for  
           Ethernet PW." 
      ::= { pwEnetObjects 3 } 
   
  pwEnetStatsEntry  OBJECT-TYPE 
      SYNTAX      PwEnetStatsEntry 
      MAX-ACCESS  not-accessible 
      STATUS      current 
      DESCRIPTION  
          "Each entry represents the statistics gathered for the  
           PW carrying the Ethernet packets since this PW was  
           first created in the pwEnetTable." 
      INDEX { pwIndex } 
      ::= { pwEnetStatsTable 1 } 

  PwEnetStatsEntry ::= SEQUENCE { 
      pwEnetStatsIllegalVlan        ZeroBasedCounter32, 
      pwEnetStatsIllegalLength      ZeroBasedCounter32 
  } 
   
  pwEnetStatsIllegalVlan  OBJECT-TYPE 
      SYNTAX     ZeroBasedCounter32 
      MAX-ACCESS  read-only 
      STATUS     current 
      DESCRIPTION  
          "The number of packets received (from the PSN) on this PW  
           with an illegal VLAN field, missing VLAN field that was  
           expected, or A VLAN field when it was not expected. This  
           counter is not applicable if the PW type is 'ethernet'  
           (i.e. raw mode), and MUST return the value of zero in 
           this case." 
      ::= { pwEnetStatsEntry 1 } 
   
  pwEnetStatsIllegalLength  OBJECT-TYPE 
      SYNTAX     ZeroBasedCounter32 
      MAX-ACCESS  read-only 
      STATUS     current 
      DESCRIPTION  
          "The number of packets that were received with an illegal  
           Ethernet packet length on this PW. An illegal length is  
           defined as being greater than the value in the advertised  
           MTU supported, or shorter than the allowed Ethernet packet 
           size. The agent should start the value of this counter at  
           the value of zero." 
      ::= { pwEnetStatsEntry 2 } 
   
  --- 
  --- Conformance description 
  --- 
   
  pwEnetGroups      OBJECT IDENTIFIER ::= { pwEnetConformance 1 } 
  pwEnetCompliances OBJECT IDENTIFIER ::= { pwEnetConformance 2 } 
   
   
  -- Compliance requirement for fully compliant implementations.  
   
  pwEnetModuleFullCompliance MODULE-COMPLIANCE 
      STATUS  current 
      DESCRIPTION 
              "The compliance statement for agents that provide full 
               support for PW-ENET MIB Module. Such devices can 
               then be monitored and also be configured using 
               this MIB module." 

      MODULE  -- this module 
        MANDATORY-GROUPS { 
                           pwEnetGroup, 
                           pwEnetStatsGroup 
                          } 
    
     GROUP pwEnetMplsPriGroup 
     DESCRIPTION 
         "Collection of objects defining classification to 
          different PW based on the user's PRI bits mapping. 
          This group is optional, and should be implemented 
          only for MPLS PSN where only L-LSP or single OA  
          E-LSP, exists, and different PSN COS is required 
          based on the PRI mapping." 
   
     OBJECT       pwEnetVlanMode 
     DESCRIPTION "An implementation MUST support at least the value 
                  noChange(2)." 
   
     OBJECT       pwEnetVcIfIndex 
     MIN-ACCESS   read-only 
     DESCRIPTION "Write access and values other than zero are  
                  required only for implementations that support the 
                  modeling the Ethernet PW in the Etherlike-MIB." 
   
     OBJECT       pwEnetRowStatus 
     SYNTAX       RowStatus { active(1), notInService(2), 
                              notReady(3) } 
     WRITE-SYNTAX RowStatus { active(1), notInService(2), 
                              createAndGo(4), destroy(6) 
                            } 
     MIN-ACCESS   read-only 
     DESCRIPTION "Support for createAndWait is not required. Support 
                  of notReady is not required for implementations that 
                  do not support signaling. 
                  Support of read-write is not required for  
                  implementations that do not support more than one 
                  VLAN mapping to the same PW." 
   
     OBJECT       pwEnetMplsPriMappingRowStatus 
     SYNTAX       RowStatus { active(1), notInService(2), 
                              notReady(3) } 
     WRITE-SYNTAX RowStatus { active(1), notInService(2), 
                              createAndGo(4), destroy(6) 
                            } 
     DESCRIPTION "Support for createAndWait is not required." 
   
      ::= { pwEnetCompliances 1 } 
   
  -- Compliance requirement for read-only compliant implementations.  
  pwEnetModuleReadOnlyCompliance MODULE-COMPLIANCE 
      STATUS  current 
      DESCRIPTION 
              "The compliance statement for agents that provide read 
               only support for PW-ENET MIB Module. Such devices can 
               then be monitored but cannot be configured using this 
               MIB module." 
   
      MODULE  -- this module 
        MANDATORY-GROUPS { pwEnetGroup, 
                           pwEnetStatsGroup 
                           } 
    
        GROUP pwEnetMplsPriGroup 
        DESCRIPTION 
            "Collection of objects defining classification to 
             different PW based on the user's PRI bits mapping. 
             This group is optional, and should be implemented 
             only for MPLS PSN where only L-LSP or single OA  
             E-LSP, exists, and different PSN COS is required 
             based on the PRI mapping." 
                         
     OBJECT       pwEnetPwVlan 
     MIN-ACCESS   read-only 
     DESCRIPTION "Write access is not required." 
   
     OBJECT       pwEnetVlanMode 
     MIN-ACCESS   read-only 
     DESCRIPTION "Write access is not required. An implementation  
                  MUST support at least the value noChange(2)." 
   
     OBJECT       pwEnetPortVlan 
     MIN-ACCESS   read-only 
     DESCRIPTION "Write access is not required." 
   
     OBJECT       pwEnetPortIfIndex 
     MIN-ACCESS   read-only 
     DESCRIPTION "Write access is not required." 
   
     OBJECT       pwEnetVcIfIndex 
     MIN-ACCESS   read-only 
     DESCRIPTION "Write access is not required. Values other than  
                  zero are required only for implementations that  
                  support the modeling the Ethernet PW in the  
                  Etherlike-MIB." 
   
     OBJECT       pwEnetRowStatus 
     SYNTAX       RowStatus { active(1), notInService(2), 
                              notReady(3) } 

     MIN-ACCESS   read-only 
     DESCRIPTION "Write access is not required. Support 
                  of notReady is not required for implementations that 
                  do not support signaling." 
   
     OBJECT       pwEnetStorageType 
     MIN-ACCESS   read-only 
     DESCRIPTION "Write access is not required." 
   
     OBJECT       pwEnetMplsPriMapping 
     MIN-ACCESS   read-only 
     DESCRIPTION "Write access is not required." 
   
     OBJECT       pwEnetMplsPriMappingRowStatus 
     SYNTAX       RowStatus { active(1), notInService(2), 
                              notReady(3) } 

     MIN-ACCESS   read-only 
     DESCRIPTION "Write access is not required." 
   
     OBJECT       pwEnetMplsPriMappingStorageType 
     MIN-ACCESS   read-only 
     DESCRIPTION "Write access is not required." 
   
      ::= { pwEnetCompliances 2 } 
   
  -- Units of conformance. 
   
  pwEnetGroup OBJECT-GROUP  
     OBJECTS { 
              pwEnetPwVlan, 
              pwEnetVlanMode, 
              pwEnetPortVlan, 
              pwEnetPortIfIndex, 
              pwEnetVcIfIndex, 
              pwEnetRowStatus, 
              pwEnetStorageType 
     } 
     STATUS  current 
     DESCRIPTION 
         "Collection of objects for basic Ethernet PW config." 
     ::= { pwEnetGroups 1 } 
   
  pwEnetStatsGroup OBJECT-GROUP  
     OBJECTS { 
              pwEnetStatsIllegalVlan, 
              pwEnetStatsIllegalLength 
     }           
     STATUS  current 
     DESCRIPTION 
         "Collection of objects counting various PW level errors." 
     ::= { pwEnetGroups 2 } 
   
  pwEnetMplsPriGroup OBJECT-GROUP  
     OBJECTS { 
              pwEnetMplsPriMapping, 
              pwEnetMplsPriMappingRowStatus, 
              pwEnetMplsPriMappingStorageType 
     }           
     STATUS  current 
     DESCRIPTION 
         "Collection of objects defining classification to 
          different PW based on the user's PRI bits mapping. 
          This group is optional, and should be implemented 
          only for MPLS PSN where only L-LSP or single OA  
          E-LSP exists, and different PSN COS is required 
          based on the PRI mapping." 
     ::= { pwEnetGroups 3 } 

 END 

-- 
--     Copyright (C) The Internet Society (2005).  This document is
--     subject to the rights, licenses and restrictions contained in BCP
--     78, and except as set forth therein, the authors retain all their
--     rights.
-- 
--     This document and the information contained herein are provided
--     on an "AS IS" basis and THE CONTRIBUTOR, THE ORGANIZATION HE/SHE
--     REPRESENTS OR IS SPONSORED BY (IF ANY), THE INTERNET SOCIETY AND
--     THE INTERNET ENGINEERING TASK FORCE DISCLAIM ALL WARRANTIES,
--     EXPRESS OR IMPLIED, INCLUDING BUT NOT LIMITED TO ANY WARRANTY THAT
--     THE USE OF THE INFORMATION HEREIN WILL NOT INFRINGE ANY RIGHTS OR
--     ANY IMPLIED WARRANTIES OF MERCHANTABILITY OR FITNESS FOR A
--     PARTICULAR PURPOSE.
--

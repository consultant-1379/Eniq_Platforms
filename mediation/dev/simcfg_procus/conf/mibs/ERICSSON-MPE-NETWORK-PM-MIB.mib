ERICSSON-MPE-NETWORK-PM-MIB DEFINITIONS ::= BEGIN

IMPORTS
     MODULE-IDENTITY, OBJECT-TYPE, Gauge32 , Counter32 
          FROM SNMPv2-SMI

     MODULE-COMPLIANCE, OBJECT-GROUP
          FROM SNMPv2-CONF

     applIndex
          FROM NETWORK-SERVICES-MIB

     mpeModules
          FROM ERICSSON-MPE-REGISTRY-MIB ;

mpeNetworkPmModule MODULE-IDENTITY
   LAST-UPDATED    "201511200053Z"
   ORGANIZATION    "Ericsson AB"
   CONTACT-INFO    "        Ericsson AB

                    Postal: Ericsson AB
                            Kistagangen 26
                            SE - 164 80 Stockholm
                            Sweden

                       Tel: +46 8 7571500
                       Fax:

                    E-Mail: support@ericsson.com"
   DESCRIPTION     "Counters related to network statistics"
::= { mpeModules 26 }

networkPmObjects  OBJECT IDENTIFIER ::= { mpeNetworkPmModule 1 }

portUtilCnt  OBJECT IDENTIFIER ::= { networkPmObjects 1 }

idsCnt  OBJECT IDENTIFIER ::= { networkPmObjects 2 }

networkPmConformance  OBJECT IDENTIFIER ::= { mpeNetworkPmModule 3 }

networkPmGroups  OBJECT IDENTIFIER ::= { networkPmConformance 1 }

networkPmCompliances  OBJECT IDENTIFIER ::= { networkPmConformance 2 }

portUtilCntTable OBJECT-TYPE
   SYNTAX          SEQUENCE OF PortUtilCntEntry
   MAX-ACCESS      not-accessible
   STATUS          current
   DESCRIPTION     "One instance is created for each IP address that is 
                    listed in the nodesupervisor configuration parameter 
                    &quot;Counter Instance binding&quot;."
::= { portUtilCnt 1 } 

portUtilCntEntry OBJECT-TYPE
   SYNTAX          PortUtilCntEntry
   MAX-ACCESS      not-accessible
   STATUS          current
   DESCRIPTION     "Counters For Port Utilization."
   INDEX { applIndex }
::= { portUtilCntTable  1 }

PortUtilCntEntry  ::= SEQUENCE
{
   portUtilCntTwPorts       Gauge32,
   portUtilCntUnusedPorts   Gauge32,
   portUtilCntEstPorts      Gauge32,
   portUtilCntReusedTwPorts Counter32,
   portUtilCntPortAllocFail Counter32,
   portUtilCntPortAllocAtt  Counter32
}

portUtilCntTwPorts  OBJECT-TYPE
   SYNTAX          Gauge32
   MAX-ACCESS      read-only
   STATUS          current
   DESCRIPTION     "Shows the number of Ports that are currently in state 
                    Time Wait."
::= { portUtilCntEntry 1 }

portUtilCntUnusedPorts  OBJECT-TYPE
   SYNTAX          Gauge32
   MAX-ACCESS      read-only
   STATUS          current
   DESCRIPTION     "Shows the number of Ports that are currently unused."
::= { portUtilCntEntry 2 }

portUtilCntEstPorts  OBJECT-TYPE
   SYNTAX          Gauge32
   MAX-ACCESS      read-only
   STATUS          current
   DESCRIPTION     "Shows the number of Ports that are currently in state 
                    established."
::= { portUtilCntEntry 3 }

portUtilCntReusedTwPorts  OBJECT-TYPE
   SYNTAX          Counter32
   MAX-ACCESS      read-only
   STATUS          current
   DESCRIPTION     "Shows the number of Ports that have been re-used from 
                    state Time Wait.
                    The applUptime epoch of the application instance 
                    should be used as reference point for this counter."
::= { portUtilCntEntry 4 }

portUtilCntPortAllocFail  OBJECT-TYPE
   SYNTAX          Counter32
   MAX-ACCESS      read-only
   STATUS          current
   DESCRIPTION     "Shows the number of Port Utilization Failures.
                    The applUptime epoch of the application instance 
                    should be used as reference point for this counter."
::= { portUtilCntEntry 5 }

portUtilCntPortAllocAtt  OBJECT-TYPE
   SYNTAX          Counter32
   MAX-ACCESS      read-only
   STATUS          current
   DESCRIPTION     "Shows the number of Port Utilization Attempts.
                    The applUptime epoch of the application instance 
                    should be used as reference point for this counter."
::= { portUtilCntEntry 6 }

idsCntAnalyzedPkts  OBJECT-TYPE
   SYNTAX          Counter32
   MAX-ACCESS      read-only
   STATUS          current
   DESCRIPTION     "Shows the number of analyzed packets.
                    The applUptime epoch of the application should be 
                    used as reference point for this counter."
::= { idsCnt 1 }

idsCntDroppedPkts  OBJECT-TYPE
   SYNTAX          Counter32
   MAX-ACCESS      read-only
   STATUS          current
   DESCRIPTION     "Shows the number of packets that were dropped by the 
                    intrusion detection function.
                    The applUptime epoch of the application should be 
                    used as reference point for this counter."
::= { idsCnt 2 }

idsCntInMarginsPkts  OBJECT-TYPE
   SYNTAX          Counter32
   MAX-ACCESS      read-only
   STATUS          current
   DESCRIPTION     "Shows the number of packets that were received inside 
                    the window margins.
                    The applUptime epoch of the application should be 
                    used as reference point for this counter."
::= { idsCnt 3 }

-- Compliance Statements

networkCompliance MODULE-COMPLIANCE
   STATUS          current
   DESCRIPTION     "The compliance statement for network."
   MODULE          -- this module
   MANDATORY-GROUPS {networkConfGroup}
::= { networkPmCompliances 1 }

-- Units of Conformance

networkConfGroup OBJECT-GROUP
   OBJECTS { portUtilCntTwPorts,
             portUtilCntUnusedPorts,
             portUtilCntEstPorts,
             portUtilCntReusedTwPorts,
             portUtilCntPortAllocFail,
             portUtilCntPortAllocAtt,
             idsCntAnalyzedPkts,
             idsCntDroppedPkts,
             idsCntInMarginsPkts}
   STATUS          current
   DESCRIPTION     "A collection of objects providing performance and 
                    fault management information about a network."
::= { networkPmGroups 1 }
END
